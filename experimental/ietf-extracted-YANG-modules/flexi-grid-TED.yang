module flexi-grid-TED {
   namespace "urn:ietf:params:xml:ns:yang:ietf-flexigrid-topology";

   prefix flexigrid;

       import ietf-inet-types {

               prefix inet;
       }

       import network-topology {

               prefix nt;
       }

   organization
      "IETF CCAMP Working Group";

   contact
      "Editor: Jorge Lopez <jorge.lopez_vergara@uam.es>";

   description
      "This module contains a collection of YANG definitions for
      Flexi-Grid.

      Copyright (c) 2015 IETF Trust and the persons identified as
      authors of the code.  All rights reserved.

      Redistribution and use in source and binary forms, with or
      without modification, is permitted pursuant to, and subject
      to the license terms contained in, the Simplified BSD
      License set forth in Section 4.c of the IETF Trust's Legal
      Provisions Relating to IETF Documents
      (http://trustee.ietf.org/license-info).";

   revision 2015-07-01 {
      description
         "version 2.";

   reference
      "RFC XXX: A Yang Data Model for Flexi-Grid Optical Networks ";
   }

   typedef optical-node-type {
      description 
         "Determines the node type: optical-sliceable-transponder";
            type enumeration {
               enum optical-sliceable-transponder;
    }

    typedef modulation {

      description 
         "Enumeration that defines the type of wave modulation";
            type enumeration {
               enum QPSK;
               enum DP_QPSK;
               enum QAM16;
               enum DP_QAM16;
               enum DC_DP_QAM16;
               }

       }

       typedef optical-technology {

               description "Enumeration that defines the type of
optical technology";

               type enumeration {

                       enum Flexigrid;

                       enum WDM50;

                       enum WDM100;

               }

       }

       typedef FEC {

               description "Enumeration that defines the type of
FEC";

               type enumeration {

                       enum reed-solomon;

                       enum hamming-code;

                       enum golay;

               }

       }

       typedef interface-type {

               description "Enumeration that defines if an interface
is numbered or unnumbered";

               type enumeration {

                       enum numbered-interfaces;

                       enum unnumbered-interfaces;

               }
       }

       typedef optical-transponder-ref {

               type leafref {

                       path "/nt:network-
topology/nt:topology/nt:node/nt:node-id";

               }

               description

                       "This type is used by data models that need
to reference

                        an optical transponder.";

       }

       typedef optical-node-ref {

               type leafref {

                       path "/nt:network-
topology/nt:topology/nt:node/nt:node-id";

               }

               description

                       "This type is used by data models that need
to reference

                        an optical node.";

       }

       typedef optical-link-ref {

               type leafref {
                       path "/nt:network-
topology/nt:topology/nt:link/nt:link-id";

               }

               description

                       "This type is used by data models that need
to reference

                        an optical link.";

       }

       typedef optical-node-port-ref {

               type leafref {

                       path "/nt:network-
topology/nt:topology/nt:node/o-ted:interface/o-ted:port-number";

               }

               description

                       "This type is used by data models that need
to reference

                        an optical link.";

       }

       grouping optical-ted-topology-type {

               container optical-ted-topology {

                       presence "indicates optical TED Topology";
               }

       }

       grouping optical-ted-topology-attributes {

               container optical-ted-topology-attributes {

                       leaf name {

                               description "Name of the topology";

                               type string;

                       }

}

       }

       grouping optical-node-type {

               description "Used to determine the type of the
optical node.";

               leaf type {

                       type optical-node-type;

               }

       }

       grouping optical-node-attributes {

               description "Set of attributes of an optical node.";

               list interface {

                       key "name";

                       unique "port-number";

                       description "List of interfaces contained by
the node";

                       leaf name {

                               type string;

                       }

                       leaf port-number {

                               type uint32;

                               description "Number of the port used
by the interface";

                       }

                       leaf input-port {

                               type boolean;
                               description "Determines if the port
is an input port";

                       }

                       leaf output-port {

                               type boolean;

                               description "Determines if the port
is an output port";

                       }

                       leaf description {

                               type string;

                               description "Description of the
interface";

                       }

                       leaf interfaces-type {

                               type interface-type;

                               description "Determines the type of
the interface";

                       }

                       container numbered-interface {

                               when "interfaces-type == numbered-
interfaces";

                               description "Grouping that defines an
numbered interface with an ip-address";

                               leaf n-i-ip-address{

                                       type inet:ip-address;

                               }

                       }

                       container unnumbered-interface {

                               when "interfaces-type == unnumbered-
interfaces";

                               description "Grouping that defines an
unnumbered interface with an ip-address and a label";

                               leaf u-i-ip-address{

                                       type inet:ip-address;

                               }

                               leaf label {

                                       type uint32;

                               }

                       }

               }
               container connectivity-matrix {

                       list connections {

                               key "input-port-id";

                               leaf input-port-id {

                                       type optical-node-port-ref;

                               }

                               leaf output-port-id {

                                       type optical-node-port-ref;

                               }

                       }

               }

       }

       grouping optical-transponder-attributes {

               description "Set of attributes of an optical
transponder.";

               leaf-list available-modulation {

                       type modulation;
                       description "List determining all the
available modulations";

               }

               leaf modulation-type {

                       type modulation;

                       description "Modulation type of the wave";

               }

               leaf-list available-FEC {

                       type FEC;

                       description "List determining all the
available FEC";

               }

               leaf FEC-enabled {

                       type boolean;

                       description "Determines whether the FEC is
enabled or not";

               }

               leaf FEC-type {

                       type FEC;

                       description "FEC type of the transponder";

               }
             uses optical-node-attributes;

       }

       grouping optical-sliceable-transponder-attributes {

               description

                       "Grouping that defines a sliceable
transponder which is composed by several transponders.";

               list transponder-list {

                       key "carrier-id";

                       leaf carrier-id {

                               type uint32;

                       }

                       uses optical-transponder-attributes;

               }

       }

       grouping optical-link-attributes {

               description "Set of attributes of an optical link";
               leaf-list available-label-flexigrid {

                       type bits {

                               bit is-available;

                       }

                       description "Array of bits that determines
whether a spectral slot is available or not.";

                       when "technology-type == Flexigrid";

                       }

                       description "Array of bits that determines
whether a wavelength is available or not.";

                       when "technology-type != Flexigrid";

               }

               leaf N-max {

                       type int32;

                       description "Maximum number of channels
available.";

               }

               leaf base-frequency {

                       type decimal64 {

                               fraction-digits 5;
                       }

                       units THz;

                       default 193.1;

                       description "Default central frequency";

                       reference "draft-ietf-ccamp-flexi-grid-fwk-
01";

               }

               leaf nominal-central-frequency-granularity {

                       type decimal64 {

                               fraction-digits 5;

                       }

                       units GHz;

                       default 6.25;

                       description "It is the spacing between
allowed nominal central frequencies and it is set to 6.25 GHz";

                       reference "draft-ietf-ccamp-flexi-grid-fwk-
01";

               }

               leaf slot-width-granularity {

                       type decimal64 {

                               fraction-digits 5;

                       }

                       units GHz;
                       description "Minimum space between slot
widths";

                       reference "draft-ietf-ccamp-flexi-grid-fwk-
01";

               }

               leaf technology-type {

                       type optical-technology;

                       description "Determines which technology is
used at optical-level";

               }

}

       augment "/nt:network-topology/nt:topology/nt:topology-types"
{

               uses optical-ted-topology-type;

       }

       augment "/nt:network-topology/nt:topology" {

               when "nt:topology-types/optical-ted-topology";

               uses optical-ted-topology-attributes;

       }
       augment "/nt:network-topology/nt:topology/nt:node" {

               when "../nt:topology-types/o-ted:optical-ted-
topology";

               uses optical-node-type;

       }

       augment "/nt:network-topology/nt:topology/nt:node" {

               when "../nt:topology-types/o-ted:optical-ted-
topology";

               uses optical-node-attributes;

       }

       augment "/nt:network-topology/nt:topology/nt:node" {

               when "o-ted:optical-node-type/o-ted:optical-
transponder";

               uses optical-transponder-attributes;

       }

       augment "/nt:network-topology/nt:topology/nt:node" {

               when "o-ted:optical-node-type/o-ted:optical-
sliceable-transponder";

               uses optical-sliceable-transponder-attributes;

       }

       augment "/nt:network-topology/nt:topology/nt:link" {

               when "../nt:topology-types/o-ted:optical-ted-
topology";

               uses optical-link-attributes;
       }

}
