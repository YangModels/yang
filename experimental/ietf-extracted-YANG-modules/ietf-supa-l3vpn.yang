module ietf-supa-l3vpn {
  namespace "urn:ietf:params:xml:ns:yang:ietf-supa-l3vpn";
  // replace with IANA namespace when assigned
  prefix l3vpn;
  organization "IETF";
  contact
    "Editor: Dacheng Zhang
    dacheng.zdc@alibaba-inc.com

    Adel Zaalouk
    adel.ietf@gmail.com

    Kostas Pentikousis
    k.pentikousis@eict.de
    ";

  description
    "This YANG module defines a component that describing
     the ddc service model for creating and optimizing
     tenant's DC (data center) services that are deployed
     in multiple data centers.
  Terms and Acronyms
    L3VPN: Layer 3 Virtual Private Network";

  revision 2015-02-04 {
   description
    "Initial revision.";
   reference "RFC4364, RFC7277";
  }

  list l3vpn-Instance {
    key "instance-name";
    max-elements "65535"; //to be discussed
    description "Indicates the name of the VPN instance
                 created.";

    leaf instance-name {
      type string {
        length "1..64";
        pattern "([^?]*)";
      }
      mandatory true;
      description "L3VPN instance name.";
    }

    leaf servic-type {
      type enumeration {
        enum full-mesh {
          value "0";
          description "full-mesh";
        }
        enum hub-spoke {
          value "1";
          description "hub-spoke";
        }
      }
      default "full-mesh";
      description "Topology type.";
    }

    leaf address-family-type{
      type enumeration {
        enum ipv4uni {
          value "0";
          description "ipv4 unicast";
        }
        enum ipv6uni {
          value "1";
          description "ipv6 unicast";
        }
      }
      default "ipv4uni";
      description " Address family type: IPv4 or IPv6.";
    }

    list access-interface-id {
      key "access-interface-id";
      max-elements "65535";
      description "Access interface ID.";

      leaf access-interface-id {
        type string {
          length "1..64";
          pattern "([^?]*)";
        }
        mandatory true;
        description "Access interface ID.";
      }

      leaf access-interface-address {
        type string {
          pattern "([^?]*)";
        }
        mandatory true;
        description " Access interface address, IPv4 or IPv6.";
      }

      leaf ip-address-mask-length{
        type uint8 {
        range "0..128";
        }
        mandatory true;
        description " IP address mask length.";
      }

      leaf role {
        type enumeration {
          enum edge-if {
            value "0";
            description "edge interface";
            }
          enum center-if {
            value "1";
            description "center interface";
          }
        }
        mandatory true;
        description
          "center-if is only available in hub-spoke mode;
           center-if is the interface in hub node.";
      }

      leaf user-name {
        type string {
          length "1..64";
          pattern "([^?]*)";
        }
        mandatory true;
        description "User name for this access interface.";
      }

      leaf user-password {
        type string {
          length "1..64";
          pattern "([^?]*)";
        }
        mandatory true;
        description "User password for the access interface.";
      }

      leaf physical-node-id {
        type string {
          length "1..64";
          pattern "([^?]*)";
        }
        mandatory true;
        description "Physical node ID.";
      }

      leaf physical-access-interface {
        type string {
          length "1..64";
          pattern "([^?]*)";
        }
        mandatory true;
        description "Physical access interface.";
      }

      container protocol {
        description ".";
        leaf protocol-type {
          type enumeration {
            enum bgp {
              value "0";
              description "bgp";
            }
            enum ospf {
              value "1";
              description "ospf";
            }
            enum isis {
              value "2";
              description "isis";
            }
          }
          default "ospf";
          description "Protocol type.";
        }

        container igp-attribute {
          description ".";

          leaf protocol-id {
            type uint32 {
            }
            default "0";
            description "Valid only when protocol is IGP;
                         it can be AS number.";
          }
        }

        container bgp-attribute {
          description ".";

          leaf remote-as-number {
            type string {
              length "1..11";
            }
            default "0";
            description "Valid only when protocol is BGP.";
          }

          leaf remote-peer-address {
            type string {
            }
            mandatory true;
            description "Valid only when protocol is BGP.";
          }
        }
      }
    }
  }
}
