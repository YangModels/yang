module ietf-flexe {
  yang-version 1.1;
  namespace "urn:ietf:params:xml:ns:yang:ietf-flexe";
  prefix "flexe";

  import iana-if-type {
    prefix ianaift;
  }
  import ietf-interfaces {
    prefix if;
    reference
      "RFC8343: A YANG Data Model for Interface Management";
  }

  organization "IETF CCAMP Working Group";
  contact
    "WG Web:   http://tools.ietf.org/wg/ccamp/
     WG List:  <mailto:ccamp@ietf.org>
     Author:   Yuanlong Jiang
               <mailto:jiangyuanlong@huawei.com>
     Author:   Xiang He
               <mailto: hexiang@huawei.com>
     Author:   Weiqiang Cheng
               <mailto: chengweiqiang@chinamobile.com>";
  description
    "This YANG module defines a data model for the configuration
     of FlexE interface.";

  revision "2019-02-25" {
    description "Initial version";
    reference
      "draft-jiang-ccamp-flexe-yang-00: YANG Data Model for FlexE
       Interface Management ";
  }

  typedef slot-granularity-enumeration {
    type enumeration {
      enum slot-5g {
        value 1;
        description
          "5Gbps per slot.";
      }
      enum slot-25g {
        value 2;
        description
          "25Gbps per slot.";
      }
      enum slot-others {
        value 254;
        description
          "Other type of granularities per slot.";
      }
    }
    description
      "The bandwidth granularity of a slot. Options for this
       enumeration are specified by the OIF standard, currently only
       5G and 25G are defined.";
    reference
      "OIF Flex 2.0: Section 6.7";
  }

  typedef slot-status-enumeration {
    type enumeration {
      enum unavailable {
        value 1;
        description
          "slot is unavailable for FlexE client.";
      }
      enum unused {
        value 2;
        description
          "slot is unused.";
      }
      enum used {
        value 3;
        description
          "slot is used.";
      }
    }
    description
      "The status of a slot. Options for this enumeration are
       specified by the OIF standard, 'used' is implicit.";
    reference
      "OIF Flex 2.0: Section 7.3.4 and Section 7.6";
  }

  typedef flexe-phy-enumeration {
    type enumeration {
      enum 'PHY-100GBASE-R' {
        value 1;
        description
          "100GBASE-R PHY, as defined in FlexE 1.0.";
      }
      enum 'PHY-200GBASE-R' {
        value 2;
        description
          "200GBASE-R PHY, as defined in FlexE 2.0.";
      }
      enum 'PHY-400GBASE-R' {
        value 3;
        description
          "400GBASE-R PHY, as defined in FlexE 2.0.";
      }
    }

    description
      "The current type of PHYs bonded in a FlexE Group. Values for
       this enumeration are specified by the OIF standard.";
    reference
      "OIF Flex 2.0: Section 5.2.1.5";
  }

  typedef calendar-enumeration {
   type enumeration {
    enum "CALENDAR-A" {
      description "Using Calendar A";
    }
    enum "CALENDAR-B" {
      description "Using Calendar B";
    }
   }
   description
      "FlexE Calendar in use, values for this enumeration
       are specified by the OIF standard.";
    reference
      "OIF Flex 2.0: Section 6.7";
  }

  augment "/if:interfaces/if:interface" {

    when "if:type = 'ianaift:flexethernet'" {
      description "Applies to Flex Ethernet interfaces";
    }

    description
      "Augment interface model with OIF Flex Ethernet interface
       specific configuration nodes. Each FlexE interface
       represents a FlexE Group configured in a device.";

    container flexe-group {
      description
        "The struct containing all FlexE related configuration
         (see OIF FlexE 2.0 Section 6.1).
         Note that max number of FlexE groups in a network is 63.";

      leaf group-number {
        type uint32 {
          range "1..1048574";
        }
        description
          "FlexE Group Number as defined in Section 7.3.6 of FlexE
           2.0.";
      }

       leaf slot-granularity {
          type slot-granularity-enumeration;
          default "slot-5g";
          description
          "The granularity of a slot in a FlexE group.";
       }

       leaf flexe-phy-type {
          type flexe-phy-enumeration;
          default "PHY-100GBASE-R";
          description
           "The type of PHYs bonded in a FlexE Group.";
       }

       leaf flexe-calendar-inuse {
          type calendar-enumeration;
          default "CALENDAR-A";
          description
           "The FlexE Calendar in use for a FlexE Group.";
       }

       list flexe-phy-list {

         key "phy-number";
         description
           "List of PHYs bonded in a FlexE group per FlexE 2.0.";
         leaf phy-number {
           type uint8 {
             range "1 .. 254";
           }
           description
             "PHY number of a FlexE PHY.
              If PHY type is 100GBASE-R, phy-number is [1,254].
              If PHY type is 200GBASE-R, phy-number is [1,126].
              If PHY type is 400GBASE-R, phy-number is [1, 62].";
         }

         list flexe-inst-list {
            key "instance-number";
            description
              "List of instances in a FlexE PHY as defined in OIF.
               Max elements of flexe-inst-list in a FlexE PHY:
               If PHY type is 100GBASE-R, max-elements is 1.
               If PHY type is 200GBASE-R, max-elements is 2.
               If PHY type is 400GBASE-R, max-elements is 4.";

            leaf instance-number {
              type uint8;
              description
                "Instance number of an instance. Its range relies on
                 phy-number of the PHY wherein this instance belongs:
                 If PHY type is 100GBASE-R:
                    instance-number=phy-number
                 If PHY type is 200GBASE-R:
                    instance-number=2*phy-number+[0, 1]
                 If PHY type is 400GBASE-R:
                    instance-number=4*phy-number+[0, 3] ";
            }

            list calendar-slot-list {
              key "slot-id";
              leaf slot-id {
                type uint8;
                description
                  "slot id of a slot in an instance.";
              }
              description
                "List of slots in a FlexE instance, i.e., sub-
                 calendar per instance in FlexE 2.0. Max elements of
                 calendar-slot-list for a FlexE instance is:
                 If slot-granularity=slot-5g, max-elements is 20.
                 If slot-granularity=slot-25g, max-elements is 4.";
              leaf flexe-slot-status {
                type slot-status-enumeration;
                default unused;
                description
                  "Slot status of a slot in an instance.";
              }
            } //calendar-slot-list
         } //flexe-inst-list
       } //flexe-phy-list

       list flexe-client-list {

         key "client-id";
         description
           "List of FlexE clients in a FlexE Group.";
         leaf client-id {
           type uint16;
           description
             "FlexE client ID as defined in FlexE IA.";
         }
         leaf group-number {
           type uint32 {
             range "1..1048574";
           }
           description
            "FlexE Group Number of the FlexE group for this client.";
         }

         list mapped-slot-list {
           key "mapped-slot-id";
           description
              "List of mapped-slots for a FlexE client.";
           leaf mapped-slot-id {
             type uint8;
             description
                  "Slot id of a slot in an instance for a client.";
           }
           leaf mapped-phy-number {
             type uint8;
             description
               "PHY number of a slot for a client.";
           }
           leaf mapped-inst-number {
             type uint8;                 description
               "Instance number of a slot for a client.";
           }
         } // mapped-slot-list

         leaf flexe-client-status {
           type uint8;
           config false;
           description
                "Fault status for a client indicated in its mapped
                 slots. If any slot is in fault, the client status
                 is indicated in fault. Status includes:
                 OK, Local Fault, Remote Fault and etc.";
         }

       } //flexe-client-list
    } //flexe-group
  }  //augment
}
