module ietf-network-slice {
  yang-version 1.1;
  namespace "urn:ietf:params:xml:ns:yang:ietf-network-slice";
  prefix "ns";

  import ietf-network {
    prefix "nw";
    reference "RFC 8345: A YANG Data Model for Network Topologies";
  }
  import ietf-network-topology {
    prefix "nt";
    reference "RFC 8345: A YANG Data Model for Network Topologies";
  }
  import ietf-te-types {
    prefix "te-types";
    reference
      "RFC 8776: Traffic Engineering Common YANG Types";
  }

  organization
    "IETF Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Jeff Tantsura
               <mailto:jefftant.ietf@gmail.com>

     Editor:   Igor Bryskin
               <mailto:i_bryskin@yahoo.com>

     Editor:   Luis Miguel Contreras Murillo
               <mailto:luismiguel.contrerasmurillo@telefonica.com>

     Editor:   Qin Wu
               <mailto:bill.wu@huawei.com>

     Editor:   Sergio Belotti
               <mailto:sergio.belotti@nokia.com>

     Editor:   Reza Rokui
               <mailto:reza.rokui@nokia.com>
    ";

  description
    "YANG data model for representing and managing network
     slices.

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2020-11-01 {
    description "Initial revision";
    reference
      "RFC XXXX: YANG Data Model for Network Slices";
  }

  /*
   * Identities
   */
  identity isolation-level {
    description
      "Base identity for the isolation-level.";
    reference
      "GSMA-NS-Template: Generic Network Slice Template,
       Version 3.0.";
  }
  identity no-isolation {
    base isolation-level;
    description
      "Network slices are not separated.";
  }
  identity physical-isolation {
    base isolation-level;
    description
      "Network slices are physically separated (e.g. different rack,
       different hardware, different location, etc.).";
  }
  identity logical-isolation {
    base isolation-level;
    description
      "Network slices are logically separated.";
  }
  identity process-isolation {
    base physical-isolation;
    description
      "Process and threads isolation.";
  }
  identity physical-memory-isolation {
    base physical-isolation;
    description
      "Process and threads isolation.";
  }
  identity physical-network-isolation {
    base physical-isolation;
    description
      "Process and threads isolation.";
  }
  identity virtual-resource-isolation {
    base logical-isolation;
    description
      "A network slice has access to specific range of resources
       that do not overlap with other network slices
       (e.g. VM isolation).";
  }
  identity network-functions-isolation {
    base logical-isolation;
    description
      "NF (Network Function) is dedicated to the network slice, but
       virtual resources are shared.";
  }
  identity service-isolation {
    base logical-isolation;
    description
      "NSC data are isolated from other NSCs, but virtual
       resources and NFs are shared.";
  }

  /*
   * Groupiings
   */
  grouping network-slice-topology-attributes {
    description "Network Slice topology scope attributes.";
    container network-slice {
      description
        "Containing Network Slice attributes.";
      leaf optimization-criterion {
        type identityref {
          base te-types:objective-function-type;
        }
        description
          "Optimization criterion applied to this topology.";
      }
      leaf delay-tolerance {
        type boolean;
        description
          "'true' if is not too critical how long it takes to deliver
           the amount of data.";
        reference
          "GSMA-NS-Template: Generic Network Slice Template,
           Version 3.0.";
      }
      leaf-list periodicity {
        type uint64;
        units seconds;
        description
          "A list of periodicities supported by the network slice.";
        reference
          "GSMA-NS-Template: Generic Network Slice Template,
           Version 3.0.";
      }
      leaf isolation-level {
        type identityref {
          base isolation-level;
        }
        description
          "A network slice instance may be fully or partly, logically
           and/or physically, isolated from another network slice
           instance. This attribute describes different types of
           isolation:";
      }
    } // network-slice
  } // network-slice-topology-attributes

  grouping network-slice-node-attributes {
    description "Network Slice node scope attributes.";
    container network-slice {
      description
        "Containing Network Slice attributes.";
      leaf isolation-level {
        type identityref {
          base isolation-level;
        }
        description
          "A network slice instance may be fully or partly, logically
           and/or physically, isolated from another network slice
           instance. This attribute describes different types of
           isolation:";
      }
      leaf compute-node-id {
        type string;
        description
          "Reference to a compute node instance specified in
           a data model specifying the computing resources.";
      }
      leaf storage-id {
        type string;
        description
          "Reference to a storage instance specified in
           a data model specifying the storage resources.";
      }
    } // network-slice
  } // network-slice-node-attributes

  grouping network-slice-link-attributes {
    description "Network Slice link scope attributes";
    container network-slice {
      description
        "Containing Network Slice attributes.";
      leaf delay-tolerance {
        type boolean;
        description
          "'true' if is not too critical how long it takes to deliver
           the amount of data.";
        reference
          "GSMA-NS-Template: Generic Network Slice Template,
           Version 3.0.";
      }
      leaf-list periodicity {
        type uint64;
        units seconds;
        description
          "A list of periodicities supported by the network slice.";
        reference
          "GSMA-NS-Template: Generic Network Slice Template,
           Version 3.0.";
      }
      leaf isolation-level {
        type identityref {
          base isolation-level;
        }
        description
          "A network slice instance may be fully or partly, logically
           and/or physically, isolated from another network slice
           instance. This attribute describes different types of
           isolation:";
      }
    } // network-slice
  } // network-slice-link-attributes

  /*
   * Data nodes
   */
  augment "/nw:networks/nw:network/nw:network-types" {
    description
      "Defines the Network Slice topology type.";
    container network-slice {
      presence "Indicates Network Slice topology";
      description
        "Its presence identifies the Network Slice type.";
    }
  }

  augment "/nw:networks/nw:network" {
    when "nw:network-types/ns:network-slice" {
      description "Augment only for Network Slice topology.";
    }
    description "Augment topology configuration and state.";
    uses network-slice-topology-attributes;
  }

  augment "/nw:networks/nw:network/nw:node" {
    when "../nw:network-types/ns:network-slice" {
      description "Augment only for Network Slice topology.";
    }
    description "Augment node configuration and state.";
    uses network-slice-node-attributes;
  }

  augment "/nw:networks/nw:network/nt:link" {
    when "../nw:network-types/ns:network-slice" {
      description "Augment only for Network Slice topology.";
    }
    description "Augment link configuration and state.";
    uses network-slice-link-attributes;
  }

}
