module ietf-bfd {
  namespace "urn:ietf:params:xml:ns:yang:ietf-bfd";
  // replace with IANA namespace when assigned
  prefix "bfd";

  import ietf-interfaces {
    prefix "if";
  }

  import ietf-inet-types {
    prefix "inet";
  }

  import ietf-yang-types {
    prefix "yang";
  }

  organization "IETF BFD Working Group";

  contact
    "WG Web:   <http://tools.ietf.org/wg/bfd>
     WG List:  <rtg-bfd@ietf.org>
     WG Chair: Jeff Haas
     WG Chair: Nobo Akiya
     Editor:   Lianshu Zheng and Reshad Rahman";

  description
    "This module contains the YANG definition for BFD parameters as
     per RFC5880, RFC5881 and RFC5883";

  revision 2015-05-25 {
    description "Initial revision.";
    reference "RFC XXXX: A YANG data model for BFD";
  }

  typedef discriminator {
    type uint32 {
      range 1..4294967295;
    }
    description "BFD discriminator";
  }

  typedef diagnostic {
    type enumeration {
      enum none {
        value 0;
        description "None";
      }
      enum controlExpiry {
        value 1;
        description "Control timer expiry";
      }
      enum echoFailed {
        value 2;
        description "Echo failure";
      }
      enum nborDown {
        value 3;
        description "Neighbor down";
      }
      enum fwdingReset {
        value 4;
        description "Forwarding reset";
      }
      enum pathDown {
        value 5;
        description "Path down";
      }
      enum concPathDown {
        value 6;
        description "Concatenated path down";
      }
      enum adminDown {
        value 7;
        description "Admin down";
      }
      enum reverseConcPathDown {
        value 8;
        description "Reverse concatenated path down";
      }
    }
    description "BFD diagnostic";
  }

  typedef state {
    type enumeration {
      enum adminDown {
        value 0;
        description "admindown";
      }
      enum down {
        value 1;
        description "down";
      }
      enum init {
        value 2;
        description "init";
      }
      enum up {
        value 3;
        description "up";
      }
    }
    description "BFD state";
  }

  typedef multiplier {
    type uint8 {
      range 1..255;
    }
    description "Multiplier";
  }

  typedef TTL {
    type uint8 {
      range 1..255;
    }
    description "Time To Live";
  }

  typedef bfd-auth-algorithm {
    type enumeration {
      enum simple-password {
        description
          "Simple password";
      }

      enum keyed-md5 {
        description
          "Keyed message Digest 5";
      }

      enum meticulous-keyed-md5 {
        description
          "Meticulous keyed message Digest 5";
      }

      enum keyed-sha-1 {
        description
          "Keyed secure hash algorithm (SHA1) ";
      }

      enum meticulous-keyed-sha-1 {
        description
          "Meticulous keyed secure hash algorithm (SHA1) ";
      }
    }
    description "Authentication algorithm";
  }

  typedef vrfName {
    type string;
    description "VRF Name";
  }

  feature bfd-centralized-session-config {
    description "BFD session centralized config supported";
  }
  feature bfd-interface-config {
    description "BFD per-interface config supported";
  }
  feature bfd-authentication {
    description "BFD authentication supported";
  }

  grouping bfd-grouping-common-cfg-parms {
    description "BFD grouping for common config parameters";

    leaf local-multiplier {
      type multiplier;
      default 3;
      description "Local multiplier";
    }

    leaf desired-min-tx-interval {
      type uint32;
      units microseconds;
      mandatory true;
      description
        "Desired minimum transmit interval of control packets";
    }

    leaf required-min-rx-interval {
      type uint32;
      units microseconds;
      mandatory true;
      description
        "Required minimum receive interval of control packets";
    }

    leaf demand-enabled {
      type boolean;
      default false;
      description "To enbale demand mode";
    }

    leaf enable-authentication {
      type boolean;
      default false;
      description
        "If set, the Authentication Section is present and the
         session is to be authenticated (see RFC5880 section 6.7
         for details).";
    }

    container authentication-parms {
      if-feature bfd-authentication;
      description "Parameters for authentication";
      leaf key-chain-name {
        type string;
        must "../algorithm" {
          error-message
            "May not be configured without algorithm";
          description "Requires algorithm";
        }
        description
          "Key chain name";
      }
      leaf algorithm {
        type bfd-auth-algorithm;
        must "../key-chain" {
          error-message
            "May not be configured without key-chain";
          description "Requires key-chain";
        }
        description "Authentication algorithm to be used";
      }
    }
  }

  grouping bfd-grouping-echo-cfg-parms {
    description "BFD grouping for echo config parameters";
    leaf desired-min-echo-tx-interval {
      type uint32;
      units microseconds;
      default 0;
      description "Desired minumum transmit interval for echo";
    }

    leaf required-min-echo-rx-interval {
      type uint32;
      units microseconds;
      default 0;
      description "Required minimum receive interval for echo";
    }
  }

  grouping bfd-client-base-cfg-parms {
    description
      "BFD grouping for base config parameters which could be used
       by a protocol which is a client of BFD";

    container bfd-cfg {
      description "BFD configuration";
      leaf enabled {
        type boolean;
        default false;
        description "True if BFD is enabled";
      }

      leaf local-multiplier {
        type multiplier;
        default 3;
        description "Multiplier transmitted by local system";
      }

      leaf desired-min-tx-interval {
        type uint32;
        units microseconds;
        mandatory true;
        description
          "Desired minimum transmit interval of control packets";
      }

      leaf required-min-rx-interval {
        type uint32;
        units microseconds;
        mandatory true;
        description
          "Required minimum receive interval of control packets";
      }
    }
  }

  grouping bfd-client-full-cfg-parms {
    description
      "BFD grouping for complete config parameters which could be
       used by a protocol which is a client of BFD.";

    container bfd-cfg {
      description "BFD configuration";
      leaf enabled {
        type boolean;
        default false;
        description "True if BFD is enabled";
      }

      uses bfd-grouping-common-cfg-parms;

      uses bfd-grouping-echo-cfg-parms;
    }
  }

  grouping bfd-all-session {
    description "BFD session operational information";
    leaf sesssion-type {
      type enumeration {
        enum ip-single-hop {
          value "0";
          description "IP single hop";
        }
        enum ip-multi-hop {
          value "1";
          description "IP multi hop";
        }
      }
      description
        "BFD session type, this indicates the path type that BFD is
        running on";
    }
    leaf local-discriminator {
      type discriminator;
      description "Local discriminator";
    }
    leaf remote-discriminator {
      type discriminator;
      description "Remote discriminator";
    }
    leaf remote-multiplier {
      type multiplier;
      description "Remote multiplier";
    }
    leaf out-interface {
      type if:interface-ref;
      description "Outgoing physical interface name";
    }
    leaf demand-capability{
      type boolean;
      description "Local demand mode capability";
    }

    list session-running {
      description "BFD session running information";
      leaf local-state {
        type state;
        description "Local state";
      }
      leaf remote-state {
        type state;
        description "Remote state";
      }
      leaf local-diagnostic {
        type diagnostic;
        description "Local diagnostic";
      }
      leaf remote-diagnostic {
        type diagnostic;
        description "Remote diagnostic";
      }
      leaf detect-Mode {
        type enumeration {
          enum async-with-echo {
            value "0";
            description "Async with echo";
          }
          enum async-without-echo {
            value "1";
            description "Async without echo";
          }
          enum demand-with-echo {
            value "2";
            description "Demand with echo";
          }
          enum demand-without-echo {
            value "3";
            description "Demand without echo";
          }
        }
        description "Detect mode";
      }
      leaf actual-tx-interval {
        type uint32;
        units microseconds;
        description "Actual transmit interval";
      }
      leaf actual-rx-interval {
        type uint32;
        units microseconds;
        description "Actual receive interval";
      }
      leaf actual-echo-tx-interval {
        type uint32;
        units microseconds;
        description "Actual echo transmit interval";
      }
      leaf detect-time {
        type uint32;
        units microseconds;
        description "Detect time";
      }
    }

    list sesssion-statistics {
      description "BFD session statistics";

      leaf create-time {
        type yang:date-and-time;
        description
          "Time and date when session was created";
      }
      leaf last-down-time {
        type yang:date-and-time;
        description
          "Time and date of last time the session went down";
      }
      leaf last-up-time {
        type yang:date-and-time;
        description
          "Time and date of last time the session went up";
      }
      leaf receive-pkt {
        type uint64;
        description "Received Packet Count";
      }
      leaf send-pkt {
        type uint64;
        description "Sent Packet Count";
      }
      leaf down-count {
        type uint32;
        description "Session Down Count";
      }
      leaf receive-bad-pkt {
        type uint64;
        description "Received bad packet count";
      }
      leaf send-failed-pkt {
        type uint64;
        description "Packet Failed to Send Count";
      }
      leaf short-break-count {
        type uint32;
        default "0";
        description "Shortbreak count";
      }
    }
  }

  container bfd {
    description "BFD top-level container";
    container bfd-cfg {
      description "BFD configuration";
      container bfd-session-cfg {
        if-feature bfd-centralized-session-config;
        description "BFD session configuration";
        list session-ip-sh {
          key "interface dest-addr";
          description "List of IP single-hop sessions";
          leaf interface {
            type if:interface-ref;
            description
              "Interface on which the IP single-hop session is
             running.";
          }
          leaf dest-addr {
            type inet:ip-address;
            description
              "IP address of the peer";
          }
          leaf admin-down {
            type boolean;
            default false;
            description
              "Is the BFD session administratively down";
          }
          uses bfd-grouping-common-cfg-parms;

          uses bfd-grouping-echo-cfg-parms;
        }

        list session-ip-mh {
          key "vrf-name source-addr dest-addr";
          description "List of IP multi-hop sessions";

          leaf vrf-name {
            type vrfName;
            description "Routing instance";
          }
          leaf source-addr {
            type inet:ip-address;
            description
              "Local IP address";
          }
          leaf dest-addr {
            type inet:ip-address;
            description
              "IP address of the peer";
          }
          leaf admin-down {
            type boolean;
            default false;
            description
              "Is the BFD session administratively down";
          }
          uses bfd-grouping-common-cfg-parms;

          leaf tx-ttl {
            type TTL;
            default 255;
            description "TTL of outgoing BFD control packets";
          }
          leaf rx-ttl {
            type TTL;
            mandatory true;
            description
              "Minimum allowed TTL value for incoming BFD control
            packets";
          }
        }
      }

      list bfd-interface-cfg {
        if-feature bfd-interface-config;
        key interface;

        description "Per-interface BFD configuration";
        leaf interface {
          type if:interface-ref;
          description "Interface";

        }
        uses bfd-grouping-common-cfg-parms;

        uses bfd-grouping-echo-cfg-parms;

      }
    }

    container bfd-oper {
      config "false";
      description "BFD operational container";
      container bfd-session-statistics {
        description "BFD session counters";
        leaf ip-sh-session-num {
          type uint32;
          description "IP single hop session number";
        }
        leaf ip-mh-session-num {
          type uint32;
          description "IP multi hop session Number";
        }
        leaf total-session-num {
          type uint32;
          description "Total session number";
        }
        leaf session-up-num {
          type uint32;
          description "Session up number";
        }
        leaf sess-down-num {
          type uint32;
          description "Session down number";
        }
      }

      container bfd-session-lists {
        description "Contains multiple session lists, one per type";
        list session-ip-sh {
          key "interface dest-addr";
          description "BFD IP single-hop sessions";
          leaf interface {
            type if:interface-ref;
            description
              "Interface on which the BFD session is running.";
          }
          leaf dest-addr {
            type inet:ip-address;
            description "BFD peer address";
          }

          uses bfd-all-session;
        }

        list session-ip-mh {
          key "vrfName source-addr dest-addr";
          description "BFD IP multi-hop sessions";
          leaf vrfName {
            type vrfName;
            description "VRF";
          }
          leaf source-addr {
            type inet:ip-address;
            description "BFD source address";
          }
          leaf dest-addr {
            type inet:ip-address;
            description "BFD peer address";
          }
          leaf ttl {
            type TTL;
            description "TTL of session";
          }
          uses bfd-all-session;
        }
      }
    }
  }

  grouping bfd-notification-params {
    description
      "This group describes common params that will be send
        as part of BFD notification";

    leaf local-discr {
      type discriminator;
      description "BFD local discriminator";
    }

    leaf remote-discr {
      type discriminator;
      description "BFD remote discriminator";
    }

    leaf new-state {
      type state;
      description "Current BFD state";
    }

    leaf state-change-reason {
      type string;
      description "BFD state change reason";
    }

    leaf time-in-previous-state {
      type string;
      description
        "How long the BFD session was in the previous state";
    }

    leaf dest-addr {
      type inet:ip-address;
      description "BFD peer address";
    }
  }

  notification bfd-singlehop-notification {
    description
      "Notitification for BFD single-hop session state change";

    uses bfd-notification-params;

    leaf interface {
      type if:interface-ref;
      description "Interface to which this BFD session belongs to";
    }

    leaf echo-enabled {
      type boolean;
      description "Was echo enabled for BFD";
    }
  }

  notification bfd-multihop-notification {
    description
      "Notitification for BFD multi-hop session state change";

    uses bfd-notification-params;

    leaf vrf-name {
      type vrfName;
      description "Routing instance";
    }

    leaf source-addr {
      type inet:ip-address;
      description "BFD local address";
    }
  }
}
