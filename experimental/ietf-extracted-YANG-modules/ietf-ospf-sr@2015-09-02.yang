module ietf-ospf-sr {
  namespace "urn:ietf:params:xml:ns:yang:ietf-ospf-sr";

  prefix ospf-sr;

  import ietf-inet-types {
    prefix "inet";
  }

  import ietf-yang-types {
    prefix "yang";
  }

  import ietf-routing {
    prefix "rt";
  }
  import ietf-segment-routing {
    prefix "sr";
  }
  import ietf-ospf {
    prefix "ospf";
  }

  organization
    "Cisco Systems
     170 West Tasman Drive
     San Jose, CA 95134-1706
     USA";

  contact
     "WG Web:   <http://tools.ietf.org/wg/ospf/>
      WG List:  <mailto:ospf@ietf.org>

      WG Chair: Acee Lindem
                <mailto:acee@cisco.com>

      WG Chair: Abhay Roy
                <mailto:akr@cisco.com>

      Editor:   Derek Yeung
                <mailto:myeung@cisco.com>
      Author:   Derek Yeung
                <mailto:myeung@cisco.com>
      Author:   Yingzhen Qu
                <mailto:yiqu@cisco.com>
      Author:   Acee Lindem
                <mailto:acee@cisco.com>
      Author:   Jeffrey Zhang
                <mailto:zzhang@juniper.net>
      Author:   Ing-Wher Chen
                <mailto:ing-wher.chen@ericsson.com>
      Author:   Greg Hankins
                <mailto:greg.hankins@alcatel-lucent.com>";

  description
    "This YANG module defines the generic configuration
     data for OSPF, which is common across all of the vendor
     implementations of the protocol. It is intended that the module
     will be extended by vendors to define vendor-specific
     OSPF configuration parameters and policies,
     for example route maps or route policies.

     Terms and Acronyms

     OSPF (ospf): Open Shortest Path First

     IP (ip): Internet Protocol

     IPv4 (ipv4):Internet Protocol Version 4

     IPv6 (ipv6): Internet Protocol Version 6

     MTU (mtu) Maximum Transmission Unit
    ";

  revision 2015-09-02 {
    description
      "* Author list update.
       * Editorial changes.";
    reference
      "RFC XXXX: A YANG Data Model for OSPF Segment Routing";
  }

  revision 2015-07-06 {
    description
      "Initial revision.";
    reference
      "RFC XXXX: A YANG Data Model for OSPF Segment Routing";
  }

  feature ti-lfa {
    description
      "Enhance IPFRR with ti-lfa support";
  }

  /* Configuration */

  augment "/rt:routing/rt:routing-instance/rt:routing-protocols"
        + "/rt:routing-protocol/ospf:ospf/ospf:instance" {
    when "../../rt:type = 'ospf:ospfv2' or "
       + "../../rt:type = 'ospf:ospfv3'" {
      description
      "This augment OSPF routing protocol when used";
    }
    description
     "This augments OSPF protocol configuration
      with segment routing.";
    uses sr:controlplane-cfg;
  }

  augment "/rt:routing/rt:routing-instance/rt:routing-protocols/"
        + "rt:routing-protocol/ospf:ospf/ospf:instance/"
        + "ospf:areas/ospf:area/ospf:interfaces/ospf:interface" {
    when "../../../../../../rt:type = 'ospf:ospfv2' or "
       + "../../../../../../rt:type = 'ospf:ospfv3'" {
      description
      "This augment OSPF routing protocol when used";
    }
    description
     "This augments OSPF protocol configuration
      with segment routing.";

    uses sr:igp-interface-cfg;
  }

  augment "/rt:routing/rt:routing-instance/rt:routing-protocols/"
        + "rt:routing-protocol/ospf:ospf/ospf:instance/"
        + "ospf:areas/ospf:area/ospf:interfaces/ospf:interface/"
        + "ospf:fast-reroute" {
    when "../../../../../../../rt:type = 'ospf:ospfv2' or "
       + "../../../../../../../rt:type = 'ospf:ospfv3'" {
      description
        "This augment OSPF routing protocol when used";
    }
    description
      "This augments ISIS IP FRR with TILFA.";

    container ti-lfa {
      if-feature ti-lfa;
      leaf enable {
        type boolean;
        description
         "Enables TI-LFA computation.";
      }
      description
        "TILFA configuration.";
    }
  }

  /* Operational states */

  augment "/rt:routing-state/rt:routing-instance/"
        + "rt:routing-protocols/rt:routing-protocol/"
        + "ospf:ospf/ospf:instance" {
    when "../../rt:type = 'ospf:ospfv2' or "
       + "../../rt:type = 'ospf:ospfv3'" {
      description
      "This augment OSPF routing protocol when used";
    }
    description
     "This augments OSPF protocol configuration
      with segment routing.";

    uses sr:controlplane-cfg;
  }

  augment "/rt:routing-state/rt:routing-instance/"
        + "rt:routing-protocols/rt:routing-protocol/"
        + "ospf:ospf/ospf:instance/ospf:areas/ospf:area/"
        + "ospf:interfaces/ospf:interface" {
    when "../../../../../../rt:type = 'ospf:ospfv2' or "
       + "../../../../../../rt:type = 'ospf:ospfv3'" {
      description
      "This augment OSPF routing protocol when used";
    }
    description
     "This augments OSPF protocol configuration
      with segment routing.";

    uses sr:igp-interface-cfg;
  }

  /* Database */

  grouping sid-sub-tlv {
    description "SID/Label sub-tlv grouping.";
    container sid-sub-tlv {
      description
        "Used to advertise the SID/Label associated with a prefix or
         adjacency.";
      leaf sid {
        type uint32;
        description "A 20 bit label or 32 bit SID.";
      }
    }
  }

  grouping prefix-sid-sub-tlvs {
    description "Prefix SID sub-tlvs";
    container perfix-sid-sub-tlvs{
      description "prefix sid sub-tlv.";
      list prefix-sid-sub-tlv {
        description "prefix sid sub-tlv.";
        leaf flags {
          type bits {
            bit NP {
              description
                "No-PHP flag.";
            }
            bit M {
              description
                "Mapping server flag.";
            }
            bit E {
              description
                "Explicit-NULL flag.";
            }
            bit V {
              description
                "Value/Index flag.";
            }
            bit L {
              description
                "Local flag.";
            }
          }
          description "Flags.";
        }
        leaf mt-id {
          type uint8;
          description "Multi-topology ID.";
        }
        leaf algorithm {
          type uint8;
          description
            "The algorithm the prefix-sid is associated with.";
        }
        leaf sid {
          type uint32;
          description "An index or label.";
        }
      }
    }
  }

  grouping sid-binding-sub-tlvs {
    description "SID/Label binding sub-tlv grouping.";
    container sid-binding-sub-tlvs {
      description "sid binding sub-tlvs.";
      list sid-binding-sub-tlv {
        description "sid binding sub-tlv.";
        leaf flags {
          type bits {
            bit M {
              description
                "Mirroring context flag.";
            }
          }
          description "Flags.";
        }
        leaf mt-id {
          type uint8;
          description "Multi-topology ID.";
        }
        leaf weight {
          type uint8;
          description "Weight for load-balancing purposes.";
        }

        uses sid-sub-tlv;

        container ero-metric-sub-tlv {
          description "The cost of an ERO path.";
          leaf metric {
            type uint32;
            description "The aggregate IGP or TE path cost.";
          }
        }

        container ipv4-ero-sub-tlv {
          description
            "The ipv4 ERO sub-tlv describes a path segment
             using ipv4 address.";
          leaf flags {
            type bits {
              bit L {
                description
                  "If set, then the segment path is designated as
                   'loose'. Otherwise as 'strict'.";
              }
            }
            description "Flags.";
          }
          leaf ipv4-address {
            type inet:ipv4-address;
            description "The address of the explicit route hop.";
          }
        }
        container unnumbered-ero-sub-tlv {
          description "The unnumbered interface ID ERO sub-tlv
                       describes a path segment that includes an
                       unnumbered interface.";
          leaf flags {
            type bits {
              bit L {
                description
                  "If set, then the segment path is designated as
                   'loose'. Otherwise as 'strict'.";
              }
            }
            description "Flags.";
          }
          leaf router-id {
            type yang:dotted-quad;
            description "Router-id of the next-hop.";
          }
          leaf interface-id {
            type uint32;
            description
              "The identifier assigned to the link by the
               router specified by the router-id.";
          }
        }
        container ipv4-backup-ero-sub-tlv {
          description
            "The ipv4 backup ERO sub-tlv describes a path
             segment using ipv4 address.";
          leaf flags {
            type bits {
              bit L {
                description
                  "If set, then the segment path is designated as
                   'loose'. Otherwise as 'strict'.";
              }
            }
            description "Flags.";
          }
          leaf ipv4-address {
            type inet:ipv4-address;
            description "The address of the explicit route hop.";
          }
        }
        container unnumbered-backup-ero-sub-tlv {
          description "The unnumbered interface ID backup ERO sub-tlv
                       describes a path segment that includes an
                       unnumbered interface.";
          leaf flags {
            type bits {
              bit L {
                description
                  "If set, then the segment path is designated as
                   'loose'. Otherwise as 'strict'.";
              }
            }
            description "Flags.";
          }
          leaf router-id {
            type yang:dotted-quad;
            description "Router-id of the next-hop.";
          }
          leaf interface-id {
            type uint32;
            description
              "The identifier assigned to the link by the
              router specified by the router-id.";
          }
        }
      }
    }
  }

  grouping extended-prefix-range-tlvs {
    description "Extended prefix range TLV grouping.";

    container extended-prefix-range-tlvs {
      description "The list of range of prefixes.";
      list extended-prefix-range-tlv {    //type=2?
        description "The range of prefixes.";
        leaf range-size {
          type uint16;
          description "The number of prefixes covered by the
                       advertisement.";
        }
        leaf flags {
          type bits {
            bit IA {
              description
                "Inter-Area flag.";
            }
          }
          description "Flags.";
        }
        leaf prefix {
          type inet:ip-prefix;
          description "Address prefix.";
        }
        uses prefix-sid-sub-tlvs;
        uses sid-binding-sub-tlvs;
        uses ospf:unknown-tlvs;
      }
    }
  }

  grouping sr-algorithm-tlv {
    description "SR algorithm TLV grouping.";
    container sr-algorithm-tlv {
      description "All SR algorithm TLVs.";
      leaf-list sr-algorithm {
        type uint8;
        description
          "The algorithms that the router is currently using.";
      }
    }
  }

  grouping sid-range-tlvs {
    description "sid-range-tlvs grouping.";
    container sid-range-tlvs {
      description "List of SID range TLVs.";
      list sid-range-tlv {
        description "SID range TLV.";
        leaf range-size {
          type ospf:uint24;
          description "The SID range.";
        }
        uses sid-sub-tlv;
      }
    }
  }

  augment "/rt:routing-state/rt:routing-instance/"
        + "rt:routing-protocols/rt:routing-protocol/"
        + "ospf:ospf/ospf:instance/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque/"
        + "ospf:extended-prefix-tlvs/ospf:extended-prefix-tlv" {
    when "../../../../../../../../../../../../../../../../../"
       + "rt:type = 'ospf:ospfv2'" {
      description
        "This augment is only valid for OSPFv2.";
    }
    description
      "SR specific TLVs for OSPFv2 extended prefix TLV
       in type 9 opaque LSA.";
    uses prefix-sid-sub-tlvs;
    uses sid-binding-sub-tlvs;
  }

  augment "/rt:routing-state/rt:routing-instance/"
        + "rt:routing-protocols/rt:routing-protocol/"
        + "ospf:ospf/ospf:instance/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-prefix-tlvs/ospf:extended-prefix-tlv" {
    when "../../../../../../../../../../../../../../../"
       + "rt:type = 'ospf:ospfv2'" {
      description
        "This augment is only valid for OSPFv2.";
    }
    description
      "SR specific TLVs for OSPFv2 extended prefix TLV
       in type 10 opaque LSA.";
    uses prefix-sid-sub-tlvs;
    uses sid-binding-sub-tlvs;
  }

  augment "/rt:routing-state/rt:routing-instance/"
        + "rt:routing-protocols/rt:routing-protocol/"
        + "ospf:ospf/ospf:instance/ospf:database/"
        + "ospf:as-scope-lsa-type/ospf:as-scope-lsas/"
        + "ospf:as-scope-lsa/ospf:version/ospf:ospfv2/"
        + "ospf:ospfv2/ospf:body/ospf:opaque/"
        + "ospf:extended-prefix-tlvs/ospf:extended-prefix-tlv" {
    when "../../../../../../../../../../../../../"
       + "rt:type = 'ospf:ospfv2'" {
      description
        "This augment is only valid for OSPFv2.";
    }
    description
      "SR specific TLVs for OSPFv2 extended prefix TLV
       in type 11 opaque LSA.";
    uses prefix-sid-sub-tlvs;
    uses sid-binding-sub-tlvs;
  }

  augment "/rt:routing-state/rt:routing-instance/"
        + "rt:routing-protocols/rt:routing-protocol/"
        + "ospf:ospf/ospf:instance/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-tlvs/ospf:extended-link-tlv" {
    when "../../../../../../../../../../../../../../../"
       + "rt:type = 'ospf:ospfv2'" {
      description
        "This augment is only valid for OSPFv2.";
    }
    description
      "SR specific TLVs for OSPFv2 extended link TLV
       in type 10 opaque LSA.";

    container adj-sid-sub-tlvs {
      description "Adj-sid is optional sub-tlv.";
      list adj-sid-sub-tlv {
        description "List of adj-sid sub-tlv.";
        leaf flags {
          type bits {
            bit B {
              description
                "Backup flag.";
            }
            bit V {
              description
                "Value/Index flag.";
            }
            bit L {
              description
                "Local/Global flag.";
            }
            bit S {
              description
                "Set flag.";
            }
          }
          description "Flags.";
        }
        leaf mt-id {
          type uint8;
          description "Multi-topology ID.";
        }
        leaf weight {
          type uint8;
          description "Weight used for load-balancing.";
        }
        leaf sid {
          type uint32;
          description "sid index/label.";
        }
      }
    }

    container lan-adj-sid-sub-tlvs {
      description "Lan adj-sid is optional sub-tlv.";
      list lan-adj-sid-sub-tlv {
        description "List of lan-adj-sid sub-tlv.";
        leaf flags {
          type bits {
            bit B {
              description
                "Backup flag.";
            }
            bit V {
              description
                "Value/Index flag.";
            }
            bit L {
              description
                "Local/Global flag.";
            }
            bit S {
              description
                "Set flag.";
            }
          }
          description "Flags.";
        }
        leaf mt-id {
          type uint8;
          description "Multi-topology ID.";
        }
        leaf weight {
          type uint8;
          description "Weight used for load-balancing.";
        }
        leaf neighbor-router-id {
          type yang:dotted-quad;
          description "Neighbor router ID.";
        }
        leaf sid {
          type uint32;
          description "sid index/label.";
        }
      }
    }
  }

  augment "/rt:routing-state/rt:routing-instance/"
        + "rt:routing-protocols/rt:routing-protocol/"
        + "ospf:ospf/ospf:instance/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque" {
    when "../../../../../../../../../../../../../../../"
       + "rt:type = 'ospf:ospfv2'" {
      description
        "This augment is only valid for OSPFv2.";
    }

    description
      "SR specific TLVs for OSPFv2 type 9 opaque LSA.";

    uses extended-prefix-range-tlvs;
    uses sr-algorithm-tlv;
    uses sid-range-tlvs;
  }

  augment "/rt:routing-state/rt:routing-instance/"
        + "rt:routing-protocols/rt:routing-protocol/"
        + "ospf:ospf/ospf:instance/ospf:areas/"
        + "ospf:area/ospf:database/"
        + "ospf:area-scope-lsa-type/ospf:area-scope-lsas/"
        + "ospf:area-scope-lsa/ospf:version/ospf:ospfv2/"
        + "ospf:ospfv2/ospf:body/ospf:opaque" {
    when "../../../../../../../../../../../../../"
       + "rt:type = 'ospf:ospfv2'" {
      description
        "This augment is only valid for OSPFv2.";
    }

    description
      "SR specific TLVs for OSPFv2 type 10 opaque LSA.";

    uses extended-prefix-range-tlvs;
    uses sr-algorithm-tlv;
    uses sid-range-tlvs;
  }

  augment "/rt:routing-state/rt:routing-instance/"
        + "rt:routing-protocols/rt:routing-protocol/"
        + "ospf:ospf/ospf:instance/ospf:database/"
        + "ospf:as-scope-lsa-type/ospf:as-scope-lsas/"
        + "ospf:as-scope-lsa/ospf:version/ospf:ospfv2/"
        + "ospf:ospfv2/ospf:body/ospf:opaque" {
    when "../../../../../../../../../../../"
       + "rt:type = 'ospf:ospfv2'" {
      description
        "This augment is only valid for OSPFv2.";
    }
    description
      "SR specific TLVs for OSPFv2 type 11 opaque LSA.";

    uses extended-prefix-range-tlvs;
    uses sr-algorithm-tlv;
    uses sid-range-tlvs;
  }
}
