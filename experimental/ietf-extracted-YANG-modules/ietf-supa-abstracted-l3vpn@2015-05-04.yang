module ietf-supa-abstracted-l3vpn {
  namespace "urn:ietf:params:xml:ns:yang:ietf-supa-abstracted-
l3vpn";
  // replace with IANA namespace when assigned
  prefix abstracted-l3vpn;

  import ietf-inet-types {
    prefix inet;
  }
  import ietf-interfaces {
    prefix if;
  }

  organization "IETF";
  contact
    "Editor: Dacheng Zhang
     dacheng.zdc@alibaba-inc.com

     Adel Zaalouk
     adel.ietf@gmail.com

     Kostas Pentikousis
     k.pentikousis@eict.de

     Jan Lindblad
     janl@tail-f.com

     Maxim Klyus
     klyus@NetCracker.com
    ";

  description
    "This YANG module an abstracted L3VPN information
     model for DDC service to useL3VPN, based on which
     users can develop applications to configure L3VPN
     instances for DDC service.

     Terms and Acronyms
       L3VPN: Layer 3 Virtual Private Network
    ";

  revision 2015-05-04 {
    description "Initial revision.";
    reference "RFC4364, RFC7277";
  }

  container l3vpns {
    description "an abstracted L3VPN information
     model for DDC service to use L3VPN.";

    list l3vpn-instance {
      key name;
      description
        "Indicates the name of the VPN instance.";

      leaf name {
        type string;
        description "L3VPN instance name.";
      }

      leaf service-type {
        type enumeration {
          enum full-mesh {
            value 0;
            description "Full-mesh topology.";
          }
          enum hub-spoke {
            value 1;
            description "Hub-spoke topology.";
          }
        }
        default "full-mesh";
        description "Topology type.";
      }

      leaf address-family {
        type enumeration {
          enum ipv4uni {
            value 0;
            description "ipv4 unicast address family.";
          }
          enum ipv6uni {
            value 1;
            description "ipv6 unicast address family.";
          }
        }
        default "ipv4uni";
        description "Address family type: IPv4 or IPv6.";
      }

      leaf instance-oper-state {
        type enumeration {
          enum enabled {
            value 1;
            description "VPN Service is enabled";
          }
          enum disabled {
            value 2;
            description "VPN Service is disabled";
          }
        }
        description
          "This part indicates the operational state
          of VPN, enabled or disabled.
          User may use this value to inquire the status
          of this instance";
      }

      leaf instance-admin-state {
        type enumeration {
          enum Enabled {
            value 1;
            description "VPN Service Administratively Enabled";
          }
          enum Disabled {
            value 2;
            description "VPN Service Administratively Disabled";
          }
        }
        description
          "This part indicates the administrative state
          of VPN, e.g., enabled, disabled.
          User may use this value to manage the instance";
      }

      leaf life-cycle-state {
        type enumeration {
          enum planned {
            value 1;
            description "VPN Service Planned";
          }
          enum installed {
            value 2;
            description "VPN Service Installed";
          }
          enum removed {
            value 3;
            description "VPN Service Removed";
          }
        }
        description
          "This part indicates the life cycle state
          of VPN, e.g., installed, removed, planned.";
      }

      leaf instance-availability-status {
        type enumeration {
          enum degraded {
            value 1;
            description
              "VPN Service Degraded";
          }
          enum failed {
            value 2;
            description
             "VPN Service Failed";
          }
        }
        description
          "This part indicates the availability status
          of VPN, e.g., degraded, failed.";
      }

      leaf instance-cfg-revision {
        type string;
        description
          "Indicates current service configuration revision";
      }

      leaf instance-sla-policy {
        type string;
        description
          "Indicates SLA decision policy name";
      }

      leaf service-quality {
        type enumeration {
          enum gold {
            value 0;
            description
             "Best quality of service is guaranteed.";
          }
          enum silver {
            value 1;
            description
             "Better quality of service than bronze class
             is guaranteed.";
          }
          enum bronze {
            value 2;
            description
            "Average quality of service is guaranteed.";
          }
        }
        default "bronze";
        description "Quality of service.";
      }

      list access-interface {
        key name;
        description "Access interfaces.";

        leaf name {
          type if:interface-ref;
          description "Access interface name.";
        }

        leaf address {
          type inet:ip-prefix;
          mandatory true;
          description "Access interface address, IPv4 or IPv6.";
        }

        leaf role {
          when "../../service-type = 'full-mesh'" {
            description
              "The role is always center-if in a
        hub-spoke topology, in a full-mesh
        topology, the role needs to be
        specified as center-if or edge-if.";
          }
          type enumeration {
            enum edge-if {
              value 0;
              description "Edge interface";
            }
            enum center-if {
              value 1;
              description "Center interface";
            }
          }
          mandatory true;
          description
      "center-if is only available in hub-spoke
      mode; There are two scenarios: in full
      mesh mode, the role of all the access-interface
      is edge-if, while in hub-spoke mode, the role of
      the interface of hub node is ceter-if, the one
            of spoke node is edge-if";
        }
      }

      leaf user-name {
        type string;
        mandatory true;
        description "User name for this access interface";
      }

      leaf user-password {
        type string;
        mandatory true;
        description
      "User password for the access interface in
      encrypted format. User name and password are
      listed here because VPN need the
      authentication, one typical way is to use
          user name and password, so that in CE dynamic
      migration case, CEs are able to access with
      authentication regardless location.";
      }

      leaf physical-node-id {
        type string;
        mandatory true;
        description "This is the physical node ID
        of access PE";
      }

      leaf physical-access-interface {
        type if:interface-ref;
        mandatory true;
        description " This is the Physical access
        interface of access PE.";
      }

      container routing {
        description
          "Routing configuration between PE and CE.";

        leaf protocol {
          type enumeration {
            enum bgp {
              value 0;
              description "bgp routing between PE and CE";
            }
            enum ospf {
              value 1;
              description "ospf routing between PE and CE";
            }
            enum isis {
              value 2;
              description "isis routing between PE and CE";
            }
            enum rip {
              value 3;
              description "rip routing between PE and CE";
            }
            enum static {
              value 4;
              description "static routing between PE and CE";
            }
          }
          default "ospf";
          description "Routing protocol between PE and CE.";
        }

        container bgp-attribute {
          when "../protocol = 'bgp'" {
            description "BGP specific parameters.";
          }

          leaf remote-as-number {
            type inet:as-number;
            description "Remote BGP peer as-number.";
          }

          leaf remote-peer-address {
            type inet:ip-address;
            mandatory true;
            description "Remote BGP peer address.";
          }
          description "Detailed configuration for BGP.";
        }

        container igp-attribute {
          when "../protocol = 'ospf' or
                ../protocol = 'isis' or
                ../protocol = 'rip'  or
                ../protocol = 'static'" {
            description "IGP specific parameters.";
          }
          leaf protocol-id {
            type uint32;
            default 0;
            description "Valid only when protocol is IGP;
                         it can be AS number.";
          }
          description " This part defines the attribute of IGP.";
        }
      }
    }
  }
}
