module example-dhcpv6-class-selector {
  yang-version 1.1;
  namespace 
    "urn:ietf:params:xml:ns:yang:example-dhcpv6-class-selector";
  prefix "dhcpv6-class-selector";

  import ietf-inet-types {
    prefix inet;
  }

  import ietf-interfaces {
    prefix if;
  }

  import ietf-dhcpv6-common {
    prefix dhcpv6-common;
  }

  import ietf-dhcpv6-server {
    prefix dhcpv6-server;
  }

  organization "DHC WG";
  contact
    "yong@csnet1.cs.tsinghua.edu.cn
    lh.sunlinh@gmail.com
    ian.farrer@telekom.de
    sladjana.zechlin@telekom.de
    hezihao9512@gmail.com";

  description "This YANG module defines components for the definition
    and configuration of the client class selector function for a
    DHCPv6 server.  As this functionality varies greatly between
    different implementations, the module provided as an example
    only.";

  revision 2020-05-26 {
    description "Version update for draft -11 publication and
      to align revisions across the different modules.";
    reference "I-D: draft-ietf-dhc-dhcpv6-yang-11";
  }

  revision 2019-06-13 {
    description "";
    reference "I-D: draft-ietf-dhc-dhcpv6-yang";
  }

  /*
   * Groupings
   */

  grouping client-class-id {
    description "Definitions of client message classification for
      authorization and assignment purposes.";
    leaf client-class-name {
      type string;
      description "Unique Identifier for client class identification
        list entries.";
    }
    choice id-type {
      description "Definitions for different client identifier
        types.";
      mandatory true;
      case client-id-id {
        description "Client class selection based on a string literal
          client identifier.";
        leaf client-id {
          description "String literal client identifier.";
          mandatory true;
          type string;
        }
      }
      case received-interface-id {
        description "Client class selection based on the incoming
          interface of the DHCPv6 message.";
        leaf received-interface {
          description "Reference to the interface entry
            for the incoming DHCPv6 message.";
          type if:interface-ref;
        }
      }
      case packet-source-address-id {
        description "Client class selection based on the source
          address of the DHCPv6 message.";
        leaf packet-source-address {
          description "Source address of the DHCPv6 message.";
          mandatory true;
          type inet:ipv6-address;
        }
      }
      case packet-destination-address-id {
        description "Client class selection based on the destination
          address of the DHCPv6 message.";
        leaf packet-destination-address {
          description "Destination address of the DHCPv6 message.";
          mandatory true;
          type inet:ipv6-address;
        }
      }
      case relay-link-address-id {
        description "Client class selection based on the prefix
          of the link-address field in the relay agent message
          header.";
        leaf relay-link-address {
          description "Prefix of the link-address field in the relay
            agent message header.";
          mandatory true;
          type inet:ipv6-prefix;
        }
      }
      case relay-peer-address-id {
        description "Client class selection based on the value of the
          peer-address field in the relay agent message header.";
        leaf relay-peer-address {
          description "Prefix of the peer-address field
            in the relay agent message header.";
          mandatory true;
          type inet:ipv6-prefix;
        }
      }
      case relay-interface-id {
        description "Client class selection based on the incoming
          interface-id option.";
        leaf relay-interface {
          description "Reference to the interface entry
            for the incoming DHCPv6 message.";
          type string;
        }
      }
      case user-class-option-id {
        description "Client class selection based on the value of the
          OPTION_USER_CLASS(15) and its user-class-data field.";
        leaf user-class-data {
          description "Value of the enterprise-number field.";
          mandatory true;
          type string;
        }
      }
      case vendor-class-present-id {
        description "Client class selection based on the presence of
          OPTION_VENDOR_CLASS(16) in the received message.";
        leaf vendor-class-present {
          description "Presence of OPTION_VENDOR_CLASS(16)
            in the received message.";
          mandatory true;
          type boolean;
        }
      }
      case vendor-class-option-enterprise-number-id {
        description "Client class selection based on the value of the
          enterprise-number field in OPTION_VENDOR_CLASS(16).";
        leaf vendor-class-option-enterprise-number {
          description "Value of the enterprise-number field.";
          mandatory true;
          type uint32;
        }
      }
      case vendor-class-option-data-id {
        description "Client class selection based on the value
          of a data field within a vendor-class-data entry
          for a matching enterprise-number field
          in OPTION_VENDOR_CLASS(16).";
        container vendor-class-option-data {
          leaf vendor-class-option-enterprise-number {
            description "Value of the enterprise-number field
              for matching the data contents.";
            mandatory true;
            type uint32;
          }
          leaf vendor-class-data {
            description "Vendor class data to match.";
            mandatory true;
            type string;
          }
        }
      }
      case remote-id {
        description "Client class selection based on the value
          of Remote-ID .";
        container remote-id {
          leaf vendor-class-option-enterprise-number {
            description "Value of the enterprise-number field
              for matching the data contents.";
            mandatory true;
            type uint32;
          }
          leaf remote-id {
            description "Remote-ID data to match.";
            mandatory true;
            type string;
          }
        }
      }
      case client-duid-id {
        description "Client class selection based on the value
          of the received client DUID.";
        uses dhcpv6-common:duid;
      }
    }
  }

  /*
   * Augmentations
   */

  augment
        "/dhcpv6-server:dhcpv6-server/dhcpv6-server:class-selector" {
    container client-classes {
      list class {
        description "List of the client class identifiers applicable
          to clients served by this address pool";
        key client-class-name;
        uses dhcpv6-class-selector:client-class-id;
      }
    }
  }

  augment
      "/dhcpv6-server:dhcpv6-server/dhcpv6-server:network-ranges/
        dhcpv6-server:network-range" {
    leaf-list client-class {
      type leafref {
        path "/dhcpv6-server:dhcpv6-server/dhcpv6-server:class-select
          or/client-classes/class/client-class-name";
      }
    }
  }

  augment
      "/dhcpv6-server:dhcpv6-server/dhcpv6-server:network-ranges/
      dhcpv6-server:network-range/dhcpv6-server:address-pools/
      dhcpv6-server:address-pool" {
    leaf-list client-class {
      type leafref {
        path "/dhcpv6-server:dhcpv6-server/dhcpv6-server:
          class-selector/client-classes/class/client-class-name";
      }
    }
  }

  augment
      "/dhcpv6-server:dhcpv6-server/dhcpv6-server:network-ranges/
      dhcpv6-server:network-range/dhcpv6-server:prefix-pools/
      dhcpv6-server:prefix-pool" {
    leaf-list client-class {
      type leafref {
        path "/dhcpv6-server:dhcpv6-server/dhcpv6-server:
          class-selector/client-classes/class/client-class-name";
      }
    }
  }
}
