module ietf-rib-extension {
  namespace "urn:ietf:params:xml:ns:yang:ietf-rib-extension";

  prefix rib;

  import ietf-inet-types {
    prefix "inet";
  }

  import ietf-routing {
    prefix "rt";
  }

  import ietf-ipv4-unicast-routing {
    prefix "v4ur";
  }

  import ietf-ipv6-unicast-routing {
    prefix "v6ur";
  }

  organization
    "Cisco Systems
     170 West Tasman Drive
     San Jose, CA 95134-1706
     USA";
  contact
    "Acee Lindem - acee@cisco.com
     Yingzhen QU - yiqu@cisco.com";

  description
    "This YANG module extends the generic data model for
     RIB by augmenting the ietf-netmod-routing-cfg
     model. It is intended that the module will be extended
     by vendors to define vendor-specific RIB parameters.
    ";

  revision 2015-10-16 {
     description
      "Initial revision.";
    reference
      "RFC XXXX: A YANG Data Model for RIB Extensions.";
  }

  feature next-hop-dampen {
    description
      "RIB next-hop dampening.";
  }

  grouping next-hop {
    description
      "Next-hop grouping.";
    leaf interface {
      type leafref {
        path "/rt:routing-state/rt:routing-instance/rt:interfaces/"
           + "rt:interface";
      }
      description
        "Outgoing interface.";
    }
    leaf address {
      type inet:ip-address;
      description
        "Address of the next-hop.";
    }
  }

  grouping attributes {
    description
      "Common attributes applicable to all paths.";
    leaf metric {
      type uint32;
      description "route metric.";
    }
    leaf tag {
      type uint32;
      description "route tag.";
    }
  }

  grouping path-attribute {
    description
      "Path attribute grouping.";
    uses attributes;
    container repair-path {
      uses next-hop;
      uses attributes;
      description
        "The IP Fast ReRoute (IPFRR) repair path.";
    }
  }

  augment "/rt:routing/rt:routing-instance/rt:routing-protocols/"
        + "rt:routing-protocol/rt:static-routes/v4ur:ipv4/"
        + "v4ur:route/v4ur:next-hop/v4ur:next-hop-options"
  {
    description
      "Augment recursive static route configuration.";
      case multi-next-hop {
        description
          "Multiple next-hop options";
        list next-hop-entries {
          key "interface address";
          leaf interface {
            type string;
            description
              "Outgoing interface name.";
          }
          leaf address {
            type inet:ipv4-address;
            description
              "Address of the next-hop.";
          }
          leaf preference {
            type uint32;
            default "1";
            description "route preference.";
          }
          leaf tag {
            type uint32;
            default "0";
            description "route tag.";
          }
          description
            "List of multiple next hops.";
        }
     }
  }

  augment "/rt:routing/rt:routing-instance/rt:routing-protocols/"
        + "rt:routing-protocol/rt:static-routes/v6ur:ipv6/"
        + "v6ur:route/v6ur:next-hop/v6ur:next-hop-options"
  {
    description
      "Augment recursive static route configuration.";
      case multi-next-hop {
        description
          "Multiple next-hop options";
        list next-hop-entries {
          key "interface address";
          leaf interface {
            type string;
            description
              "Outgoing interface name.";
          }
          leaf address {
            type inet:ipv6-address;
            description
              "Address of the next-hop.";
          }
          leaf preference {
            type uint32;
            default "1";
            description "route preference.";
          }
          leaf tag {
            type uint32;
            default "0";
            description "tag for this path.";
          }
          description
            "List of multipath.";
        }
     }
  }

  augment "/rt:routing/rt:routing-instance/rt:ribs/rt:rib"
  {
    description
      "Augment configuration for RIB dampening enable/disable.";
    leaf next-hop-dampen-enable {
      if-feature next-hop-dampen;
      type boolean;
      default true;
      description "Enable rib next-hop dampening.";
    }
  }

  augment "/rt:routing-state/rt:routing-instance/rt:ribs/rt:rib"
  {
    description
      "Augment operation state for RIB dampening enable/disable.";
    leaf next-hop-dampen-enable {
      type boolean;
      description "Rib next-hop dampening state.";
    }
  }

  augment "/rt:routing-state/rt:routing-instance/rt:ribs/rt:rib/"
        + "rt:routes/rt:route"
  {
    description
      "Augment a route in RIB with tag.";
    uses attributes;
  }

  augment "/rt:routing-state/rt:routing-instance/rt:ribs/rt:rib/"
        + "rt:routes/rt:route/rt:next-hop/rt:next-hop-options/"
        + "rt:simple-next-hop"
  {
     description
       "Add more parameters to a path.";
     uses path-attribute;
  }

  augment "/rt:routing-state/rt:routing-instance/rt:ribs/rt:rib/"
        + "rt:routes/rt:route/rt:next-hop/rt:next-hop-options/"
        + "rt:special-next-hop"
  {
     description
       "Add more parameters to a path.";
     uses path-attribute;
  }

  augment "/rt:routing-state/rt:routing-instance/rt:ribs/rt:rib/"
        + "rt:routes/rt:route/rt:next-hop/rt:next-hop-options"
  {
     description
       "This case augments the 'next-hop-options' in the routing
        model.";
     case multi-paths {
       description
         "ecmp";
       list path-entries {
         uses next-hop;
         uses path-attribute;
         description
           "List of multipaths.";
       }
     }
   }
}
