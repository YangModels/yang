module ietf-te-wson-types {
     namespace "urn:ietf:params:xml:ns:yang:ietf-te-wson-types";
     prefix "te-wson-types";

     organization
         "IETF CCAMP Working Group";
     contact
         "WG Web: <http://tools.ietf.org/wg/ccamp/>
         WG List: <mailto:ccamp@ietf.org>

         Editor: Aihua Guo
                 <mailto:aihuaguo@huawei.com>

         Editor: Young Lee
                 <mailto:leeyoung@huawei.com>";

     description
         "This module defines WSON types.";

     revision "2017-10-09" {
         description
             "Revision 0.1";
         reference "TBD";
     }

     typedef operational-mode {
        type string;
        description
          "Vendor-specific mode that guarantees interoperability.
           It must be an string with the following format:
           B-DScW-ytz(v) where all these attributes are conformant
           to the ITU-T recomendation";
          reference "ITU-T G.698.2 (11/2009) Section 5.3";
     }
     identity wson-node-type {
         description
                 "WSON node type.";
         reference
                 "";
     }

     identity wson-node-foadm {
         base wson-node-type;
         description
                 "Fixed OADM node.";
     }

     identity wson-node-roadm {
         base wson-node-type;
         description
                 "ROADM or OXC node.";
     }

     identity wson-node-ila {
         base wson-node-type;
         description
                 "ILA (In-Line Amplifier) node.";
     }

    //ADDED
     typedef wavelength-range-type {
         type string {
             pattern "([1-9][0-9]{0,3}(-[1-9][0-9]{0,3})?" +
                     "(,[1-9][0-9]{0,3}(-[1-9][0-9]{0,3})?)*)";
         }
         description
             "A list of WDM channel numbers (starting at 1)
              in ascending order. For example: 1,12-20,40,50-80";
     }

    identity wavelength-assignment {
        description "Wavelength selection base";
    }
    identity unspecified-wavelength-assignment {
        base wavelength-assignment;
        description "No method specified";
    }

    identity first-fit-wavelength-asignment {
        base wavelength-assignment;
        description "All the available wavelengths are numbered,
            and this WA method chooses the available wavelength
            with the lowest index.";
    }

    identity random-wavelength-asignment {
        base wavelength-assignment;
        description "This WA method chooses an available
            wavelength randomly.";
    }

    identity least-loaded-wavelength-asignment {
        base wavelength-assignment;
        description "This WA method selects the wavelength that
            has the largest residual capacity on the most loaded
            link along the route (in muli-fiber networks).";
    }

 }
