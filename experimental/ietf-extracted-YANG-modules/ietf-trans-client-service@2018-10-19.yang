module ietf-trans-client-service {
  /* TODO: FIXME */
  //yang-version 1.1;

  namespace "urn:ietf:params:xml:ns:yang:ietf-trans-client-service";
  prefix "clntsvc";

  import ietf-te-types {
    prefix "te-types";
  }

  import ietf-l1-service-types {
    prefix "l1-svc-types";
  }

  organization
    "Internet Engineering Task Force (IETF) CCAMP WG";
  contact
    "

      ID-draft editor:
        Aihua Guo (aihuaguo@huawei.com);
        Haomian Zheng (zhenghaomian@huawei.com);
        Italo Busi (italo.busi@huawei.com);
        Yunbin Xu (xuyunbin@ritt.cn);
        Yang Zhao (zhaoyangyjy@chinamobile.com);
        Xufeng Liu (Xufeng_Liu@jabil.com);
        Giuseppe Fioccola (giuseppe.fioccola@telecomitalia.it);
    ";

  description
    "This module defines a YANG data model for describing
     simple transport client services.";

  revision 2018-10-19 {
    description
      "Initial version";
    reference
      "draft-zheng-ccamp-client-signal-yang";
  }

  /*
   * Groupings
   */

  grouping client-svc-access-parameters {
    description
      "Transport client services access parameters";

    leaf access-node-id {
      type te-types:te-node-id;
      description
        "The identifier of the access node in the underlying
         transport topology.";
    }
    leaf access-ltp-id {
      type te-types:te-tp-id;
      description
        "The TE link termination point identifier, used together with
         access-node-id to identify the access LTP.";
    }
    leaf client-signal {
      type identityref {
        base l1-svc-types:protocol-type;
      }
      description
        "Identifiies the client signal type associated with this port";
    }
  }

  grouping client-svc-tunnel-parameters {
    description
      "Transport client services tunnel parameters";

    leaf tunnel-name {
      type string;
      description
        "TE service tunnel instance name.";
    }
  }

  grouping  client-svc-instance_config {
    description
      "Configuraiton parameters for client services.";

    leaf client-svc-name {
      type string;
      description
        "Name of the p2p transport client service.";
    }
    leaf client-svc-descr {
      type string;
      description
        "Description of the transport client service.";
    }
    uses te-types:te-topology-identifier;
    container src-access-ports {
      description
        "Source access port of a client service.";
      uses client-svc-access-parameters;
    }
    container dst-access-ports {
      description
        "Destination access port of a client service.";
      uses client-svc-access-parameters;
    }
    list svc-tunnels {
      key tunnel-name;
      description
        "List of the TE Tunnels supporting the client service.";
      uses client-svc-tunnel-parameters;
    }
    leaf admin-status {
      type identityref {
        base te-types:tunnel-state-type;
      }
      default te-types:tunnel-state-up;
      description "Client service administrative state.";
    }
  }

  grouping  client-svc-instance_state {
        description
          "State parameters for client services.";
        leaf operational-state {
          type identityref {
                base te-types:tunnel-state-type;
          }
          config false;
          description "Client service operational state.";
        }
        leaf provisioning-state {
          type identityref {
                base te-types:lsp-state-type;
          }
          config false;
          description "Client service provisioning state.";
        }
  }

  /*
   * Data nodes
   */

  container client-svc {
    description
      "Transport client services.";

    list client-svc-instances {
      key client-svc-name;
      description
        "The list of p2p transport client service instances";

          uses client-svc-instance_config;
          uses client-svc-instance_state;
    }
  }
}
