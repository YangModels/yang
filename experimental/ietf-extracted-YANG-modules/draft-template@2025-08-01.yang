module draft-template {
  yang-version 1.1;
  namespace "urn:ietf:params:xml:ns:yang:draft-template";
  prefix dr-tmp;

  import ietf-inet-types {
    prefix inet;
    reference
      "RFC 6991: Common YANG Data Types";
  }

  organization
    "INSA Lyon";
  contact
    "Editor:   Vivekananda Boudia
     <mailto:vivekananda.boudia@insa-lyon.fr>";
  description
    "template yang model";

  revision 2025-08-01 {
    description
      "Initial revision";
    reference
      "";
  }

  identity template-type {
    description
      "base identity for template type";
  }

  identity CONFIG {
    base template-type;
    description
      "template used to retrieve configuration data";
  }

  identity STATE {
    base template-type;
    description
      "template used to retrieve operational state data";
  }

  identity METRIC {
    base template-type;
    description
      "template used to retrieve metrics";
  }

  identity label {
    description
      "base identity for label";
  }

  identity request-type {
    description
      "base identity for request type";
  }

  identity ALL_REQUESTS {
    base request-type;
    description
      "all requests";
  }

  container template {
    description
      "template container";
    list template {
      key "template-id";
      description
        "template list";
      leaf template-id {
        type inet:uri;
        description
          "uniquely identifies a template";
      }
      leaf description {
        type string;
        description
          "template description";
      }
      container template-type {
        description
          "template type;
           used for filtering template";
        leaf base {
          type identityref {
            base template-type;
          }
          description
            "template base type";
        }
        leaf is-historical {
          type boolean;
          description
            "check if template is used 
            to get historical data or not";
        }
        leaf-list label {
          type identityref {
            base label;
          }
          description
            "used to defined which data can 
            be retrieve with the template";
        }
      }
      list parameter {
        key "param-id";
        description
          "list of parameter used by request";
        leaf param-id {
          type inet:uri;
          description
            "uniquely identifies a parameter";
        }
        leaf description {
          type string;
          description
            "parameter description";
        }
      }
      list request {
        key "request-type";
        description
          "request list";
        leaf request-type {
          type identityref {
            base request-type;
          }
          description
            "request type";
        }
         leaf description {
          type string;
          description
            "request description";
        }
        container request-builder {
          description
            "request container that contains 
             everything needed to build the request;
             parameters must be enclosed in brackets.";
        }
      }
      anydata extra {
        description
          "use for augmentation";
      }
    }
  }

}
