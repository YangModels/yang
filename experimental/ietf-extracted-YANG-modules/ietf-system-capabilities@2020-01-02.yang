module ietf-system-capabilities {
  yang-version 1.1;
  namespace
    "urn:ietf:params:xml:ns:yang:ietf-system-capabilities";
  prefix sysc;

  import ietf-netconf-acm  {
    prefix nacm;
    description
       "The module ietf-netconf-acm is OPTIONAL to implement.";
  }

  import ietf-yang-library {
    prefix yanglib;
    description "The module ietf-yang-library is REQUIRED to
      be implemented. Revision 2019-01-04 or a
      revision derived from it is REQUIRED.";
  }

  organization
    "IETF NETCONF (Network Configuration) Working Group";
  contact
    "WG Web:   <https://datatracker.ietf.org/wg/netconf/>
     WG List:  <mailto:netconf@ietf.org>

     Editor:   Balazs Lengyel
               <mailto:balazs.lengyel@ericsson.com>";
  description
    "This module specifies a module intended to contain system
      capabilities. System capabilities may include capabilities of a
      NETCONF or RESTCONF server or a notification publisher.

     This module does not contain any specific capabilities it only
     provides a structure where containers containing the actual
     capabilities should be augmented in.

     Capability values can be specified on system level,
     datastore level or for specific data nodes (and their contained
     sub-tree) of a specific datastore.
     If a capability is specified on multiple levels, the
     specification on a more specific level overrides more
     generic capability specifications; thus
     - a system level specification is overridden by any
     other specification
     - a datastore level specification (with a node-selector '/') is
     overridden by a specification with a more specific node-selector.
     - a specification for a specific datastore and node-selector
     is overridden by a specification for the same datastore with
     a node-selector that describes more levels of containing lists
     and containers.
     It is not allowed to have multiple node selectors which
     - are defined for the same datastore AND
     - have the same number of containment levels AND
     - select an overlapping set of nodes.

     To find a capability value for a specific data node in a
     specific datastore the user SHALL
     1) consider the system level capabilities under the
     system-capabilities container if the
     capability value is specified.
     2) search for a datastore-capabilities list entry for
     the specific datastore.
     3) within that datastore entry search for a
     per-node-capabilities entry that specifies the specific
     capability and that has the node-selector selecting the
     specific data node and that specifies the most levels of
     containing containers and lists.
     4) If no entries are found in the previous steps the
     publisher is not capable of providing a value because
     it is unknown, the capability is changing for some reason,
     there is no specified limit etc. In this case the
     system's behavior is unspecified.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX
     (https://www.rfc-editor.org/info/rfcXXXX); see the RFC itself
     for full legal notices.";

  revision 2020-01-02 {
    description
      "Initial version";
    reference
      "RFC XXX: YANG-Push Notification Capabilities";
  }

  container system-capabilities {
    config false;
    description "System capabilities.
      Capability values specified here at the system level
      are valid for all datastores and
      are used when the capability is not specified on the
      datastore level or for specific data nodes.";

    // augmentation point for system level capabilities

    list datastore-capabilities {
      key datastore;

      description "Capabilities values per datastore.
        For non-NMDA servers/publishers config=false data is
        considered as if it was part of the running datastore.";

      leaf datastore {
        type leafref {
          path /yanglib:yang-library/yanglib:datastore/yanglib:name;
        }
        description "The datastore for which capabilities are defined.
          Only individual datastores can be specified
          e.g., ds:conventional is not allowed.";
      }

      list per-node-capabilities {
        key "node-selector";
        description
          "Each list entry specifies capabilities
           for the selected data nodes. The same capabilities apply for
           the data nodes in the subtree below them unless another list
           entry with a more specific node selector specifying the same
           capability is present.";

        leaf node-selector {
          type nacm:node-instance-identifier;
          description
            "Selects the data nodes for which capabilities are
             specified. The special value '/' denotes all data nodes
             in the datastore.
             The system SHOULD order list entries according to
             the tree structure of the data models to make
             reading/parsing the data more simple.";
        }

        // augmentation point for datastore or data node level
        // capabilities
      }
    }
  }
}
