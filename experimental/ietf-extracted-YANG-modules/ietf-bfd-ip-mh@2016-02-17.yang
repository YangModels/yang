module ietf-bfd-ip-mh {
namespace "urn:ietf:params:xml:ns:yang:ietf-bfd-ip-mh";
// replace with IANA namespace when assigned
prefix "bfd-ip-mh";

import ietf-bfd {
  prefix "bfd";
}

import ietf-inet-types {
  prefix "inet";
}

import ietf-routing {
  prefix "rt";
}

organization "IETF BFD Working Group";

contact
  "WG Web:   <http://tools.ietf.org/wg/bfd>
   WG List:  <rtg-bfd@ietf.org>
   WG Chair: Jeff Haas
   WG Chair: Reshad Rahman
   Editor:   Lianshu Zheng and Reshad Rahman";

description
  "This module contains the YANG definition for BFD IP multi-hop
   asper RFC5883.";

revision 2016-02-17 {
  description "Initial revision.";
  reference "RFC XXXX: A YANG data model for BFD IP multi-hop";
}

augment "/bfd:bfd" {
  description "BFD augmentation for IP multi-hop";
  container ip-mh {
    description "BFD IP multi-hop top level container";

    container config {
      description "BFD IP multi-hop configuration container";
    }
    container oper {
      config "false";
      description "BFD IP multi-hop operational container";
      uses bfd:bfd-session-statistics;
    }
  }
}

augment "/rt:routing/rt:routing-instance/rt:routing-protocols/"
  + "rt:routing-protocol/bfd:bfd" {
  when "rt:type = 'bfd:bfd'" {
    description
      "This augment is only valid for a protocol instance
      of BFD.";
  }
  description "BFD augmentation for IP multi-hop.";

  container ip-mh {
    description "BFD IP multi-hop container";
    container config {
      description "BFD configuration";
      container session-cfg {
        description "BFD IP multi-hop session configuration";

        list sessions {
          key "source-addr dest-addr";
          description "List of IP multi-hop sessions";

          leaf source-addr {
            type inet:ip-address;
            description
              "Local IP address";
          }
          leaf dest-addr {
            type inet:ip-address;
            description
              "IP address of the peer";
          }
          uses bfd:bfd-grouping-common-cfg-parms;

          leaf tx-ttl {
            type bfd:ttl;
            default 255;
            description "TTL of outgoing BFD control packets";
          }
          leaf rx-ttl {
            type bfd:ttl;
            mandatory true;
            description
              "Minimum allowed TTL value for incoming BFD control
               packets";
          }
        }
      }
    }

    container oper {
      config "false";
      description "BFD operational container";

      container bfd-session-statistics {
        description "BFD session counters";
        uses bfd:bfd-session-statistics;
      }

      list session-group {
        key "source-addr dest-addr";
        description
          "BFD IP multi-hop group of sessions. A group of " +
          "sessions is between 1 source and 1 destination, " +
          "each session has a different field in UDP/IP hdr for " +
          "ECMP.";
        leaf source-addr {
          type inet:ip-address;
          description "BFD source address";
        }
        leaf dest-addr {
          type inet:ip-address;
          description "BFD peer address";
        }
        list sessions {
          key "local-discriminator";
          description
            "The BFD sessions between a source and a. " +
            "destination. Local discriminator is unique for " +
            "each session in the group.";
          leaf ttl {
            type bfd:ttl;
            description "TTL of outgoing packets";
          }
          uses bfd:bfd-all-session;
        }
      }
    }
  }
}

notification bfd-multihop-notification {
  description
    "Notification for BFD multi-hop session state change. An " +
    "implementation may rate-limit notifications, e.g. when a" +
    "session is continuously changing state.";

  uses bfd:bfd-notification-parms;

  leaf routing-instance {
    type rt:routing-instance-ref;
    description "Routing instance";
  }
}

}
