module ietf-multicast-model {

 yang-version 1.1;

 namespace "urn:ietf:params:xml:ns:yang:ietf-multicast-model";
 prefix multicast-model;

 import ietf-inet-types {
     prefix "inet";
     reference "RFC6991";
 }

 import ietf-routing-types {
     prefix rt-types;
     reference "RFC8294";
 }

 organization " IETF MBONED( MBONE Deployment ) Working Group";
 contact
     "WG List:  <mailto:mboned@ietf.org>

      Editor:   Zheng Zhang
                <mailto:zzhang_ietf@hotmail.com>
      Editor:   Cui Wang
                <mailto:lindawangjoy@gmail.com>
      Editor:   Ying Cheng
                <mailto:chengying10@chinaunicom.cn>
      Editor:   Xufeng Liu
                <mailto:xufeng.liu.ietf@gmail.com>
      Editor:   Mahesh Sivakumar
                <mailto:sivakumar.mahesh@gmail.com>
     ";
 description
      "The module defines the YANG definitions for multicast service
       management.

       Copyright (c) 2018 IETF Trust and the persons
       identified as authors of the code.  All rights reserved.

       Redistribution and use in source and binary forms, with or
       without modification, is permitted pursuant to, and subject
       to the license terms contained in, the Simplified BSD License
       set forth in Section 4.c of the IETF Trust's Legal Provisions
       Relating to IETF Documents
       (http://trustee.ietf.org/license-info).

       This version of this YANG module has relationship with
       overall multicast technologies, such as PIM(RFC7761),
       BIER(RFC8279), MVPN(RFC6513), and so on; see the RFC itself
       for full legal notices.";

 revision 2018-07-30 {
     description
      "Initial revision.";
    reference
      "RFC XXXX: A YANG Data Model for multicast YANG.
       RFC 7761: Protocol Independent Multicast - Sparse Mode (PIM-SM):
                 Protocol Specification (Revised).
       RFC 8279: Multicast Using Bit Index Explicit Replication (BIER);
       RFC 6513: Multicast in MPLS/BGP IP VPNs";
 }

/*key*/

    typedef ip-multicast-source-address {
        type union {
            type rt-types:ipv4-multicast-source-address;
            type rt-types:ipv6-multicast-source-address;
        }
        description
            "This type represents a version-neutral IP multicast
             source address.  The format of the textual
             representation implies the IP version.";
        reference
            "RFC8294: Common YANG Data Types for the Routing Area.";
    }

    typedef virtual-type {
        type enumeration {
            enum "vxlan" {
                description "The vxlan type. See more detail in RFC7348.";
            }
            enum "virtual subnet" {
                description "The nvgre type. See more detail in RFC7637.";
            }
            enum "vni" {
                description
                  "The geneve type. See more detail in [ietf-nvo3-geneve].";
            }
        }
        description "The collection of virtual network type.";
    }

    grouping general-multicast-key {
        description "The general multicast keys. They are used to
                     distinguish different multicast service.";
        leaf vpn-rd {
            type rt-types:route-distinguisher;
            description "A Route Distinguisher used to distinguish
                         routes from different MVPNs (RFC 6513).";
            reference
                "RFC8294: Common YANG Data Types for the Routing Area.";
        }
        leaf source-address {
            type ip-multicast-source-address;
            description
                "The IPv4/IPv6 source address of multicast flow. The
                 value set to zero means that the receiver interests
                 in all source that relevant to one given group.";
        }
        leaf group-address {
            type rt-types:ip-multicast-group-address;
            description
                "The IPv4/IPv6 group address of multicast flow. This
                 type represents a version-neutral IP multicast group
                 address. The format of the textual representation
                 implies the IP version.";
            reference
                "RFC8294: Common YANG Data Types for the Routing Area.";
        }
        leaf vni-type {
            type virtual-type;
            description
                "The type of virtual network identifier. Includes the
                 Vxlan, NVGRE and Geneve. This value and vni-value is
                 used to indicate a specific virtual multicast service.";
        }
        leaf vni-value {
            type uint32;
            description
                "The value of Vxlan network identifier, virtual subnet
                 ID or virtual net identifier. This value and vni-type
                 is used to indicate a specific virtual multicast service.";
        }
    }

/*overlay*/

    grouping overlay-technology {
        leaf overlay-tech-type {
            type enumeration {
                enum mld {
                    description "MLD technology is used for multicast
                        overlay. See more detail in [draft-ietf-bier-mld]";
                }
                enum mvpn {
                    description "MVPN technology is used for multicast
                        overlay. See more detail in RFC6513.";
                }
                enum bgp {
                    description "BGP technology is used for multicast
                                 overlay. See more detail in RFC7716.";
                }
                enum mld-snooping {
                    description "MLD snooping technology is used for
                                 multicast overlay. See more detail in RFC4541.";
                }
            }
            description "The possible overlay technologies for multicast service.";
        }
        description "The possible overlay technologies for multicast service.";
    }

    grouping multicast-overlay {
        description
          "The multicast overlay information, includes ingress node
           and egress nodes' information.";

        container ingress-egress {
            description "The ingress and egress nodes address collection.";
            leaf ingress-node {
                type inet:ip-address;
                description
                  "The ip address of ingress node for one or more
                   multicast flow. Or the ingress node of MVPN and
                   BIER. In MVPN, this is the address of ingress
                   PE; in BIER, this is the BFR-prefix of ingress
                   nodes.";
            }

            list egress-nodes {
                key "egress-node";
                description
                  "The egress multicast nodes of multicast flow. Or
                   the egress node of MVPN and BIER. In MVPN, this
                   is the address of egress PE; in BIER, this is the
                   BFR-prefix of ingress nodes.";

                leaf egress-node {
                    type inet:ip-address;
                    description
                      "The ip-address of egress multicast nodes.
                       See more details in RFC6513.";
                }
            }
        }

        container bier-ids {
            description
              "The BFR-ids of ingress and egress BIER nodes for
               one or more multicast flows.";
            leaf sub-domain {
                type uint16;
                description
                  "The sub-domain that this multicast flow belongs
                   to. See more details in RFC8279.";
            }
            leaf ingress-node {
                type uint16;
                description
                  "The ingress node of multicast flow. This is the
                   BFR-id of ingress nodes. See more details in RFC8279.";
            }
            list egress-nodes {
                key "egress-node";
                description
                  "This ID information of one adjacency. See more
                   details in RFC8279.";

                leaf egress-node {
                    type uint16;
                    description
                      "The BFR-ids of egress multicast BIER nodes.
                       See more details in RFC8279.";
                }
            }
        }

        uses overlay-technology;
    }

/*transport*/

    grouping transport-pim {
        description
          "The requirement information of pim transportion.
           PIM protocol is defined in RFC7761.";
        leaf graceful-restart {
            type boolean;
            description
              "If the graceful restart function should be supported.";
        }
        leaf bfd {
            type boolean;
            description "If the bfd function should be supported.";
        }
    }

    grouping multicast-transport {
        description "The transport information of multicast service.";
        container bier {
            description
              "The transport technology is BIER. The BIER technology
               is introduced in RFC8279. The parameter is consistent
               with the definition in [ietf-bier-bier-yang].";
            leaf sub-domain {
                type uint16;
                description
                  "The subdomain id that the multicast flow belongs
                   to. See more details in RFC8279.";
            }
            choice encap-type {
                case mpls {
                    description "The BIER forwarding depends on mpls.
                                 See more details in RFC8296.";
                }
                case eth {
                    description "The BIER forwarding depends on ethernet.
                                 See more details in RFC8296.";
                }
                case ipv6 {
                    description "The BIER forwarding depends on IPv6.";
                }
                description "The encapsulation type in BIER.";
            }
            leaf bitstringlength {
                type uint16;
                description "The bitstringlength used by BIER forwarding.
                             See more details in RFC8279.";
            }
            leaf set-identifier {
                type uint16;
                description "The set identifier used by the multicast flow.
                             See more details in RFC8279.";
            }
            leaf ecmp {
                type boolean;
                description
                  "The capability of ECMP. If this value is set to true,
                   ecmp mechanism should be enabled. See more details in RFC8279.";
            }
            leaf frr {
                type boolean;
                description
                  "The capability of fast re-route. If this value is
                   set to true, fast re-route mechanism should be
                   enabled. See more details in RFC8279.";
            }
        }
        container bier-te {
            description
              "The transport technology is BIER-TE. BIER-TE technology
               is introduced in [ietf-bier-te-arch].";
            leaf sub-domain {
                type uint16;
                description
                  "The subdomain id that the multicast flow belongs to.
                   See more details in [ietf-bier-te-arch].";
            }
            choice encap-type {
                case mpls {
                    description
                      "The BIER-TE forwarding depends on mpls. See more
                       details in [ietf-bier-te-arch].";
                }
                case non-mpls {
                    description
                      "The BIER-TE forwarding depends on non-mpls. See
                       more details in [ietf-bier-te-arch].";
                }
                description "The encapsulation type in BIER-TE.";
            }
            leaf bitstringlength {
                type uint16;
                description "The bitstringlength used by BIER-TE forwarding.
                             See more details in [ietf-bier-te-arch].";
            }
            leaf set-identifier {
                type uint16;
                description
                  "The set identifier used by the multicast flow,
                   especially in BIER TE. See more details in
                   [ietf-bier-te-arch].";
            }
            leaf ecmp {
                type boolean;
                description
                  "The capability of ECMP. If this value is set to
                   true, ecmp mechanism should be enabled.
                   See more details in [ietf-bier-te-arch].";
            }
            leaf frr {
                type boolean;
                description
                  "The capability of fast re-route. If this value
                   is set to true, fast re-route mechanism should
                   be enabled. See more details in
                   [ietf-eckert-bier-te-frr].";
            }
        }
        container cisco-mode {
            description
              "The transport technology is cisco-mode. The Cisco MDT
               multicast mechanism is defined in RFC6037.";
            leaf p-group {
                type rt-types:ip-multicast-group-address;
                description
                  "The address of p-group. It is used to encapsulate
                   and forward flow according to multicast tree from
                   ingress node to egress nodes.";
            }
            uses transport-pim;
        }
        container mpls {
            description
              "The transport technology is mpls. MVPN overlay can use
               mpls tunnel technologies to build transport layer. The
               usage is introduced in RFC6513.";
            choice mpls-tunnel-type {
                case mldp {
                    description "The mldp tunnel. The protocol detail
                                 is defined in RFC6388.";
                    leaf mldp-tunnel-id {
                        type uint32;
                        description "The tunnel id that correspond this
                                     flow. The detail is defined in RFC6388.";
                    }
                    leaf mldp-frr {
                        type boolean;
                        description
                          "If the fast re-route function should be
                           supported. The detail is defined in RFC6388.";
                    }
                    leaf mldp-backup-tunnel {
                        type boolean;
                        description
                          "If the backup tunnel function should be
                           supported. The detail is defined in RFC6388.";
                    }
                }
                case p2mp-te {
                    description
                      "The p2mp te tunnel. The protocol detail is
                       defined in RFC4875.";
                    leaf te-tunnel-id {
                        type uint32;
                        description
                          "The tunnel id that correspond this flow.
                           The detail is defined in RFC4875.";
                    }
                    leaf te-frr {
                        type boolean;
                        description
                          "If the fast re-route function should be
                           supported. The detail is defined in RFC4875.";
                    }
                    leaf te-backup-tunnel {
                        type boolean;
                        description
                          "If the backup tunnel function should be
                           supported. The detail is defined in RFC4875.";
                    }
                }
                description "The collection types of mpls tunnels";
            }
        }
        container pim {
            uses transport-pim;
            description
              "The transport technology is PIM. PIM [RFC7761] is used
               commonly in traditional network.";
        }
    }

/*underlay*/

    grouping multicast-underlay {
        description
          "The underlay information relevant multicast service.
           Underlay protocols are used to build transport layer.
           It is unnecessary in traditional network that use
           PIM [RFC7761] to build multicast tree. Diversity underlay
           protocols can be choosed to build BIER transport layer.";
        leaf underlay-requirement {
            type boolean;
            description "If the underlay technology is required.";
        }
        container bgp {
            description
              "The underlay technology is BGP. BGP protocol RFC4271
               should be triggered to run if BGP is used as
               underlay protocol.";
        }
        container ospf {
            description
              "The underlay technology is OSPF. OSPF protocol RFC2328
               should be triggered to run if OSPF is used as underlay
               protocol.";
            leaf topology-id {
                type uint8;
                description
                  "The topology id of ospf instance. The topology id
                   can be assigned In some situations. More details
                   is defined in RFC2328.";
            }
        }
        container isis {
            description
              "The underlay technology is ISIS. ISIS protocol should
               be triggered to run if ISIS is used as underlay protocol.
               Details is defined in RFC1195.";
            leaf topology-id {
                type uint16;
                description
                  "The topology id of isis instance. The topology id
                   can be assigned In some situations.";
            }
        }
        container babel {
            description
              "The underlay technology is Babel. Babel protocol should
               be triggered to run if Babel is used as underlay protocol.";
        }
    }

    container multicast-model {
        description
          "The model of multicast YANG data. Include keys, overlay,
           transport and underlay.";

        list multicast-keys{
            key "vpn-rd source-address group-address vni-type vni-value";
            uses general-multicast-key;

            container multicast-overlay {
                description
                  "The overlay information of multicast service.
                   Overlay technology is used to exchange multicast
                   flows information. Overlay technology may not be
                   used in SDN controlled completely situation, but
                   it can be used in partial SDN controlled situation
                   or non-SDN controlled situation. Different overlay
                   technology can be choosed according to different
                   deploy consideration.";
                uses multicast-overlay;
            }
            container multicast-transport {
                description
                  "The transportion of multicast service. Transport
                   protocol is responsible for delivering multicast
                   flows from ingress nodes to egress nodes with or
                   without specific encapsulation. Different transport
                   technology can be choosed according to different
                   deploy consideration. Once a transport technology
                   is choosed, associated protocol should be triggered
                   to run.";
                uses multicast-transport;
            }
            container multicast-underlay {
                description
                  "The underlay of multicast service. Underlay protocol
                   is used to build transport layer. Underlay protocol
                   need not be assigned in ordinary network since
                   existed underlay protocol fits well, but it can be
                   assigned in particular networks for better
                   controll. Once a underlay technology is choosed,
                   associated protocol should be triggered to run.";
                uses multicast-underlay;
            }
            description
              "The model of multicast YANG data. Include keys,
               overlay, transport and underlay.";
        }
    }

/*Notifications*/

    notification head-end-event {
        leaf event-type {
            type enumeration {
                enum down {
                    description
                      "There is something wrong with head end node,
                       and head end node can't work properlay.";
                }
                enum module-loaded {
                    description
                      "Some new modules that can be used by multicast
                       flows finish loading.";
                }
                enum module-unloaded {
                    description
                      "Some new modules that can be used by multicast
                       flows have been unloaded.";
                }
            }
            description "Event type.";
        }
        container multicast-key {
            uses general-multicast-key;
            description
              "The associated multicast keys that are influenced by
               head end node failer.";
        }
        uses overlay-technology;

        leaf transport-tech {
            type enumeration {
                enum bier {
                    description
                      "BIER(RFC8279) technology can be used to
                       forward multicast flows.";
                }
                enum bier-te {
                    description
                      "BIER-TE(draft-ietf-bier-te-arch) technology
                       can be used to forward multicast flows.";
                }
                enum cisco-mode {
                    description
                      "Cisco mode(RFC6037) technology can be used
                       to forward multicast flows.";
                }
                enum mldp {
                    description
                      "MLDP(RFC6388) technology can be used to
                       forward multicast flows.";
                }
                enum p2mp-te {
                    description
                      "P2MP TE(RFC4875) technology can be used to
                       forward multicast flows.";
                }
                enum pim {
                    description
                      "PIM(RFC7761) technology can be used to
                       forward multicast flows.";
                }
            }
            description "The modules can be used to forward multicast flows.";
        }
        leaf underlay-tech {
            type enumeration {
                enum bgp {
                    description "BGP protocol can be used to build
                                 multicast transport layer.";
                }
                enum ospf {
                    description "OSPF protocol can be used to build
                                 multicast transport layer.";
                }
                enum isis {
                    description "ISIS protocol can be used to build
                                 multicast transport layer.";
                }
                enum babel {
                    description "Babel protocol can be used to build
                                 multicast transport layer.";
                }
            }
            description "The modules can be used to build multicast
                         transport layer.";
        }
        description
          "Notification events for the head end nodes. Like head
           node failer, overlay/ transport/ underlay module
           loading/ unloading. And the potential failer about some
           multicast flows and associated
           overlay/ transport/ underlay technologies.";
    }
}
