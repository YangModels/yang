module ietf-l3-te-topology-state {
  yang-version 1.1;
  namespace "urn:ietf:params:xml:ns:yang:ietf-l3-te-topology-state";
  prefix "l3tet-s";

  import ietf-l3-te-topology {
    prefix "l3tet";
  }
  import ietf-network-state {
    prefix "nw-s";
  }
  import ietf-network-topology-state {
    prefix "nt-s";
  }
  import ietf-l3-unicast-topology-state {
    prefix "l3t-s";
  }

  organization "TBD";
  contact "TBD";
  description "L3 TE Topology model";

  revision 2018-02-28 {

    description "Initial revision";
    reference "TBD";
  }

  augment "/nw-s:networks/nw-s:network/nw-s:network-types/"
    + "l3t-s:l3-unicast-topology" {
    description
      "Defines the L3 TE topology type.";
    uses l3tet:l3-te-topology-type;
  }

  augment "/nw-s:networks/nw-s:network/"
    + "l3t-s:l3-topology-attributes" {
    when "../nw-s:network-types/l3t-s:l3-unicast-topology/"
      + "l3tet-s:l3-te" {
      description "Augment only for L3 TE topology";
    }
    description "Augment topology configuration";
    uses l3tet:l3-te-topology-attributes;
  }

  augment "/nw-s:networks/nw-s:network/nw-s:node/"
    + "l3t-s:l3-node-attributes" {
    when "../../nw-s:network-types/l3t-s:l3-unicast-topology/"
      + "l3tet-s:l3-te" {
      description "Augment only for L3 TE topology";
    }
    description "Augment node configuration";
    uses l3tet:l3-te-node-attributes;
  }

  augment "/nw-s:networks/nw-s:network/nw-s:node/"
    + "nt-s:termination-point/"
    + "l3t-s:l3-termination-point-attributes" {
    when "../../../nw-s:network-types/l3t-s:l3-unicast-topology/"
      + "l3tet-s:l3-te" {
      description "Augment only for L3 TE topology";
    }
    description "Augment termination point configuration";
    uses l3tet:l3-te-tp-attributes;
  }

  augment "/nw-s:networks/nw-s:network/nt-s:link/"
    + "l3t-s:l3-link-attributes" {
    when "../../nw-s:network-types/l3t-s:l3-unicast-topology/"
      + "l3tet-s:l3-te" {
      description "Augment only for L3 TE topology";
    }
    description "Augment link configuration";
    uses l3tet:l3-te-link-attributes;
  }
}
