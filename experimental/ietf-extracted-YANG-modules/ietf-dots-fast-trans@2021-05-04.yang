module ietf-dots-fast-trans {
  yang-version 1.1;
  namespace "urn:ietf:params:xml:ns:yang:ietf-dots-fast-trans";
  prefix dots-fast;

  import ietf-dots-signal-channel {
    prefix dots-signal;
    reference
      "RFC YYYY: Distributed Denial-of-Service Open Threat
                 Signaling (DOTS) Signal Channel Specification";
  }
  import ietf-yang-structure-ext {
    prefix sx;
    reference
      "RFC 8791: YANG Data Structure Extensions";
  }

  organization
    "IETF DDoS Open Threat Signaling (DOTS) Working Group";
  contact
    "WG Web:   <https://datatracker.ietf.org/wg/dots/>
     WG List:  <mailto:dots@ietf.org>

     Author:  Mohamed Boucadair
              <mailto:mohamed.boucadair@orange.com>;

     Author:  Jon Shallow
              <mailto:ietf-supjps@jpshallow.com>";
  description
    "This module contains YANG definitions for the configuration
     of parameters that can be negotiated between a DOTS client
     and a DOTS server for faster block transmission.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2021-05-04 {
    description
      "Initial revision.";
    reference
      "RFC XXXX: Distributed Denial-of-Service Open Threat
                 Signaling (DOTS) Configuration Attributes
                 for Faster Block Transmission";
  }

  grouping fast-transmission-attributes {
    description
      "A set of DOTS signal channel session configuration
       that are negotiated between DOTS agents when
       making use of Q-Block1 and Q-Block2 Options.";
    container max-payloads {
      description
        "Indicates the maximum number of payloads that
         can be transmitted at any one time.";
      choice direction {
        description
          "Indicates the communication direction in which the
           data nodes can be included.";
        case server-to-client-only {
          description
            "These data nodes appear only in a mitigation message
             sent from the server to the client.";
          leaf max-value {
            type uint16;
            description
              "Maximum acceptable max-payloads value.";
          }
          leaf min-value {
            type uint16;
            description
              "Minimum acceptable max-payloads value.";
          }
        }
      }
      leaf current-value {
        type uint16;
        default "10";
        description
          "Current max-payloads value.";
      }
    }
    container non-max-retransmit {
      description
        "Indicates the the maximum number of times a
         request for the retransmission of missings payloads
         can occur without a response from the remote peer.";
      leaf max-value {
        type uint16;
        config false;
        description
          "Maximum acceptable non-max-retransmit value.";
      }
      leaf min-value {
        type uint16;
        config false;
        description
          "Minimum acceptable non-max-retransmit value.";
      }
      leaf current-value {
        type uint16;
        default "3";
        description
          "Current non-max-retransmit value.";
      }
    }
    container non-timeout {
      description
        "Indicates the maximum period of delay between
         sending sets of MAX_PAYLOADS payloads for the same
         body. By default, this parameter has the same value
         as ACK_TIMEOUT.";
      choice direction {
        description
          "Indicates the communication direction in which the
           data nodes can be included.";
        case server-to-client-only {
          description
            "These data nodes appear only in a mitigation message
             sent from the server to the client.";
          leaf max-value-decimal {
            type decimal64 {
              fraction-digits 2;
            }
            units "seconds";
            description
              "Maximum ack-timeout value.";
          }
          leaf min-value-decimal {
            type decimal64 {
              fraction-digits 2;
            }
            units "seconds";
            description
              "Minimum ack-timeout value.";
          }
        }
      }
      leaf current-value-decimal {
        type decimal64 {
          fraction-digits 2;
        }
        units "seconds";
        default "2";
        description
          "Current ack-timeout value.";
      }
    }
    container non-probing-wait {
      description
        "Is used to limit the potential wait needed calculated
         when using probing-rate.";
      choice direction {
        description
          "Indicates the communication direction in which the
           data nodes can be included.";
        case server-to-client-only {
          description
            "These data nodes appear only in a mitigation message
             sent from the server to the client.";
          leaf max-value-decimal {
            type decimal64 {
              fraction-digits 2;
            }
            units "seconds";
            description
              "Maximum non-probing-wait value.";
          }
          leaf min-value-decimal {
            type decimal64 {
              fraction-digits 2;
            }
            units "seconds";
            description
              "Minimum non-probing-wait value.";
          }
        }
      }
      leaf current-value-decimal {
        type decimal64 {
          fraction-digits 2;
        }
        units "seconds";
        default "247";
        description
          "Current non-probing-wait value.";
      }
    }
    container non-partial-wait {
      description
        "Is used for expiring partially received bodies.";
      choice direction {
        description
          "Indicates the communication direction in which the
           data nodes can be included.";
        case server-to-client-only {
          description
            "These data nodes appear only in a mitigation message
             sent from the server to the client.";
          leaf max-value-decimal {
            type decimal64 {
              fraction-digits 2;
            }
            units "seconds";
            description
              "Maximum non-partial-wait value.";
          }
          leaf min-value-decimal {
            type decimal64 {
              fraction-digits 2;
            }
            units "seconds";
            description
              "Minimum non-partial-wait value.";
          }
        }
      }
      leaf current-value-decimal {
        type decimal64 {
          fraction-digits 2;
        }
        units "seconds";
        default "247";
        description
          "Current non-partial-wait value.";
      }
    }
  }

  sx:augment-structure "/dots-signal:dots-signal"
                     + "/dots-signal:message-type"
                     + "/dots-signal:signal-config"
                     + "/dots-signal:mitigating-config" {
    description
      "Indicates DOTS configuration parameters to use for
       faster transmission when a mitigation is active.";
    uses fast-transmission-attributes;
  }
  sx:augment-structure "/dots-signal:dots-signal"
                     + "/dots-signal:message-type"
                     + "/dots-signal:signal-config"
                     + "/dots-signal:idle-config" {
    description
      "Indicates DOTS configuration parameters to use for
       faster transmission when no mitigation is active.";
    uses fast-transmission-attributes;
  }
}
