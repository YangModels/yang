module ietf-lmo-assets-inventory {
  yang-version 1.1;
  namespace "urn:ietf:params:xml:ns:yang:ietf-lmo-assets-inventory";
  prefix lmo-asset;
  import ietf-yang-types {
    prefix yang;
  }
  import ietf-lmo-common {
    prefix lmocom;
  }
  import ietf-geo-location {
    prefix geo ;
    revision-date 2019-02-17 ;
  }
  import ietf-inet-types {
    prefix inet;
  }

  organization
    "IETF OPSA (Operations and Management Area) Working Group";
  contact
    "WG Web:   <https://datatracker.ietf.org/wg/opsawg/>
     WG List:  <mailto:opsawg@ietf.org>
     Editor:  Marisol Palmero
              <mailto:mpalmero@cisco.com>
     Editor:  Josh Suhr
              <mailto:josuhr@cisco.com>
     Editor:  Sudhendu Kumar
              <mailto:skumar23@ncsu.edu>";
  description
    "This YANG module includes the concept asset aggregation
     and platform dependency of an asset.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  revision 2021-10-25 {
    description
      "Initial revision for Aggregated Assets Inventory as part of
       the LMO YANG Model";
    reference
      "RFC XXXX: LMO YANG Model";
  }
  container capture-info {
    config false;
    description
      "Capture information for this data";
    leaf collected-on {
      type yang:date-and-time;
      description
        "Time at which this data was collected";
    }
    leaf collected-from {
      type string;
      description
        "Identifier for original source of this data";
    }
  }
  container assets {
    config false;
    description
      "Assets container includes attributes that add the aggregated
       view";
    list asset {
      key "id";
      description
        "Asset ID";
      leaf id {
        type lmocom:asset-id;
        description
          "Unique identifier for the hardware or software instance.
           It could be same as the Serial Number.";
      }
      leaf vendor {
        type lmocom:vendor-id;
        description
          "Vendor or Manufacturer name or identifier; e.g. Cisco";
      }
      leaf pid {
        type string;
        description
          "Part or Product Identifier";
      }
      leaf serial-number {
        type string;
        description
          "Serial number";
      }
      leaf vid {
        type string;
        description
          "Hardware Version ID";
      }
      leaf mac-address {
        type yang:mac-address;
        description
          "The mac-address type represents an IEEE 802 MAC address.
       The canonical representation uses lowercase characters.";
      }
      leaf-list ip-address {
        type inet:ip-address;
        description
          "IP address, representing the management IP of the asset.
        It can refer to ipv4 and/or ipv6 address.";
      }
      leaf entity-name {
        type string;
        description
          "Hardware type, e.g., chassis, slot, or power-supply";
      }
      leaf product-description {
        type string;
        description
          "Standard description of the assset; e.g., '1-port Gigabit
           Ethernet'";
      }
      leaf udi {
        type string;
        description
          "Identify uniquely an asset = vendor-id + pid + id";
      }
      leaf transparency-info {
        type inet:uri;
        description
         "Link to software bill of material and security advisory
          information, see draft-ietf-opsawg-sbom-access";
      }
      leaf type {
        type identityref {
          base lmocom:asset-type;
        }
        description
          "Asset type; e.g. hardware, software, sw-cloud, ...
           It can be extended";
      }
      leaf subtype {
        type identityref {
          base lmocom:asset-subtype;
        }
        description
          "Subtype of hardware or software; e.g. router, switch,
           wireless, controller, ...";
      }
      leaf role {
        type identityref {
          base lmocom:role;
        }
        description
          "What the role of a given device/component is in the
          network. This attribute normally will be configured on the
          specific component during setup";
      }
      leaf aggregation {
        type boolean;
        must "../number-of-instances = 1 or . = 'true'";
        default false;
        description
          "Asset aggregation; e.g., false (default) or true";
      }
      leaf number-of-instances {
        type uint32;
        description
          "Number of instances or endpoints covered by the aggregated
           asset. If different from 1, it should enforce that
           aggregation attribute is set to true";
      }
      leaf platform-dependency-os {
        type identityref {
           base lmocom:platform-dependency-os;
        }
        description
          "Operating system for the asset to be deployed.";
      }
      container install-location {
        uses geo:geo-location;
        description
          "Physical installed location of the product. Location is
           provided based on what customer/user configures";
      }
      leaf deployment-mode {
        type identityref {
          base lmocom:deployment-mode;
        }
        description
          "Deployment mode for the asset, if applicable; e.g.,
           HA cluster, virtual appliance, etc.";
      }
      leaf activation-date {
        type yang:date-and-time;
        description
          "Date of asset activation or initial contact";
      }
      leaf software-version {
        type string;
        description
          "Software version running on the hardware device or
           software component";
      }
      container hotfixes {
        config false;
        description "list of hotfixes";
        list hostfix {
        description
          "List of hotfixes that have been installed";
          leaf version {
            type identityref {
              base lmocom:version;
            }
            description
              "It includes the first hotfix installed";
          }
          leaf order {
            type uint8;
            description
              "It refers to the order of how the hotfixes have been
               installed, range 0..100";
          }
        }
      }
      leaf software-type {
        type string;
        description
          "Software type or Operating System";
      }
      leaf sign-of-life-timestamp {
        type yang:date-and-time;
        description
          "Date of last contact";
      }
      leaf tags {
        type string;
        description
          "Comma-separated descriptive tags for this asset";
      }
    }
  }
  container subassets {
    config false;
    description
      "Subassets container, includes assets under parent assets";
    list subasset {
      key "id";
      description
        "Subasset ID";
      leaf id {
        type leafref {
          path "/assets/asset/id";
        }
        description
          "Reference to Asset-ID";
      }
    }
  }
}
