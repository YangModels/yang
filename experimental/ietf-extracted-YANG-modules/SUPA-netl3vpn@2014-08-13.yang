module SUPA-netl3vpn {
    namespace "";
    prefix "nc";
    organization "";
    description "";
    revision "2014-08-13";

    list netl3vpnInstance {
        key "instanceName";
        max-elements "unbounded";
        min-elements "0";
        description ".";

        leaf instanceName {
            description "L3VPN instance name.";
            config "true";
            type string {
                length "1..64";
                pattern "([^?]*)";
            }
        }

        leaf servicType {
            description "Topology type.";
            config "true";
            default "full-mesh";
            type enumeration {
                enum full-mesh {
                    value "0";
                    description "full-mesh";
                }
                enum hub-spoke {
                    value "1";
                    description "hub-spoke";
                }
            }
        }

        leaf afType {
            description " Address family type: IPv4 or IPv6.";
            config "true";
            default "ipv4uni";
            type enumeration {
                enum ipv4uni {
                    value "0";
                    description "ipv4uni";
                }
                enum ipv6uni {
                    value "1";
                    description "ipv6uni";
                }
            }
        }

        list acIf {
            key "acIfId";
            max-elements "unbounded";
            min-elements "0";
            description ".";

            leaf acIfId {
                description " Access interface ID.";
                config "true";
                type string {
                    length "1..64";
                    pattern "([^?]*)";
                }
            }

            leaf acIfAddr {
                description " Access interface address, IPv4 or
IPv6.";
                config "true";
                type string {
                    pattern "([^?]*)";
                }
            }

            leaf acIfMask {
                description " IP address mask length.";
                config "true";
                type uint8 {
                range "0..128";
                }
            }

            leaf role {
                description " center-if is only available in hub-
spoke mode; center-if is the interface in hub node.";
                config "true";
                type enumeration {
                    enum edge-if {
                        value "0";
                        description "edge-if:";
                        }
                    enum center-if {
                        value "1";
                        description "center:";
                    }
                }
            }

            leaf userName {
                description " User name for this access
interface.";
                config "true";
                type string {
                    length "1..64";
                    pattern "([^?]*)";
                }
            }

            leaf userPassword {
                description " User password for the access
interface.";
                config "true";
                type string {
                    length "1..64";
                    pattern "([^?]*)";
                }
            }

            leaf phyNodeId {
                description " Physical node ID.";
                config "true";
                type string {
                    length "1..64";
                    pattern "([^?]*)";
                }
            }

            leaf phyAcIfId {
                description " Physical access interface.";
                config "true";
                type string {
                    length "1..64";
                    pattern "([^?]*)";
                }
            }

            container protocol {
                description ".";

                leaf protocolType {
                    description " Protocol type.";
                    config "true";
                    default "ospf";
                    type enumeration {
                        enum bgp {
                            value "0";
                            description "bgp";
                        }
                        enum ospf {
                            value "1";
                            description "ospf";
                        }
                        enum isis {
                            value "2";
                            description "isis";
                        }
                    }
                }

                container igpAttr {
                    description ".";
                    leaf protocolId {
                        description " Valid only when protocol is
IGP; it can be AS number.";
                        config "true";
                        default "0";
                        type uint32 {
                        }
                    }
                }

                container bgpAttr {
                    description ".";

                    leaf remoteAsNumber {
                        description " Valid only when protocol is
BGP.";
                        config "true";
                        default "0";
                        type string {
                            length "1..11";
                        }
                    }

                    leaf remotePeerAddr {
                        description " Valid only when protocol is
BGP.";
                        config "true";
                        type string {
                        }
                    }
                }
            }
        }
    }
}
