module ietf-pcp-proxy {
  yang-version 1.1;

  namespace "urn:ietf:params:xml:ns:yang:ietf-pcp-proxy";
  prefix pcp-proxy;

  import ietf-inet-types { prefix inet; }
  import ietf-pcp { prefix pcp; }
  import ietf-pcp-client { prefix pcp-client; }

  organization "xxxx Working Group";
  contact
     "Mohamed Boucadair <mohamed.boucadair@orange.com>
      Christian Jacquenet <christian.jacquenet@orange.com>";

  description
       "This module contains a collection of YANG definitions for
        PCP Proxy implementations.

        Copyright (c) 2017 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

  revision 2017-10-17 {
    description "Align with NMDA";
    reference "-05";
  }

  revision 2015-08-05 {
      description "Changes xxxx.";
       reference "xxxx";
   }

augment "/pcp-client:pcp-client/pcp-client:instances/pcp-client:instance/pcp-client:option-configuration" {
  description
    "Augment the PCP client module with proxy
     specific parameters: instruct the behavior
     with regards to unknown options.";

  leaf relay-mandatory-unknown-option {
    type boolean;

    description
      "The proxy can be instructed to relay or
       to reject mandatory unknown options.";
  }

  leaf relay-optionnal-unknown-option {
    type boolean;

    description
      "The proxy can be instructed to relay or
       to reject optional unknown options.";
  }
}

augment "/pcp-client:pcp-client/pcp-client:instances/pcp-client:instance" {
  description
    "Instruct the proxy to terminate recusion.";

  leaf terminate-proxy-recursion {
    type boolean;

    description
      "The proxy can be instructed to terminate
       proxy recursion.";
  }
}

augment "/pcp-client:pcp-client/pcp-client:instances/pcp-client:instance/pcp-client:mapping-table/pcp-client:mapping-entry" {
  description
    "Augment the local mapping table with locally
     assigned parameters.";

  leaf local-assigned-ip-address {
    type inet:ipv6-prefix;
    description
      "If the local PCP-controlled function
       alters the source IP address, this
       information must be stored.";
  }

  container local-assigned-port {
     description
        "If the local PCP-controlled function
         alters the source port, this
         information must be stored.";

     uses pcp:port-number;
  }
 }
}
