module ietf-netconf-error-parameters {

   namespace "urn:ietf:params:xml:ns:yang:ietf-netconf-error-parameters";

   prefix ncep;

   import yuma-netconf { prefix nc; }

   organization
    "IETF NETCONF (Network Configuration Protocol) Working Group";

   contact
    "WG Web:   <http://tools.ietf.org/wg/netconf/>

     WG List:  <netconf@ietf.org>

     WG Chair: Bert Wijnen
               <bertietf@bwijnen.net>

     WG Chair: Mehmet Ersue
               <mehmet.ersue@nsn.com>

     Editor: Andy Bierman
             <andy.bierman@brocade.com>

     Editor: Balazs Lengyel
             <balazs.lengyel@ericsson.com>";

   description
    "This module defines an extension to the NETCONF protocol
     that allows the NETCONF server to return error parameters in
     the rpc-error which are refered in the error-message.

     Copyright (c) 2013 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: remove this note
     // Note: extracted from draft-ysc-netconf-rpc-error-extension-00.txt

     // RFC Ed.: update the date below with the date of RFC publication
     // and remove this note.

   revision 2013-07-11 {
     description
       "Initial version.";
     reference
       "RFC XXXX: NETCONF rpc-error extension";
   }

   grouping ErrorParameters {
     description
       "Contains the <error-parameters> for the <rpc-error> extension.";

     container error-parameters {
       description
         "The container of all error parameters in the <rpc-error>";
       reference
         "RFC XXXX; Section 4.5";

       leaf-list error-parameter {
         type string;
         description
           "error-parameter element";
         reference
           "RFC XXXX; Section 4.5";
       }
     }
   }

   // extending the rpc-error
   augment /nc:rpc-reply/nc:rpc-error {
       description
         "Adds the <error-parameters> parameter to the <rpc-error>.";
       reference
         "RFC XXXX; Section 4.5";

       uses ErrorParameters;
   }
}
