module ietf-transport-service {
        yang-version 1;
        namespace "urn:ietf:params:xml:ns:yang:ietf-transport-service";
        prefix transservice;

        import ietf-inet-types {
                prefix inet;
        }

        import ietf-yang-types {
          prefix ytypes;
        }

        import ietf-te-types {
                prefix "tet";
        }

        organization "Internet Engineering Task Force";
        contact
                "Editor: Xian ZHANG (zhang.xian@huawei.com)";
        description
                "this module describes a service module that is an essential
                API for a client to ask for a provider network for a path
                without the need to care about underlying technologies.
                Capability to specify constraints/policies are provided as
                optional features.";

        revision 2016-10-31 {
                description
                        "Initial revision.";
                        reference "to add the draft name";
        }

        grouping endpoints-grouping{
                description "end point grouping";
                leaf type {
                        type enumeration {
                                enum root {
                                        description "root";
                                }
                                enum leaf {
                                        description "leaf";
                                }
                                enum unknown {
                                        description "unknown";
                                }
                        }
                default root;

                description
                        "This attribute indicates whether a endpoint of the
                        service is acting as a root or leaf, and takes on
                        the value either root, leaf or unkown. If the service
                        type is Point-to-Point or Multipoint-to-Multipoint,
                        then the type is equal to root. If the service type
                        is Point-to-Multipoint, then the type can be either
                        root or leaf.";
                }

                leaf node-id {
                        type union {
                                type inet:ip-address; //IPv4 or IPv6
                                type uint32;
                        }
                        description
                                "the node address of a service .";
                }

                leaf tp-id {
                        type uint32;
                        description
                                "the termination point of a service.";
                }

                leaf endpoint-name {
                        type string;
                        description
                                "the name of this service endpoint";
                }
        }

        identity service-type {
                description
                        "base identity from which the specific service
                        type can be derived.";
        }

        identity service-P2P {
                base service-type;
                description
                        "a point-to-point service type";
        }

        identity service-P2MP {
                base service-type;
                description
                        "a point to multi-point type";
        }

        identity service-MP2MP {
                base service-type;
                description
                        "a multi-point to multi-point type";
        }

//note: service type such as EPL, EVPL, EPLAN
//      EVPLAN, E-Tree can be added when augmenting
//      this model.

        identity service-prot-type {
                description
                        "base identity from which the specific
                         protection type can be derived.";
        }

        identity service-prot-unprotected {
                base service-prot-type;
                description
                        "service protection type: unprotected";
        }

        identity service-prot-1plusR {
                base service-prot-type;
                description
                        "service protection type: dynamic reroute";
                reference
                        "draft-ietf-teas-gmpls-resource-sharing-proc-04";
        }

        identity service-prot-1plus1 {
                base service-prot-type;
                description
                        "service protection type: static 1+1";
        }

        identity service-prot-1plus1plusR {
                base service-prot-type;
                description
                        "service protection type: 1+1+R";
                reference
                        "draft-ietf-teas-gmpls-resource-sharing-proc-04";
        }

        identity objective-type{
                description
                        "base identity from which the specific obective
                        funciton can be derived.";
        }
        identity objective-mindelay{
                base objective-type;
                description
                        "objective: minimized delay";
        }
        identity objective-mincost {
                base objective-type;
                description
                        "objective: minimized cost";
        }

        identity objective-mindistance {
                base objective-type;
                description
                        "objective: minimized distance";
        }

        grouping service-config-grouping {
                description "service-config-groupoing";

                leaf service-name{
                        type string;
                        description "the name for a service";
                }

                leaf service-id {
                        type uint32;
                        description
                                "an unique identificaiton of a service.";
                }

                list service-endpoints{
                        key "node-id tp-id";
                        description
                                "this provides the service endpoints and it can be used
                                to support different types of services (including P2P,
                                MP2MP, P2MP)";

                        uses endpoints-grouping;
                }

                leaf service-type {
                        type identityref {
                                base service-type;
                        }
                        mandatory true;
                        description
                                "the type of a service request";
                }

                container supporting-tunnel {
                        leaf tunnel-name{
                                type string;
                                description "the name of a tunnel (unique)";
                        }

                        description
                                "the tunnels that can be used to support the service";
                }

                leaf bandwidth {
                        type decimal64 {
                                fraction-digits 2;
                        }
                        description "the bandwidth requested by a service.";
                }

                leaf protection-type{
                        type identityref {
                                base service-prot-type;
                        }
                        description
                        "the type of protection expected for this
                        service";
                }
        }

        grouping constraints-grouping {
                leaf delay-limit {
                        type uint32;
                        description
                        "Delay variation in micro-seconds.";
                }

                leaf delayvariation-limit {
                        type uint32;
                        description
                        "Delay variation.";
                }

                leaf packetloss-limit {
                        type decimal64 {
                                fraction-digits 6;
                                range "0 .. 50.331642";
                        }
                        description
                        "Delay variation in %.";
                }
                leaf objective {
                        type identityref
                        {
                                base objective-type;
                        }
                        description
                                "objective function imposed for path computation
                                from this service.";
                }
                description "constraints gropuing";
        }

        container transport_service {
                description
                        "serves as a top-level container for a list of services";

                list service {
                        key "service-name";
                        description
                                "an unique identifier of a service";

                        leaf service-name {
                                type leafref {
                                        path "../config/service-name";
                                }
                                description "a unique service identifier.";
                        }
                        container config{
                                description "service config container";

                                uses service-config-grouping;

                                container constraints{
                                        uses constraints-grouping;
                                        description
                                                "specify the constraints imposed by a
                                                service";
                                }
                        }

                        container state
                        {
                                config false;
                                description "operational state of a service";

                                uses service-config-grouping;

                                leaf creation-time {
                                        type ytypes:date-and-time;
                                        description
                                                "the time when service is created";
                                }

                                container constraints{
                                        uses constraints-grouping;
                                        description
                                                "specify the constraints imposed by a
                                                service";
                                }

                                container performance-info{
                                        description "service state-performance info";
                                        leaf delay{
                                                type uint32;
                                                description "the latency of this service";
                                        }

                                        leaf delay-variation {
                                                type uint32;
                                                description "the service delay varation";
                                        }
                                        leaf packet-loss {
                                                type decimal64 {
                                                        fraction-digits 6;
                                                        range "0 .. 50.331642";
                                                }
                                                description "packet loss";
                                        }
                                }
                                leaf oper-status {
                                        type tet:te-oper-status;
                                        mandatory true;
                                        description
                                                "the operational status of this service";
                                }
                        }//end of state of a service
                }//end of service list (including config and state)
        }//service top container
}
