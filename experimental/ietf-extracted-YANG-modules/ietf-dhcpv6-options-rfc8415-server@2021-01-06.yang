module ietf-dhcpv6-options-rfc8415-server {
  yang-version 1.1;
  namespace "urn:ietf:params:xml:ns:yang:" +
    "ietf-dhcpv6-options-rfc8415-server";
  prefix "rfc8415-srv";

  import ietf-inet-types {
    prefix inet;
    reference
      "RFC 6991: Common YANG Data Types";
  }

  import ietf-dhcpv6-common {
    prefix dhcpv6-common;
    reference
      "To be updated on publication";
  }

  import ietf-dhcpv6-server {
    prefix dhcpv6-server;
    reference
      "To be updated on publication";
  }

  organization "DHC WG";
  contact
    "cuiyong@tsinghua.edu.cn
    wangh13@mails.tsinghua.edu.cn
    lh.sunlinh@gmail.com
    ian.farrer@telekom.de
    sladjana.zechlin@telekom.de
    hezihao9512@gmail.com";

  description "This YANG module contains DHCPv6 options defined
    in RFC8415 that can be used by DHCPv6 clients.

    Copyright (c) 2021 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX
    (https://www.rfc-editor.org/info/rfcXXXX); see the RFC itself
    for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2021-01-06 {
    description "Version update for draft -16 publication.";
    reference "I-D: draft-ietf-dhc-dhcpv6-yang-16";
  }

  revision 2020-12-22 {
    description "Version update for draft -13 publication.";
    reference "I-D: draft-ietf-dhc-dhcpv6-yang-15";
  }

  revision 2020-12-10 {
    description "Version update for draft -13 publication.";
    reference "I-D: draft-ietf-dhc-dhcpv6-yang-13";
  }

  revision 2020-12-01 {
    description "Version update for draft -12 publication.";
    reference "I-D: draft-ietf-dhc-dhcpv6-yang-12";
  }

  revision 2020-11-19 {
    description "Separated into a client specific set of options.";
    reference "I-D: draft-ietf-dhc-dhcpv6-yang-12";
  }

  revision 2020-05-26 {
    description "Version update for draft -11 publication and
      to align revisions across the different modules.";
    reference "I-D: draft-ietf-dhc-dhcpv6-yang-11";
  }

  revision 2019-06-07 {
    description "Major reworking to only contain RFC8415 options.
      if-feature for each option removed. Removed groupings
        of features by device or combination of devices. Added ";
    reference "I-D: draft-ietf-dhc-dhcpv6-yang";
  }

  revision 2018-09-04 {
    description "";
    reference "I-D: draft-ietf-dhc-dhcpv6-yang";
  }

  revision 2018-03-04 {
    description "Resolved most issues on the DHC official
      github";
    reference "I-D: draft-ietf-dhc-dhcpv6-yang";
  }

  revision 2017-12-22 {
    description "Resolve most issues on Ian's github.";
    reference "I-D: draft-ietf-dhc-dhcpv6-yang";
  }

  revision 2017-11-24 {
    description "First version of the separated DHCPv6 options
      YANG model.";
    reference "I-D:draft-ietf-dhc-dhcpv6-yang";
  }

  /*
   * Groupings
   */

  grouping preference-option-group {
    description "OPTION_PREFERENCE (7) Preference Option.";
    reference "RFC8415: Dynamic Host Configuration Protocol for
      IPv6 (DHCPv6)";
   container preference-option {
     description "OPTION_PREFERENCE (7) Preference Option
       container.";
     leaf pref-value {
        type uint8;
        description "The preference value for the server in this
          message. A 1-octet unsigned integer.";
      }
    }
  }

  grouping auth-option-group {
    description "OPTION_AUTH (11) Authentication Option.";
    reference "RFC8415: Dynamic Host Configuration Protocol
      for IPv6 (DHCPv6)";
    container auth-option {
     description "OPTION_AUTH (11) Authentication Option container.";
     leaf protocol {
        type uint8;
        description "The authentication protocol used in this
          Authentication option.";
      }
      leaf algorithm {
        type uint8;
        description "The algorithm used in the authentication
          protocol.";
      }
      leaf rdm {
        type uint8;
        description "The replay detection method used
          in this Authentication option.";
      }
      leaf replay-detection {
        type uint64;
        description "The replay detection information for the RDM.";
      }
      leaf auth-information {
        type string;
        description "The authentication information, as specified
          by the protocol and algorithm used in this Authentication
          option.";
      }
    }
  }

  grouping server-unicast-option-group {
    description "OPTION_UNICAST (12) Server Unicast Option.";
    reference "RFC8415: Dynamic Host Configuration Protocol for
      IPv6 (DHCPv6)";
    container server-unicast-option {
      description "OPTION_UNICAST (12) Server Unicast Option
        container.";
      leaf server-address {
        type inet:ipv6-address;
        description "The 128-bit address to which the client
          should send messages delivered using unicast.";
      }
    }
  }

  grouping status-code-option-group {
    description "OPTION_STATUS_CODE (13) Status Code Option.";
    reference "RFC8415: Dynamic Host Configuration Protocol
      for IPv6 (DHCPv6)";
    container status-code-option {
      description "OPTION_STATUS_CODE (13) Status Code Option
        container.";
      leaf status-code {
        type uint16;
        description "The numeric code for the status encoded
          in this option. See the Status Codes registry at
          <https://www.iana.org/assignments/dhcpv6-parameters>
          for the current list of status codes.";
      }
      leaf status-message {
        type string;
        description "A UTF-8 encoded text string suitable for
          display to an end user. MUST NOT be null-terminated.";
      }
    }
  }

  grouping rapid-commit-option-group {
    description "OPTION_RAPID_COMMIT (14) Rapid Commit Option.";
    reference "RFC8415: Dynamic Host Configuration Protocol for
      IPv6 (DHCPv6)";
   container rapid-commit-option {
     presence "Enable sending of this option";
     description "OPTION_RAPID_COMMIT (14) Rapid Commit Option
       container.";
    }
  }

  grouping vendor-specific-information-option-group {
    description "OPTION_VENDOR_OPTS (17) Vendor-specific
      Information Option.";
    reference "RFC8415: Dynamic Host Configuration Protocol
      for IPv6 (DHCPv6)";
    container vendor-specific-information-option {
      description "OPTION_VENDOR_OPTS (17) Vendor-specific
        Information Option container.";
      list vendor-specific-information-option-instances {
        key enterprise-number;
        description "The vendor specific information option allows
          for multiple instances in a single message. Each list entry
          defines the contents of an instance of the option.";
        leaf enterprise-number {
          type uint32;
          description "The vendor's registered Enterprise Number,
            as maintained by IANA.";
        }
        list vendor-option-data {
          key sub-option-code;
          description "Vendor options, interpreted by vendor-specific
            client/server functions.";
          leaf sub-option-code {
            type uint16;
            description "The code for the sub-option.";
          }
          leaf sub-option-data {
            type string;
            description "The data area for the sub-option.";
          }
        }
      }
    }
  }

  grouping reconfigure-message-option-group {
    description "OPTION_RECONF_MSG (19) Reconfigure Message
      Option.";
    reference "RFC8415: Dynamic Host Configuration Protocol for
      IPv6 (DHCPv6)";
    container reconfigure-message-option {
      description "OPTION_RECONF_MSG (19) Reconfigure Message
        Option.";
      leaf msg-type {
        type uint8;
        description "5 for Renew message, 6 for Rebind message,
          11 for Information-request message.";
      }
    }
  }

  grouping reconfigure-accept-option-group {
    description "OPTION_RECONF_ACCEPT (20)  Reconfigure Accept
      Option.
      A client uses the Reconfigure Accept option to announce to
      the server whether the client is willing to accept Reconfigure
      messages, and a server uses this option to tell the client
      whether or not to accept Reconfigure messages.  In the absence
      of this option, the default behavior is that the client is
      unwilling to accept Reconfigure messages.  The presence node
      is used to enable the option.";
    reference "RFC8415: Dynamic Host Configuration Protocol
      for IPv6 (DHCPv6)";
    container reconfigure-accept-option {
      presence "Enable sending of this option";
      description "OPTION_RECONF_ACCEPT (20)  Reconfigure Accept
        Option container.";
    }
  }
  grouping info-refresh-time-option-group {
    description "OPTION_INFORMATION_REFRESH_TIME (32)
      Information Refresh Time option.";
    reference "RFC8415: Dynamic Host Configuration Protocol for
      IPv6 (DHCPv6)";
    container info-refresh-time-option {
      description "OPTION_INFORMATION_REFRESH_TIME (32)
        Information Refresh Time option container.";
      leaf info-refresh-time {
        type dhcpv6-common:timer-seconds32;
        description "Time duration relative to the current time,
          expressed in units of seconds.";
      }
    }
  }

  grouping sol-max-rt-option-group {
    description "OPTION_SOL_MAX_RT (82) sol max rt option.";
    reference "RFC8415: Dynamic Host Configuration Protocol for
      IPv6 (DHCPv6)";
   container sol-max-rt-option {
      description "OPTION_SOL_MAX_RT (82) sol max rt option
        container.";
      leaf sol-max-rt-value {
        type dhcpv6-common:timer-seconds32;
        description "sol max rt value";
      }
    }
  }

  grouping inf-max-rt-option-group {
    description "OPTION_INF_MAX_RT (83) inf max rt option.";
    reference "RFC8415: Dynamic Host Configuration Protocol for
      IPv6 (DHCPv6)";
    container inf-max-rt-option {
      description "OPTION_INF_MAX_RT (83) inf max rt option
        container.";
      leaf inf-max-rt-value {
        type dhcpv6-common:timer-seconds32;
        description "inf max rt value";
      }
    }
  }

  /*
   * Augmentations
   */

  augment "/dhcpv6-server:dhcpv6-server/dhcpv6-server:option-sets/" +
    "dhcpv6-server:option-set" {
    when "../../../dhcpv6-server:dhcpv6-node-type=" +
      "'dhcpv6-server:server'";
    description "Augment the option definition groupings to the
      relay module.";
    uses preference-option-group;
    uses auth-option-group;
    uses server-unicast-option-group;
    uses status-code-option-group;
    uses rapid-commit-option-group;
    uses vendor-specific-information-option-group;
    uses reconfigure-message-option-group;
    uses reconfigure-accept-option-group;
    uses info-refresh-time-option-group;
    uses sol-max-rt-option-group;
    uses inf-max-rt-option-group;
  }
}
