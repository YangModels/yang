module ietf-actn-vn {

    namespace "urn:ietf:params:xml:ns:yang:ietf-actn-vn";

    prefix "vn";

    /* Import TE generic types */
    import ietf-te-types {
        prefix "te-types";
    }
    organization
        "IETF Traffic Engineering Architecture and Signaling (TEAS)
        Working Group";

    contact
        "Editor: Young Lee <leeyoung@huawei.com>";

    description
        "This module contains a YANG module for the ACTN VN. It
        describes a VN operation module that takes place in the
        context of the CNC-MDSC Interface (CMI) of the ACTN
        architecture where the CNC is the actor of a VN creation
        /modification /deletion.";

    revision 2016-07-05 {
        description
            "initial version.";
        reference
            "TBD";
    }

    /*
     * Groupings
     */

    grouping access-point{
        description
            "AP related information";
        leaf access-point-id {
            type uint32;
            description
                "unique identifier for the referred
                access point";
        }
        leaf access-point-name {
            type string;
            description
                "ap name";
        }
        leaf max-bandwidth {
            type decimal64 {
                fraction-digits 2;
                range "0..max";
            }
            description
                "max bandwidth of the AP";
        }
        leaf avl-bandwidth {
            type decimal64 {
                fraction-digits 2;
                range "0..max";
            }
            description
                "available bandwidth of the AP";
        }
        /*add details and any other properties of AP,
        not associated by a VN
        CE port, PE port etc.

        This link may not be in the TE topology model(?)
        thus reference to that model would be incorrect
        */
    }//access-point

    grouping vn-member {
        description
            "vn-member is described by this container";
        leaf vn-member-id {
            type uint32;
            description
                "vn-member identifier";
        }
        leaf src {
            type leafref {
                path "/actn/ap/access-point-list/access-point-id";
            }
            description
                "reference to source AP";
        }
        leaf src-vn-ap-id{
            type uint32;
            description
                "vn-ap-id";
        }
        leaf dest {
            type leafref {
                path "/actn/ap/access-point-list/access-point-id";
            }
            description
                "reference to destination AP";
        }
        leaf dest-vn-ap-id{
            type uint32;
            description
                "vn-ap-id";
        }

        /* can we add reference to itef-te model(?) here
        */

    }//vn-member

    grouping connectivity-metric {
        description
            "service aware metrics";
        leaf delay {
            type uint32 {
                range "0..max";
            }
            description
                "Path Delay or latency in micro seconds.";
        }
        leaf delay-variation {
            type uint32 {
                range "0..max";
            }
            description
                "Path Delay variation in micro seconds.";
        }
        leaf packet-loss {
            type decimal64 {
                fraction-digits 6;
                range "0 .. max";
            }
            description
                "Path Packet Loss in percentage";
        }
        /*should we add other metrics
        like bandwidth utilization?*/

    }//connectivity-metric

    grouping policy {
        description
            "policy related to vn-member-id";
        leaf local-reroute {
            type boolean;
            description
                "Policy to state if reroute
                can be done locally";
        }
        leaf push-allowed {
            type boolean;
            description
                "Policy to state if changes
                can be pushed to the customer";
        }
        leaf incremental-update {
            type boolean;
            description
                "Policy to allow only the
                changes to be reported";
        }
    }//policy

    grouping objective-function {
        description
            "objective-function";

        uses connectivity-metric;

        leaf bandwidth {
            type decimal64 {
                fraction-digits 2;
                range "0..max";
            }
            description
                "bandwidth requested/required for
                vn-member-id";
        }

        leaf protection {
            type identityref {
                base te-types:lsp-prot-type;
            }
            description "protection type.";
        }

        uses policy;

    }//objective-function

    /*
     * Configuration data nodes
     */
    container actn {
        description
            "actn is described by this container";
        container ap {
            description
                "AP configurations";
         list access-point-list {
                key "access-point-id";
                description
                    "access-point identifier";
                uses access-point{
                    description
                        "access-point information";
                }
         }
        }
        container vn {
            description
                "VN configurations";
            list vn-list {
                key "vn-id";
                description
                    "a virtual network is identified by a vn-id";
                leaf vn-id {
                    type uint32;
                    description
                        "a unique vn identifier";
                }
                leaf vn-name {
                    type string;
                    description "vn name";
                }
                list vn-member-list{
                    key "vn-member-id";
                    description
                        "List of VN-members in a VN";
                    uses vn-member;
                }
                uses objective-function;

                leaf admin-status {
                    type identityref {
                        base te-types:state-type;
                    }
                    default te-types:state-up;
                    description "VN administrative state.";
                }
            }//vn-list
        }//vn
    }//actn

    /*
     * Operational data nodes
     */

    container actn-state{
        config false;

        description
            "actn is described by this container";
        container ap {
            description
                "AP state";
            list access-point-list {
                key "access-point-id";
                description
                    "access-point identifier";
                uses access-point{
                    description
                        "access-point information";
                }
         }
        }
        container vn {
            description
                "VN state";
            list vn-list {
                key "vn-id";
                description
                    "a virtual network is identified by a vn-id";
                leaf vn-id {
                    type uint32;
                    description
                        "a unique vn identifier";
                }
                leaf vn-name {
                    type string;
                    description "vn name";
                }
                list vn-member-list{
                    key "vn-member-id";
                    description
                        "List of VN-members in a VN";
                    uses vn-member;
                    uses connectivity-metric;
                    leaf oper-status {
                        type identityref {
                            base te-types:state-type;
                        }
                        description
                            "VN-member operational state.";
                    }
                }

                uses objective-function;

                leaf admin-status {
                    type identityref {
                        base te-types:state-type;
                    }
                    description "VN administrative state.";
                }
                leaf oper-status {
                    type identityref {
                        base te-types:state-type;
                    }
                    description "VN operational state.";
                }
            }//vn-list
        }//vn
    }//actn-state
}
