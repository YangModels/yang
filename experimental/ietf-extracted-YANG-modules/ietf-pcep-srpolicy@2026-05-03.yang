module ietf-pcep-srpolicy {
  yang-version 1.1;
  namespace "urn:ietf:params:xml:ns:yang:ietf-pcep-srpolicy";
  prefix pcep-srp;

  import ietf-inet-types {
    prefix inet;
    reference
      "RFC 6991: Common YANG Data Types";
  }
  import ietf-te-types {
    prefix te-types;
    reference
      "RFC 8776: Common YANG Data Types for Traffic Engineering";
  }
  import ietf-pcep {
    prefix pcep;
    reference
      "RFC 9826: A YANG Data Model for Path
       Computation Element Communications Protocol (PCEP)";
  }
  import ietf-sr-policy-types {
    prefix sr-policy-types;
    reference
      "I-D.ietf-spring-sr-policy-yang: YANG Data Model for
       Segment Routing Policy";
  }
  import ietf-srv6-types {
    prefix srv6-types;
    reference
      "I-D.ietf-spring-srv6-yang: YANG Data Model for SRv6
       Base and Static";
  }
  import ietf-pcep-srv6 {
    prefix pcep-srv6;
    reference
      "I-D.ietf-pce-pcep-srv6-yang: A YANG Data Model for
       Segment Routing (SR) Policy and SR in IPv6 (SRv6)
       support in Path Computation Element Communications
       Protocol (PCEP)";
  }

  organization
    "IETF PCE (Path Computation Element) Working Group";
  contact
    "WG Web:   <https://datatracker.ietf.org/wg/pce/>
     WG List:  <mailto:pce@ietf.org>
     Editor:   Cheng Li
               <mailto:c.l@huawei.com>
               Shuping Peng
               <mailto:pengshuping@huawei.com>";
  description
    "The YANG module augments the Path Computation Element
     Communications Protocol (PCEP) YANG model with Segment
     Routing (SR) Policy.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see the
     RFC itself for full legal notices.";

  revision 2026-05-03 {
    description
      "Initial revision.";
    reference
      "RFC XXXX:  A YANG Data Model for Segment Routing (SR) Policy
       and SRv6 support in Path Computation Element Communications
       Protocol (PCEP)";
  }

  /* Features */

  feature multipath {
    description
      "Support for multipath ERO.";
    reference
      "I-D.ietf-pce-multipath: PCEP Extensions for Signaling
       Multipath Information";
  }

  feature algo {
    description
      "Support for SR Algorithm";
    reference
      "I-D.ietf-pce-sid-algo: Carrying SR-Algorithm in Path
       Computation Element Communication Protocol (PCEP)";
  }

  /* Identities */

  identity sr-policy {
    base te-types:association-type;
    description
      "SR Policy Association";
    reference
      "I-D.ietf-pce-segment-routing-policy-cp: PCEP extension to
       support Segment Routing Policy Candidate Paths";
  }

  identity nai-type {
    description
      "Base identity for NAI (Node or Adjacency Identifier) Type
       (NT)";
    reference
      "Derived from the specification of NAI Type (NT) field in
       [I-D/related document section].";
  }

  identity nai-type-absent {
    base nai-type;
    description
      "NT=0: The NAI is absent.";
  }

  identity nai-type-ipv4-node-id {
    base nai-type;
    description
      "NT=1: The NAI is an IPv4 node ID.";
  }

  identity nai-type-ipv6-node-id {
    base nai-type;
    description
      "NT=2: The NAI is an IPv6 node ID.";
  }

  identity nai-type-ipv4-adjacency {
    base nai-type;
    description
      "NT=3: The NAI is an IPv4 adjacency.";
  }

  identity nai-type-ipv6-adjacency-global {
    base nai-type;
    description
      "NT=4: The NAI is an IPv6 adjacency with global IPv6
       addresses.";
  }

  identity nai-type-unnumbered-adjacency-ipv4-node-id {
    base nai-type;
    description
      "NT=5: The NAI is an unnumbered adjacency with IPv4 node
       IDs.";
  }

  identity nai-type-ipv6-adjacency-linklocal {
    base nai-type;
    description
      "NT=6: The NAI is an IPv6 adjacency with link-local
       IPv6 addresses.";
  }

  /* Groupings */

  grouping sr-policy {
    description
      "Segment Routing Policy grouping";
    leaf headend {
      type inet:ip-address-no-zone;
      description
        "SR Policy headend";
      reference
        "RFC 9256: Segment Routing Policy Architecture";
    }
    leaf color {
      type sr-policy-types:color-type;
      description
        "SR Policy Color";
      reference
        "RFC 9256: Segment Routing Policy Architecture";
    }
    leaf endpoint {
      type inet:ip-address-no-zone;
      description
        "SR Policy Endpoint";
      reference
        "RFC 9256: Segment Routing Policy Architecture";
    }
    leaf name {
      type sr-policy-types:name-type;
      description
        "SR Policy name";
      reference
        "RFC 9256: Segment Routing Policy Architecture";
    }
  }

  grouping sr-policy-cp {
    description
      "Segment Routing Policy Candidate Path grouping";
    leaf protocol-origin {
      type identityref {
        base sr-policy-types:protocol-origin-type;
      }
      description
        "SR Policy Candidate Path Protocol";
      reference
        "RFC 9256: Segment Routing Policy Architecture";
    }
    leaf originator {
      type string;
      description
        "SR Policy Candidate Path Originator";
      reference
        "RFC 9256: Segment Routing Policy Architecture";
    }
    leaf discriminator {
      type uint32 {
        range "1..max";
      }
      description
        "SR Policy Candidate Path Discriminator";
      reference
        "RFC 9256: Segment Routing Policy Architecture";
    }
    leaf name {
      type string;
      description
        "SR Policy Candidate Path name";
      reference
        "RFC 9256: Segment Routing Policy Architecture";
    }
  }

  grouping segment-lists {
    description
      "Segment list grouping";
    list segment-list {
      key "path-id";
      leaf path-id {
        type uint32;
        description
          "Uniquely identify a path or segment-list within
           a candidate path";
      }
      description
        "Segment list";
      list segment {
        key "index";
        description
          "Configure Segment/hop at the index";
        uses segment-properties;
      }
    }
  }

  grouping segment-properties {
    description
      "Segment properties grouping";
    leaf index {
      type uint32;
      description
        "Segment index";
    }
    leaf sid-value {
      type sr-policy-types:sid-value-type;
      description
        "SID value";
      reference
        "RFC 8664:Path Computation Element Communication Protocol
         (PCEP) Extensions for Segment Routing
         RFC 9603:Path Computation Element Communication Protocol
         (PCEP) Extensions for IPv6 Segment Routing";
    }
    leaf nai-type {
      type identityref {
        base nai-type;
      }
      description
        "Indicates the type and format of the NAI";
    }
    choice nai {
      description
        "Choice for NAI Types";
      case ipv4-node-id {
        when "derived-from-or-self(./nai-type,
              'pcep-srp:nai-type-ipv4-node-id')";
        leaf ipv4-node-id {
          type inet:ipv4-address-no-zone;
          mandatory true;
          description
            "NT=1: IPv4 Node ID.";
        }
      }
      case ipv6-node-id {
        when "derived-from-or-self(./nai-type,
              'pcep-srp:nai-type-ipv6-node-id')";
        leaf ipv6-node-id {
          type inet:ipv6-address-no-zone;
          mandatory true;
          description
            "NT=2: IPv6 Node ID.";
        }
      }
      case ipv4-adjacency {
        when "derived-from-or-self(./nai-type,
              'pcep-srp:nai-type-ipv4-adjacency')";
        container ipv4-adjacency {
          description
            "NT=3: pair of IPv4 addresses (local, remote).";
          leaf local {
            type inet:ipv4-address-no-zone;
            mandatory true;
            description
              "local IPv4 address.";
          }
          leaf remote {
            type inet:ipv4-address-no-zone;
            mandatory true;
            description
              "remote IPv4 address.";
          }
        }
      }
      case ipv6-adjacency-global {
        when "derived-from-or-self(./nai-type,
              'pcep-srp:nai-type-ipv6-adjacency-global')";
        container ipv6-adjacency-global {
          description
            "NT=4: pair of global IPv6 addresses (local, remote).";
          leaf local {
            type inet:ipv6-address-no-zone;
            mandatory true;
            description
              "local IPv6 address.";
          }
          leaf remote {
            type inet:ipv6-address-no-zone;
            mandatory true;
            description
              "remote IPv6 address.";
          }
        }
      }
      case unnumbered-adjacency-ipv4-node-id {
        when "derived-from-or-self(./nai-type,
              'pcep-srp:nai-type-unnumbered-adjacency-ipv4-node-id')";
        container unnumbered-adjacency {
          description
            "NT=5: (node ID, interface ID) tuples for local and
             remote.";
          container local {
            description
              "local";
            leaf node-id {
              type inet:ipv4-address-no-zone;
              mandatory true;
              description
                "local node ID.";
            }
            leaf if-id {
              type uint32;
              mandatory true;
              description
                "local interface ID.";
            }
          }
          container remote {
            description
              "remote";
            leaf node-id {
              type inet:ipv4-address-no-zone;
              mandatory true;
              description
                "remote node ID.";
            }
            leaf if-id {
              type uint32;
              mandatory true;
              description
                "remote interface ID.";
            }
          }
        }
      }
      case ipv6-adjacency-linklocal {
        when "derived-from-or-self(./nai-type,
              'pcep-srp:nai-type-ipv6-adjacency-linklocal')";
        container ipv6-adjacency-linklocal {
          description
            "NT=6: (global IPv6 address, interface ID) tuples for
             local/remote.";
          container local {
            description
              "local";
            leaf global-address {
              type inet:ipv6-address-no-zone;
              mandatory true;
              description
                "local global address.";
            }
            leaf if-id {
              type uint32;
              mandatory true;
              description
                "local interface ID.";
            }
          }
          container remote {
            description
              "remote";
            leaf global-address {
              type inet:ipv6-address-no-zone;
              mandatory true;
              description
                "remote global address.";
            }
            leaf if-id {
              type uint32;
              mandatory true;
              description
                "remote interface ID.";
            }
          }
        }
      }
      case absent {
        when "derived-from-or-self(./nai-type,
              'pcep-srp:nai-type-absent')";
        description
          "NT=0: NAI absent; no payload.";
      }
    }
    leaf algorithm {
      type uint8;
      description
        "SID algorithm identifier";
    }
    container srv6 {
      when "derived-from-or-self
            (/pcep:pcep/pcep:entity/pcep:lsp-db/pcep:lsp/pcep:pst,
             'path-setup-srv6')" {
        description
          "For SRv6 path";
      }
      if-feature "pcep-srv6:srv6";
      uses pcep-srv6:sid-str;
      leaf endpoint-behavior {
        type identityref {
          base srv6-types:srv6-endpoint-type;
        }
        description
          "The behavior associated with the SRv6 SIDs.";
      }
      description
        "SRv6 specific parameters";
    }
  }

  augment "/pcep:pcep/pcep:entity/pcep:lsp-db/pcep:lsp" {
    description
      "Augmenting SR Policy";
    container sr-policy {
      when "derived-from-or-self
            (/pcep:pcep/pcep:entity/pcep:lsp-db/pcep:lsp/pcep:pst,
             'path-setup-sr') or
            derived-from-or-self
            (/pcep:pcep/pcep:entity/pcep:lsp-db/pcep:lsp/pcep:pst,
             'path-setup-srv6')" {
        description
          "Applicable for SR or SRv6";
      }
      uses sr-policy;
      container cp {
        uses sr-policy-cp;
        description
          "SR Policy Candidate Path Information";
      }
      description
        "SR Policy information";
    }
  }

  augment "/pcep:pcep/pcep:entity/pcep:capabilities"
        + "/pcep:sr-mpls" {
    description
      "Augmenting Algorithm Capability";
    leaf algo {
      if-feature "algo";
      type boolean;
      default "false";
      description
        "Indicates capability for SR-MPLS Algorithm";
    }
  }

  augment "/pcep:pcep/pcep:entity/pcep:peers/pcep:peer"
        + "/pcep:capabilities/pcep:sr-mpls" {
    description
      "Augmenting Algorithm Capability";
    leaf algo {
      if-feature "algo";
      type boolean;
      default "false";
      description
        "Indicates capability for SR-MPLS Algorithm";
    }
  }

  augment "/pcep:pcep/pcep:entity/pcep:lsp-db/pcep:lsp" {
    description
      "Augmenting SR-MPLS for LSP";
    container sr {
      when "derived-from-or-self
            (/pcep:pcep/pcep:entity/pcep:lsp-db/pcep:lsp/pcep:pst,
             'path-setup-sr') or
            derived-from-or-self
            (/pcep:pcep/pcep:entity/pcep:lsp-db/pcep:lsp/pcep:pst,
             'path-setup-srv6')" {
        description
          "Applicable for SR or SRv6";
      }
      uses segment-lists;
      description
        "SR information";
    }
  }
}
