module ietf-vpn-svc-pm {
  yang-version 1.1;
  namespace "urn:ietf:params:xml:ns:yang:ietf-vpn-svc-pm";
  prefix svc-topo;
  import ietf-network {
    prefix nw;
  }
  import ietf-network-topology {
    prefix nt;
  }
  import ietf-l3vpn-svc {
   prefix l3vpn-svc;
  }
  organization
    "IETF xxx Working Group";
  contact
    "Zitao Wang: wangzitao@huawei.com
     Qin Wu: bill.wu@huawei.com";
  description
    "This module defines a model for the service topology.";

  revision 2018-08-29 {
    description
      "Initial revision.";
    reference "foo";
  }

  identity service-type {
    description
      "Base type for service topology";
  }

  identity l3vpn-svc {
    base service-type;
    description
      "Indentity for layer3 vpn service";
  }

  identity l2vpn-svc {
    base service-type;
    description
      "Identity for layer2 vpn service";
  }

  identity node-type {
    description
      "Base identity for node type";
  }

  identity pe {
    base node-type;
    description
      "Identity for PE type";
  }

  identity ce {
    base node-type;
    description
      "Identity for CE type";
  }

  identity asbr {
    base node-type;
    description
      "Identity for ASBR type";
  }

  identity p {
    base node-type;
    description
      "Identity for P type";
  }

  identity direction {
    description
      "Base Identity for measurement direction including
       one way measurement and two way measurement.";
  }

  identity oneway {
    base direction;
    description
      "Identity for one way measurement.";
  }

  identity twoway {
    base direction;
    description
      "Identity for two way measurement.";
  }

  typedef percentage {
    type decimal64 {
      fraction-digits 5;
      range "0..100";
    }
    description
      "Percentage.";
  }

  grouping link-error-statistics {
    description
      "Grouping for per link error statistics";
    container loss-statistics {
      description
        "Per link loss statistics.";
       leaf direction {
        type identityref {
          base direction;
        }
        default "oneway";
        description
          "Define measurement direction including one way
           measurement and two way measurement.";
      }
      leaf packet-loss-count {
        type uint32 {
          range "0..4294967295";
        }
        default "0";
        description
          "Total received packet drops count.
           The value of count will be set to zero (0)
           on creation and will thereafter increase
           monotonically until it reaches a maximum value
           of 2^32-1 (4294967295 decimal), when it wraps
           around and starts increasing again from zero.";
      }
      leaf loss-ratio {
        type percentage;
        description
          "Loss ratio of the packets. Express as percentage
           of packets lost with respect to packets sent.";
      }
      leaf packet-reorder-count {
        type uint32 {
          range "0..4294967295";
        }
        default "0";
        description
          "Total received packet reordered count.
           The value of count will be set to zero (0)
           on creation and will thereafter increase
           monotonically until it reaches a maximum value
           of 2^32-1 (4294967295 decimal), when it wraps
           around and starts increasing again from zero.";
      }
      leaf packets-out-of-seq-count {
        type uint32 {
          range "0..4294967295";
        }
        description
          "Total received out of sequence count.
           The value of count will be set to zero (0)
           on creation and will thereafter increase
           monotonically until it reaches a maximum value
           of 2^32-1 (4294967295 decimal), when it wraps
           around and starts increasing again from zero..";
      }
      leaf packets-dup-count {
        type uint32 {
          range "0..4294967295";
        }
        description
          "Total received packet duplicates count.
           The value of count will be set to zero (0)
           on creation and will thereafter increase
           monotonically until it reaches a maximum value
           of 2^32-1 (4294967295 decimal), when it wraps
           around and starts increasing again from zero.";
      }
    }
  }

  grouping link-delay-statistics {
    description
      "Grouping for per link delay statistics";
    container delay-statistics {
      description
        "Link delay summarised information. By default,
         one way measurement protocol (e.g., OWAMP) is used
         to measure delay.";
      leaf direction {
        type identityref {
          base direction;
        }
        default "oneway";
        description
          "Define measurement direction including one way
           measurement and two way measurement.";
      }
      leaf min-delay-value {
        type uint32;
        description
          "Minimum delay value observed.";
      }
      leaf max-delay-value {
        type uint32;
        description
          "Maximum delay value observed.";
      }
      leaf average-delay-value {
        type uint32;
        description
          "Average delay value observed.";
      }
    }
  }

  grouping link-jitter-statistics {
    description
      "Grouping for per link jitter statistics";
    container jitter-statistics {
      description
        "Link jitter summarised information. By default,
         jitter is measured using IP Packet Delay Variation
         (IPDV) as defined in RFC3393.";
      leaf direction {
        type identityref {
          base direction;
        }
        default "oneway";
        description
          "Define measurement direction including one way
           measurement and two way measurement.";
      }
      leaf min-jitter-value {
        type uint32;
        description
          "Minimum jitter value observed.";
      }
      leaf max-jitter-value {
        type uint32;
        description
          "Maximum jitter value observed.";
      }
      leaf average-jitter-value {
        type uint32;
        description
          "Average jitter value observed.";
      }
    }
  }

  augment "/nw:networks/nw:network/nw:network-types" {
    description
      "Augment the network-types with service topologyies types";
    leaf svc-topo-type {
      type identityref {
        base service-type;
      }
      description
        "Identify the topology type to be composited service topology";
    }
  }
  augment "/nw:networks/nw:network" {
    description
      "Augment the network with service topology attributes";
    container svc-topo-attributes {
      leaf vpn-topology {
        type identityref {
          base l3vpn-svc:vpn-topology;
        }
        description
          "VPN service topology, e.g. hub-spoke, any-to-any, hub-spoke-disjoint, etc";
      }
      description
        "Container for vpn services";
    }
  }
  augment "/nw:networks/nw:network/nw:node" {
    description
      "Augment the network node with serice attributes";
    container node-attributes {
      leaf node-type {
        type identityref {
          base node-type;
        }
        description
          "Node type, e.g. PE, P, ASBR, etc";
      }
      leaf site-id {
        type string;
        description
          "Asscoiated vpn site";
      }
      leaf site-role {
        type identityref {
          base l3vpn-svc:site-role;
        }
        default "l3vpn-svc:any-to-any-role";
        description
          "Role of the site in the IP VPN.";
      }
      description
        "Container for service topology attributes";
    }
  }
  augment "/nw:networks/nw:network/nt:link" {
    description
      "Augment the network topology link with vpn service attributes";
    container svc-telemetry-attributes {
      config false;
      uses link-error-statistics;
      uses link-delay-statistics;
      uses link-jitter-statistics;
      description
        "Container for service telemetry attributes";
    }
  }
}
