module ietf-ace-brski-ace {
  yang-version 1.1;

  namespace "urn:ietf:params:xml:ns:yang:ietf-ace-brski-ace";

  prefix vch-ace;

  import ietf-voucher {
    prefix vch;
    reference "I-D.ietf-anima-rfc8366bis-07";
  }

  organization
    "IETF ACE (Authentication and Authorization for Constrained Environments)
    Working Group";

  contact
    "WG Web:   <http://tools.ietf.org/wg/ace/>
     WG List:  <mailto:ace@ietf.org>

     Editor:   Christian AmsÃ¼ss
               <mailto:christian@amsuess.com>";

  description
    "This module augments the voucher artifact for bootstrapping
    (onboarding) with mechanisms for onboarding onto ACE (Authentication
    and Authorization for Constrained Environments) Authorization
    Servers.

    Copyright (c) 2019 IETF Trust and the persons identified as
    authors of the code. All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see the
    RFC itself for full legal notices.";

  revision 2023-07-07 {
    description
      "Initial revision.";

    reference
      "I-D.amsuess-ace-brski-ace, Provisioning ACE credentials through
      BRSKI";
  }

  uses "vch:voucher-artifact-grouping" {
    augment "voucher" {
      description
        "Mechanisms for onboarding onto ACE (Authentication and Authorization
        for Constrained Environments) Authorization Servers";

      leaf ace-as-key {
        type binary;
        description
          "Key(s) held by the ACE Authorization Server by which it
          authenticates (and the Resource Server verifies) tokens.
          It is a CBOR encoded COSE_KeySet.";
        reference
          "I-D.amsuess-ace-brski-ace, Provisioning ACE credentials
          through BRSKI";
      }

      leaf ace-aud {
        type string;
        description
          "Audience identifier by which the ACE Authorization Server
          will be the pledge that is enrolled as an ACE Resource
          Server.";
        reference
          "I-D.amsuess-ace-brski-ace, Provisioning ACE credentials
          through BRSKI";
      }
    }
  }
}
