module ietf-supa-policy { 
  namespace "urn:ietf:params:xml:ns:yang:ietf-supa-policy"; 
  // replace with IANA namespace when assigned 
  prefix policy; 

  import ietf-inet-types { 
    prefix inet; 
  } 

  organization "IETF"; 
  contact 
    "Editor: Maoke Chen"; 

  description 
    "This YANG module defines a component that describing 
     the ECA policy data model refining from SGPIM and EPRIM. 

     Terms and Acronyms 

  revision 2015-07-02 { 
    description 
    "Initial revision."; 
    reference 
        " ECA Policy YANG Data Model refining from SGPIM and 
     EPRIM"; 
  }
