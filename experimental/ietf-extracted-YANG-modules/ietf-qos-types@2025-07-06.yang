module ietf-qos-types {
  yang-version 1.1;
  namespace "urn:ietf:params:xml:ns:yang:ietf-qos-types";
  prefix qos-types;

  organization
    "IETF Routing Area Working Group";

  contact
    "WG Web:   <https://datatracker.ietf.org/wg/rtgwg/>
     WG List:  <mailto:rtgwg@ietf.org>

     Editor:   Aseem Choudhary
               <mailto:asechoud@cisco.com>
     Editor:   Mahesh Jethanandani
               <mailto:mjethanandani@gmail.com>";

  description
    "This module contains type definitions for all QoS types.

     Copyright (c) 2022 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2025-07-06 {
    description
      "Initial version";
    reference
      "RFC XXXX: YANG Models for Quality of Service (QoS).";
  }

  /*
   * Features.
   */
  feature child-policy {
    description
      " This feature allows configuration of hierarchical policy.";
  }
  feature count {
    description
      "This feature allows action configuration to enable
       counter in a classifier";
  }
  feature named-counter {
    description
      "This feature allows action configuration to enable
       named counter in a classifier";
  }

  /*
   * Identities.
   */
  identity policy-type {
    description
      "Base identity for policy type.";
  }
  identity diffserv-policy-type {
    base policy-type;
    description
      "Policy type defined as DiffServ.";
  }
  identity ipv4-diffserv-policy-type {
    base policy-type;
    description
      "Policy type defined as a DiffServ IPv4 policy type.";
  }
  identity ipv6-diffserv-policy-type {
    base policy-type;
    description
      "Policy type defined as a DiffServ IPv6 policy type.";
  }
  identity queue-policy-type {
    base policy-type;
    description
      "Policy type defined as a queue policy type.";
  }
  identity scheduler-policy-type {
    base policy-type;
    description
      "Policy type defined as a scheduler policy type.";
  }

  identity action-type {
    description
      "Base identity for the action type.";
  }
  identity dscp-marking {
    base action-type;
    description
      "Action type defined as DSCP marking.";
  }
  identity meter-inline {
    base action-type;
    description
      "Action type defined as meter inline.";
  }
  identity meter-reference {
    base action-type;
    description
      "Action type defined as meter reference.";
  }
  identity queue {
    base action-type;
    description
      "Action type defined as queue.";
  }
  identity scheduler {
    base action-type;
    description
      "Action type defined as scheduler.";
  }
  identity discard {
    base action-type;
    description
      "Action type defined as discard.";
  }
  identity child-policy {
    if-feature child-policy;
    base action-type;
    description
      "Action type defined as child policy.";
  }
  identity count {
    if-feature count;
    base action-type;
    description
      "Action type defined as count.";
  }
  identity named-counter {
    if-feature named-counter;
    base action-type;
    description
      "Action type specified as a named counter.";
  }
  identity queue-policy-name {
    base action-type;
    description
      "Action type specified as a queue policy name.";
  }

  identity meter-type {
    description
      "Base identity for types of meter.";
  }
  identity one-rate-two-color {
    base meter-type;
    description
      "Meter type specified as one rate two color meter.";
  }
  identity one-rate-tri-color {
    base meter-type;
    description
      "Meter type specified as one rate three color meter.";
  }
  identity two-rate-tri-color {
    base meter-type;
    description
      "Meter type specified as two rate three color meter.";
  }

  identity drop-type {
    description
      "Base identity for drop algorithm.";
  }
  identity tail-drop {
    base drop-type;
    description
      "Drop algorithm specified as tail drop.";
  }
  identity red {
    base drop-type;
    description
      "Drop algorithm specified as RED.";
  }
  identity wred {
    base drop-type;
    description
      "Drop algorithm specified as WRED.";
  }

  identity rate-unit-type {
    description
      "Base definition for the type of rate unit.";
  }
  identity bits-per-second {
    base rate-unit-type;
    description
      "Rate specified in bits per second.";
  }
  identity percent {
    base rate-unit-type;
    description
      "Rate specified as a percentage of queue depth.";
  }

  identity burst-unit-type {
    description
      "Base definition for burst specification.";
  }
  identity bytes {
    base burst-unit-type;
    description
      "Burst specified in bytes.";
  }
  identity microsecond {
    base burst-unit-type;
    description
      "Burst specified in microseconds.";
  }

  identity red-threshold-unit {
    description
      "Base definition for RED threshold specification.";
  }
  identity red-threshold-bytes {
    base red-threshold-unit;
    description
      "RED threshold specified in bytes.";
  }
  identity red-threshold-us {
    base red-threshold-unit;
    description
      "RED threshold specified in microseconds.";
  }
  identity red-threshold-pc {
    base red-threshold-unit;
    description
      "RED threshold specified as a percentage.";
  }
  identity red-theshold-pt {
    base red-threshold-unit;
    description
      "RED threshold specified per-thousand.";
  }

  identity wred-color-type {
    description
      "Base identity for WRED color type.";
  }
  identity wred-color-dscp {
    base wred-color-type;
    description
      "WRED color specified by DSCP.";
  }

  identity probability-unit {
    description
      "Base definition for probability unit.";
  }
  identity probability-pc {
    base probability-unit;
    description
      "Probability specified in percentage.";
  }
  identity probability-pt {
    base probability-unit;
    description
      "Probability specified in unit of per thousand.";
  }
  identity probability-denominator {
    base probability-unit;
    description
      "Probability value specified as a denominator value
       while numerator is always 1.";
  }

  identity filter-type {
    description
      "Base identity for filter type.";
  }

  identity dscp {
    base filter-type;
    description
      "Filter type specified as DSCP.";
  }
  identity source-ipv4-prefix {
    base filter-type;
    description
      "Filter type specified as source IPv4 prefix.";
  }
  identity destination-ipv4-prefix {
    base filter-type;
    description
      "Filter type specified as destination IPv4 prefix.";
  }
  identity source-ipv6-prefix {
    base filter-type;
    description
      "Filter type specified as source IPv6 prefix.";
  }
  identity destination-ipv6-prefix {
    base filter-type;
    description
      "Filter type specified as destination IPv6 prefix.";
  }
  identity source-port {
    base filter-type;
    description
      "Filter type specified as source port.";
  }
  identity destination-port {
    base filter-type;
    description
      "Filter type specified as destination port.";
  }
  identity protocol {
    base filter-type;
    description
      "Filter type specified as protocol.";
  }
  identity traffic-group-name {
    base filter-type;
    description
      "Filter type specified as traffic group name.";
  }
  identity filter-match-all {
    base filter-type;
    description
      "Filter type specified as match all.";
  }

  typedef match-operation-type {
    type enumeration {
      enum match-all {
        description
          "Classifier entry filters logical AND operation";
      }
      enum match-any {
        description
          "Classifier entry filters logical OR operation";
      }
    }
    default "match-all";
    description
      "Filter match logical operation type";
  }

  identity direction {
    description
      "Base identity for traffic direction";
  }
  identity ingress {
    base direction;
    description
      "Direction of traffic coming into the network entry";
  }
  identity egress {
    base direction;
    description
      "Direction of traffic going out of the network entry";
  }

  identity meter-action-type {
    description
      "Base identify for actions related to metering";
  }
  identity action-drop {
    base meter-action-type;
      description
        "Drop packets that conform/exceed/violate to the set value.";
  }
  identity action-transmit {
    base meter-action-type;
      description
        "Transmit packets that conform/exceed/violate to the set
         value.";
  }
  identity action-mark {
    base meter-action-type;
      description
        "Mark packets that conform/exceed/violate to the set value.";
  }

  identity clear-counters-type {
    description
      "Base identify for clear interface counters related options";
  }
  identity all-counters {
    base clear-counters-type;
      description
        "Clear all counters in both directions.";
  }
  identity inbound-counters {
    base clear-counters-type;
      description
        "Clear counters in inbound direction.";
  }
  identity outbound-counters {
    base clear-counters-type;
      description
        "Clear counters in outbound direction.";
  }
}
