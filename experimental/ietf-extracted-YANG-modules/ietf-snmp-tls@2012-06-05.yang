submodule ietf-snmp-tls {

  belongs-to ietf-snmp {
    prefix snmp;
  }

  import ietf-inet-types {
    prefix inet;
  }

  include ietf-snmp-common;
  include ietf-snmp-engine;
  include ietf-snmp-target;

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";

  description
    "This submodule contains a collection of YANG definitions for
     configuring the Transport Layer Security Transport Model (TLSTM)
     of SNMP.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  reference
    "RFC6353: Transport Layer Security (TLS) Transport Model for
              the Simple Network Management Protocol (SNMP)";

  // RFC Ed.: update the date below with the date of RFC publication
  // and remove this note.

  revision 2012-06-05 {
    description
      "Initial revision.";
    reference
      "RFC XXXX: A YANG Data Model for SNMP Configuration";
  }

  /* Typedefs */

  typedef tls-fingerprint {
    type string { // FIXME hex-string?
      pattern '([0-9a-fA-F]){2}(:([0-9a-fA-F]){2}){4,31}';
    }
  }

  /* Identities */

  identity cert-to-tm-security-name {
  }

  identity specified {
    base cert-to-tm-security-name;
    reference "SNMP-TLS-TM-MIB.snmpTlstmCertSpecified";
  }

  identity san-rfc822-name {
    base cert-to-tm-security-name;
    reference "SNMP-TLS-TM-MIB.snmpTlstmCertSANRFC822Name";
  }

  identity san-dns-name {
    base cert-to-tm-security-name;
    reference "SNMP-TLS-TM-MIB.snmpTlstmCertSANDNSName";
  }

  identity san-ip-address {
    base cert-to-tm-security-name;
    reference "SNMP-TLS-TM-MIB.snmpTlstmCertSANIpAddress";
  }

  identity san-any {
    base cert-to-tm-security-name;
    reference "SNMP-TLS-TM-MIB.snmpTlstmCertSANAny";
  }

  augment /snmp:snmp/snmp:engine/snmp:listen {
    if-feature tlstm;
    list tls {
      key "ip port";
      description
        "A list of IPv4 and IPv6 addresses and ports to which the
         engine listens for SNMP messages over TLS.";

      leaf ip {
        type inet:ip-address;
        description
          "The IPv4 or IPv6 address on which the engine listens
           for SNMP messages over TLS.";
      }
      leaf port {
        type inet:port-number;
        description
          "The TCP port on which the engine listens for SNMP
           messages over TLS.";
      }
    }
    list dtls {
      key "ip port";
      description
        "A list of IPv4 and IPv6 addresses and ports to which the
         engine listens for SNMP messages over DTLS.";

      leaf ip {
        type inet:ip-address;
        description
          "The IPv4 or IPv6 address on which the engine listens
           for SNMP messages over DTLS.";
      }
      leaf port {
        type inet:port-number;
        description
          "The UDP port on which the engine listens for SNMP messages
           over DTLS.";
      }
    }
  }

  augment /snmp:snmp {
    if-feature tlstm;
    container tlstm {
      list cert-to-tm-security-name {
        key id;
        reference "SNMP-TLS-TM-MIB.snmpTlstmCertToTSNEntry";
        leaf id {
          type uint32;
          reference "SNMP-TLS-TM-MIB.snmpTlstmCertToTSNID";
        }
        leaf fingerprint {
          type tls-fingerprint;
          reference "SNMP-TLS-TM-MIB.snmpTlstmCertToTSNFingerprint";
        }
        leaf map-type {
          type identityref {
            base cert-to-tm-security-name;
          }
          reference "SNMP-TLS-TM-MIB.snmpTlstmCertToTSNMapType";
        }
        // FIXME: not as flexible as the mib.  to get the same
        // flexibility, either change this to data (choice of binary
        // and string), or remove the identities and use
        // augmentation.
        leaf cert-specified-tm-security-name {
          when "../map-type = snmp:specified";
          type admin-string;
          reference "SNMP-TLS-TM-MIB.snmpTlstmCertToTSNData";
        }
      }
    }
  }

  grouping tls-transport {
    leaf ip {
      type inet:ip-address;
      reference "SNMP-TARGET-MIB.snmpTargetAddrTAddress";
    }
    leaf port {
      type inet:port-number;
      default 10161;
      reference "SNMP-TARGET-MIB.snmpTargetAddrTAddress";
    }
    leaf client-fingerprint {
      type tls-fingerprint;
      reference "SNMP-TLS-TM-MIB.snmpTlstmParamsClientFingerprint";
    }
    choice server-identification {
      leaf server-fingerprint {
        type tls-fingerprint;
        reference "SNMP-TLS-TM-MIB.snmpTlstmAddrServerFingerprint";
      }
      leaf server-identity {
        type admin-string;
        reference "SNMP-TLS-TM-MIB.snmpTlstmAddrServerIdentity";
      }
    }
  }

  augment /snmp:snmp/snmp:target/snmp:transport {
    if-feature tlstm;
    case tls {
      reference "SNMP-TLS-TM-MIB.snmpTLSTCPDomain";
      container tls {
        uses tls-transport;
      }
    }
  }

  augment /snmp:snmp/snmp:target/snmp:transport {
    if-feature tlstm;
    case dtls {
      reference "SNMP-TLS-TM-MIB.snmpDTLSUDPDomain";
      container dtls {
        uses tls-transport;
      }
    }
  }
}
