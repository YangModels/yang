module ietf-ipv6-sav-rule {
  yang-version "1.1";
  namespace "urn:ietf:params:xml:ns:yang:ietf-ipv6-sav-rule";
  prefix "v6sav";

  import ietf-sav {
    prefix "sav";
  }

  import ietf-interfaces {
    prefix "if";
  }

  import ietf-inet-types {
    prefix "inet";
  }

  organization
    "IETF SAVNET Working Group";

  contact
    "TBD";

  description
    "This YANG module defines the essential elements for the
     management of IPv6 SAV rule.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2023-05-20 {
    description
      "Initial revision.";
    reference
      "RFC XXXX: A YANG Data Model for SAV Management";
  }

  /* Identities */

  identity ipv6 {
    base sav:ipv6;
    description
      "This identity represents the IPv6 address family.";
  }

  /* Groupings */
  grouping limit-metadata {
    description
      "Common SAV-rule limit metadata.";
    leaf number {
      type uint32;
      description
        "This attribute allows for controlling number limit.";
    }
    leaf threshold-percent {
      type uint8 {
        range "0..100";
      }
      description
        "This attribute allows for controlling threshold percentage
         limit.";
    }
    leaf threshold-number {
      type uint32;
      description
        "This attribute allows for controlling threshold number
         limit.";
    }
  }

  augment "/sav:sav/sav:sav-tables/sav:sav-table/"
        + "sav:sav-rules/sav:sav-rule" {
    when "derived-from-or-self(../../sav:address-family, "
       + "'v6sav:ipv6')" {
      description
        "This augment is valid only for IPv6.";
    }
    description
      "This leaf augments an IPv6 SAV rule.";
    leaf source-prefix {
      type inet:ipv6-prefix;
      description
        "IPv6 source prefix.";
    }
  }

  augment "/sav:sav/sav:sav-tables/sav:sav-table/"
        + "sav:active-sav-rule/sav:input" {
    when "derived-from-or-self(../sav:address-family, "
       + "'v6sav:ipv6')" {
      description
        "This augment is valid only for IPv6.";
    }
    description
      "This augment adds the input parameter of the
       'active-sav-rule' action.";
    leaf source-address {
      type inet:ipv6-address;
      description
        "IPv6 source address.";
    }
  }

  augment "/sav:sav/sav:sav-tables/sav:sav-table/"
        + "sav:active-sav-rule/sav:output/sav:sav-rule" {
    when "derived-from-or-self(../../sav:address-family, "
       + "'v6sav:ipv6')" {
      description
        "This augment is valid only for IPv6.";
    }
    description
      "This augment adds the source prefix to the reply of the
       'active-sav-rule' action.";
    leaf source-prefix {
      type inet:ipv6-prefix;
      description
        "IPv6 source prefix.";
    }
  }

  augment "/sav:sav/sav:static-savs" {
    description
      "This augment defines the 'static' pseudo-protocol
       with data specific to IPv6.";
    container ipv6 {
      description
        "Support for a 'static' pseudo-protocol instance
         consists of a list of SAV rules.";
      container sav-entry-limits {
        description
          "Specification limit of ipv6 SAV table.";
        uses limit-metadata;
      }
      list sav-rule {
        key "source-prefix";
        description
          "A list of static SAV rules.";
        leaf source-prefix {
          type inet:ipv6-prefix;
          mandatory true;
          description
            "IPv6 source prefix.";
        }
        leaf description {
          type string;
          description
            "Textual description of the SAV rule.";
        }
        container incoming-interfaces {
          description
            "Support for incoming interfaces.";
          list incoming-interface {
            key "name";
            description
              "Each entry contains the information of a
               incoming interface";
            leaf name {
              type if:interface-ref;
              description
                "The name of an incoming interface.";
            }
            leaf check-type {
              type identityref {
                base sav:sav-check-type;
              }
              description
                "The SAV check type of an incoming interface.";
            }
          }
        }
      }
    }
  }
}
