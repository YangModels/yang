module ietf-taps-api {
  yang-version 1.1;

  namespace "urn:ietf:params:xml:ns:yang:ietf-taps-api";
  prefix "taps";

  import ietf-inet-types {
      prefix "inet";
      reference "RFC 6991 Section 4";
  }

  import ietf-interfaces {
      prefix "if";
      reference "RFC 8343 Section 5";
  }

  import iana-if-type {
      prefix "ianaift";
      reference "RFC 7224 Section 2";
  }

  organization "IETF";

  contact
      "Author:   Jake Holland
                 <mailto:jholland@akamai.com>
      ";

  description
      "This module contains the definition for the TAPS
       interface.

       Copyright (c) 2018 IETF Trust and the persons identified as
       authors of the code.  All rights reserved.

       Redistribution and use in source and binary forms, with or
       without modification, is permitted pursuant to, and subject
       to the license terms contained in, the Simplified BSD License
       set forth in Section 4.c of the IETF Trust's Legal Provisions
       Relating to IETF Documents
       (http://trustee.ietf.org/license-info).

       This version of this YANG module is part of
       draft-jholland-taps-api-yang,
       see the internet draft itself for full legal notices.";

  revision 2019-03-09 {
      description "Draft -01 revision.";
      reference
        "draft-jholland-taps-api-yang";
  }

  typedef preference-level {
    type enumeration {
      enum require {
        description
          "select only options providing this property, fail otherwise";
      }
      enum prefer {
        description
          "prefer options providing this property, proceed otherwise";
      }
      enum ignore {
        description
          "cancel any system default preference for this property";
      }
      enum avoid {
        description
          "prefer options not providing the property,
           proceed otherwise";
      }
      enum prohibit {
        description
          "select only options not proiding ths property, fail
           otherwise";
      }
    }
    description
      "This value represents the preference level of a property.";
  }

  identity connection-config-property {
    description "Base identity for configuring connections";
  }

  identity transport-property {
    base connection-config-property;
    description "Base identity for transport properties";
  }

  identity local-endpoint-property {
    base connection-config-property;
    description "Base identity for local endpoint properties";
  }

  identity local-address {
    base local-endpoint-property;
    description
      "Identity for the address of a local endpoint";
  }

  identity local-port {
    base local-endpoint-property;
    description
      "Identity for the port of a local endpoint";
  }

  identity remote-endpoint-property {
    base connection-config-property;
    description "Base identity for remote endpoint properties";
  }

  identity remote-host {
    base remote-endpoint-property;
    description
      "Identity for the host of a remote endpoint";
  }

  identity remote-port {
    base remote-endpoint-property;
    description
      "Identity for the port of a remote endpoint";
  }

  identity reliable {
    base transport-property;
    description "Reliable Transport";
  }
  identity per-message-reliable {
    base transport-property;
    description "Per-message Reliable Transport";
  }
  identity preserve-order {
    base transport-property;
    description "Per-message Reliable Transport";
  }
  identity zero-rtt-establishment {
    base transport-property;
    description
      "Use 0-RTT session establishment with an idempotent Message";
  }
  identity multistream-connections-in-group {
    base transport-property;
    description "Multistream Connections in Group";
  }
  identity control-checksum-coverage {
    base transport-property;
    description "Control checksum coverage on sending or receiving
        TBD: draft-ietf-taps-interface-02#section-5.2.6 seems to
             indicate some parameters are in order with this type,
             not sure exactly what it should look like? Use case?";
  }
  identity congestion-control {
    base transport-property;
    description "Congestion control";
  }
  identity local-interface-selection {
    base transport-property;
    description "Interface Instance or Type
        TBD: should this be a local-endpoint-property?";
  }
  identity provisioning-domain {
    base transport-property;
    description "Base for provisioning domain.
        TBD: add relevant provisioning domain types";
    reference "RFC 7556: Multiple Provisioning Domain Architecture";
  }

  identity transport-protocol {
    base transport-property;
    description "Identity for a transport selection.
      TBD: finish the rest of the protocols in
           https://tools.ietf.org/html/rfc8095#section-3.1
           maybe add quic, maybe use as external augment demo.
      note: this isn't in taps-interface, but is available in
            e.g. NEAT-project/neat/examples/client.c";
    reference "Section 3 of RFC 8095: Existing Transport Protocols";
  }

  identity tcp {
    base transport-protocol;
    description "Identity for TCP";
    reference "RFC 793: Transmission Control Protocol.
      See also RFC 7414: A Roadmap for TCP Specification Documents.";
  }
  identity mptcp {
    base transport-protocol;
    description "Identity for MPTCP";
    reference
      "RFC 6824: TCP Extensions for Multipath Operation";
  }
  identity udp {
    base transport-protocol;
    description "Identity for UDP";
    reference "TBD";
  }
  identity udp-lite {
    base transport-protocol;
    description "Identity for UDP-Lite";
    reference "TBD";
  }
  identity sctp {
    base transport-protocol;
    description "Identity for SCTP";
    reference "TBD";
  }
  identity dccp {
    base transport-protocol;
    description "Identity for DCCP";
    reference "TBD";
  }
  identity tls {
    base transport-protocol;
    description "Identity for TLS";
    reference "TBD";
  }
  identity rtp {
    base transport-protocol;
    description "Identity for RTP";
    reference "TBD";
  }
  identity http {
    base transport-protocol;
    description "Identity for HTTP";
    reference "TBD";
  }
  identity flute {
    base transport-protocol;
    description "Identity for FLUTE";
    reference "TBD";
  }
  identity norm {
    base transport-protocol;
    description "Identity for NORM";
    reference "TBD";
  }
  identity icmp {
    base transport-protocol;
    description "Identity for ICMP";
    reference "TBD";
  }

  identity security-algorithm {
    description "Base identity for security algorithms.";
  }

  identity cipher-suite {
    base security-algorithm;
    description "Base identity for security cipher suites.";
  }

  identity signature-algorithm {
    base security-algorithm;
    description "Base identity for security signature algorithms.";
  }

  identity ed25519 {
    base signature-algorithm;
    description "Identity for ED25519";
  }

  identity TLS_ECDHE_ECDSA_WITH_CHACHA20_POLY1305_SHA256 {
    base cipher-suite;
    description "Identity for ECDHE ECDSA with ChaCha20, Poly1305,
        and SHA256";
  }

  grouping security-credentials {
    description "security credentials";

    leaf identity {
      type string;
      description "identity for security credentials";
    }

    leaf algorithm {
      type identityref {
        base security-algorithm;
      }
      description "security algorithm for credentials";
    }

    leaf pre-shared-key {
      type string;
      description "pre-shared key for security credentials";
    }

    leaf private-key {
      type string;
      description "private key for security credentials";
    }

    leaf private-key-callback-handle {
      type string;
      description "private key callback handle for
        externally managed security credentials";
    }

    leaf public-key {
      type string;
      description "public key for security credentials";
    }
  }

  container preconnection {
    /* config true; */
    description "preconnection config for a taps connection";
    list properties {
      key "type preference";
      description "list of transport property constraints.";

      leaf type {
        type identityref {
          base "connection-config-property";
        }
        description "type of the property";
      }
      leaf preference {
        type preference-level;
        /* TBD: would be nice if i could set default and have
           less verbose config file.
           default require; */
        description "preference level for the property";
      }

      leaf-list iftype {
        when "derived-from-or-self(../type,
            'taps:local-interface-selection')";
        type identityref {
          base "ianaift:iana-interface-type";
        }
        description "interface type constraint for local
          interface selection";
        reference "RFC 7224 Section 2";
      }

      leaf-list ifref {
        when "derived-from-or-self(../type,
            'taps:local-interface-selection')";
        type if:interface-ref {
          require-instance false;
        }
        description "specific interface constraint for local
          interface selection.";
      }

      leaf-list address {
        when "derived-from-or-self(../type,
            'taps:local-address')";
        type inet:ip-address;
        description "ip address of local endpoint";
      }

      leaf-list port {
        when "derived-from-or-self(../type,
            'taps:local-port') or
              derived-from-or-self(../type,
            'taps:remote-port')";
        type inet:port-number;
        description "port value of an endpoint port";
      }

      leaf-list host {
        when "derived-from-or-self(../type,
            'taps:remote-host')";
        type inet:host;
        description "host value of a remote endpoint";
      }
    }

    container security {
      description "Security properties for the connection";
      list credentials {
        key "identity algorithm";

        uses security-credentials;
        description "security credentials";
      }

      leaf session-cache-capacity {
        type uint32;
        description "Max number of cache elements";
      }
      leaf session-cache-lifetime {
        type uint32;
        description "Number of seconds of session cache lifetime";
      }
    }
  }
}
