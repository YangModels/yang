module ietf-te-service-mapping-types {

       namespace "urn:ietf:params:xml:ns:yang:ietf-te-service-mapping-types";

       prefix "tsm";

       import ietf-te-types {
           prefix "te-types";
       }

       import ietf-network {
           prefix "nw";
       }

       import ietf-te {
           prefix "te";
       }

       import ietf-vn {
           prefix "vn";
       }

       organization
           "IETF Traffic Engineering Architecture and Signaling (TEAS)
           Working Group";

       contact
           "Editor: Young Lee <leeyoung@huawei.com>
                    Dhruv Dhody <dhruv.ietf@gmail.com>
                   Qin Wu <bill.wu@huawei.com>";
       description
           "This module contains a YANG module for TE & Service mapping
         parameters and policies as a common grouping applicable to
         variuous service models (e.g., L1CSM, L2SM, L3SM, etc.)";

       revision 2018-12-30 {
           description
               "initial version.";
           reference
               "TBD";
       }

       /*
        * Identity for map-type
        */
      identity map-type {
         description
         "Base identity from which specific map types are
          derived.";
      }

      identity new {
         base map-type;
         description
           "The new VN/tunnels are binded to the service.";
      }
      identity detnet-hard-isolation {
         base new;
         description
           "Hard isolation with deterministic characteristics.";
      }

      identity hard-isolation {
         base new;
         description
           "Hard isolation.";
      }

      identity soft-isolation {
         base new;
         description
           "Soft-isolation.";
      }

      identity select {
         base map-type;
         description
           "The VPN service selects an existing tunnel with no
            modification.";
      }

      identity modify {
         base map-type;
         description
           "The VPN service selects an existing tunnel and allows
            to modify the properties of the tunnel (e.g., b/w)";
      }

       /*
        * Identity for availability-type
        */
      identity availability-type {
         description
           "Base identity from which specific map types are
            derived.";
      }

      identity level-1 {
         base availability-type;
         description
           "level 1: 99.9999%";
      }

      identity level-2 {
         base availability-type;
         description
           "level 2: 99.999%";
      }

      identity level-3 {
         base availability-type;
         description
           "level 3: 99.99%";
      }

      identity level-4 {
         base availability-type;
         description
           "level 4: 99.9%";
      }

      identity level-5 {
         base availability-type;
         description
           "level 5: 99%";
      }

       /*
        * Groupings
        */

      grouping te-ref {
         description
           "The reference to TE.";
         choice te {
            description
               "The TE";
               case actn-vn {
                   leaf actn-vn-ref {
                       type leafref {
                           path "/vn:actn/vn:vn/vn:vn-list/vn:vn-id";
                       }
                       description
                           "The reference to ACTN VN";
                   }
               }
               case te-topo {
                  leaf vn-topology-id{
                      type te-types:te-topology-id;
                      description
                          "An identifier to the TE Topology Model
                           where the abstract nodes and links of
                           the Topology can be found for Type 2
                           VNS";
                  }
                  leaf abstract-node {
                    type leafref {
                      path "/nw:networks/nw:network/nw:node/"
                      + "nw:node-id";
                    }
                    description
                      "a reference to the abstract node in TE
                      Topology";
                  }
               }
               case te-tunnel {
                   leaf-list te-tunnel-list {
                       type te:tunnel-ref;
                       description
                           "Reference to TE Tunnels";
                   }

               }

           }

       }

       grouping te-endpoint-ref {
           description
              "The reference to TE endpoints.";
           choice te {
              description
                 "The TE";
              case actn-vn {
                 leaf actn-vn-ref {
                       type leafref {
                           path "/vn:actn/vn:ap/vn:access-point-list"
                           + "/vn:access-point-id";
                       }
                       description
                           "The reference to ACTN VN";
                   }
              }
              case te {
                 leaf ltp {
                      type te-types:te-tp-id;
                      description
                          "Reference LTP in the TE-topology";
                 }
              }
           }
       }

       grouping te-mapping {
           description
               "Mapping between Services and TE";
           container te-mapping {
               description
                   "Mapping between Services and TE";
               leaf map-type {
                  type identityref {
          base map-type;
             }
                  description
                    "Isolation Requirements, Tunnel Bind or
                     Tunnel Selection";
               }
               leaf availability-type {
                  type identityref {
                    base availability-type;
                  }
                  description
                    "Availability Requirement for the Service";
               }
               uses te-ref;
           }
       }

}
