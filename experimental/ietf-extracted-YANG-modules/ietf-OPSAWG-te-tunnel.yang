module ietf-OPSAWG-te-tunnel{
    namespace "urn:ietf:params:xml:ns:yang:ietf-OPSAWG-te-tunnel";
    prefix "te-tunnel";

    import ietf-yang-types {prefix yang;}
    import ietf-inet-types {prefix inet;}
    import ietf-OPSAWG-ute-tunnel{prefix ute-tunnel;}
    import ietf-pce-type {prefix pce-type;}

    organization "IETF OPSA Working Group";
    contact
    "Editor:   Robin Li
                <mailto:lizhenbin@huawei.com>";
    description "Net MPLS TE tunnel";
    revision 2016-01-01{
        description "Initial version";
        reference "";
    }

  /*****************************************************************
  * enumeration
  *****************************************************************/
    typedef  revertive-type{
        type enumeration{
            enum revertive{
                value 0;
                description "hot-standby revertive";
            }
            enum no-revertive{
                value 1;
                description "hot-standby no-revertive";
            }
        }
    }

    typedef bandwidth-mode{
        type enumeration{
            enum original-bandwidth{
                value 0;
                description "hotstandby lsp's bandwidth is same with the primary lsp";
            }
            enum dynamic-bandwidth{
                value 1;
                description "hotstandby lsp use 0 bandwidth";
            }
        }
    }

    typedef sr-path-type{
        type enumeration{
            enum adjacency-sid{
                value 1;
            }
            enum node-sid{
                value 2;
            }
            /*
            enum hybrid{
                value 3;
            }
            */
        }
    }

    typedef sid-type {
        type enumeration {
            enum "ipv4-node" {
                value 1;
                description "IPv4 node sid";
            }
            /*
            enum "ipv6-node" {
                value 2;
                description "IPv6 node sid";
            }
            */
            enum "ipv4-adjacency" {
                value 3;
                description "IPv4 adjacency sid";
            }
            /*
            enum "ipv6-adjacency" {
                value 4;
                description "IPv6 adjacency sid";
            }
            */
            /* value 5 is remained for unnumbered adjacency */
            enum "adhere-label" {
                value 6;
                description "IPv6 adjacency sid";
            }
        }
      }

    typedef protocol-type{
        type enumeration{
            enum isis{
                value 1;
            }
            enum ospf{
                value 2;
            }
        }
    }

      typedef igp-metric-type{
        type enumeration{
            enum relative{
                value 1;
            }
            enum absolute{
                value 2;
            }
        }
    }

    typedef propagate-mode{
        type enumeration{
            enum shortcut{
                value 1;
            }
            enum forward-adjacency{
                value 2;
            }
        }
    }

 /*****************************************************************
  * Groupings
  *****************************************************************/
    grouping tunnel-constraint-cfg{

            leaf setup-priority{
                type uint8 {
                    range "0 .. 7";
                }
                default 7;
            }
            leaf holdup-priority{
                type uint8 {
                    range "0 .. 7";
                }
                default 7;
            }
            leaf bandwidth{
                type uint32 {
                    range "0..4000000000";
                }
                default 0;
            }
            leaf oper-bandwidth{
                type uint32 {
                    range "0..4000000000";
                }
                default 0;
            }
            list path-options{
                key "option-number";
                leaf option-number{
                    type uint16{
                        range "1 | 65535";
                    }
                    description "path option number , only support  1 and 65535, 65535 is for the best-effort path";
                }
                list path-constraints{
                    key "path-role";
                    leaf path-role{
                        type pce-type:lsp-role;
                    }
                    leaf latency{
                        type uint32 {
                            range "0..60000000";
                        }
                        default 0;
                    }
                    leaf hop-limit{
                        type uint16 {
                            range "1..32";
                        }
                        default 32;
                    }
                    leaf include-affinity-any{
                        type pce-type:affinity;
                    }
                    leaf include-affinity-all{
                        type pce-type:affinity;
                                                description "include-affinity-all";
                    }
                    leaf exclude-affinity{
                        type pce-type:affinity;
                    }
                    leaf te-attribute-ignore{
                        type bits {
                            bit ignore-affinity {
                                position 0;
                            }
                        }
                    }
                    container explicit-path-hops{
                        list explicit-path-hop{
                            key "hop-index";
                            leaf hop-index{
                                type uint32{
                                    range 0..63;
                                }
                            }
                            leaf ne-id{
                                type yang:uuid;
                            }
                            leaf ltp-id{
                                type yang:uuid;
                            }
                            leaf ip-address{
                                type "inet:ipv4-address";
                            }
                            leaf hop-inc-type{
                                type pce-type:hop-inc-type;
                            }
                            leaf hop-type{
                                type pce-type:hop-type;
                            }
                        }
                    }
                }
            }
        }

    grouping hot-standby{
        leaf revertive{
            type revertive-type;
            default revertive;
        }
        leaf bandwidth-mode{
            type bandwidth-mode;
            default original-bandwidth;
        }
        leaf wtr{
            type uint32 {
                range "0..2592000";
            }
            default 10;
            description "wait to restore";
        }
    }
/*************************************************************
  * augment extension
  **************************************************************/
    augment "/ute-tunnel:ute-tunnel-cfg" {
        container global-cfg {
            leaf bandwidth-threshold {
                description "TE tunel max bandwidth of network, only effective to service-driven tunnel";
                type uint32 {
                    range "0..4000000000";
                }
                default 500000;
            }
        }
    }
    augment "/ute-tunnel:ute-tunnel-cfg/ute-tunnel:p2p-tunnel/ute-tunnel:tunnels/ute-tunnel:tunnel"{
        when "ute-tunnel:tunnel-type='te'";

        leaf path-setup-type{
            type pce-type:path-setup-type;
            default rsvp-te;
        }
        leaf sr-path-type {
                description "The SR-TE tunnel path's type";
            type sr-path-type;
            default adjacency-sid;
        }

        leaf is-bypass-tunnel{
            must "path-setup-type = 'pce-type:rsvp-te'";
            type boolean;
            default false;
        }

        container bypass-tunnel{
            must "path-setup-type = 'pce-type:rsvp-te'";
            when "is-bypass-tunnel='true'";
            container protect-interface{
                leaf ltp-id{
                    type yang:uuid;
                }
            }
        }

        leaf hot-standby-enable {
            type "boolean";
            default false;
            description "hot-standby protect capability";
        }

        container tunnel-constraint{
            uses tunnel-constraint-cfg;
        }

        container protect-policy{
            when "is-bypass-tunnel='false'";

            container hot-standby{
                uses hot-standby;
            }
            container frr{
                must "path-setup-type = 'pce-type:rsvp-te'";

                leaf fast-reroute{
                    type boolean;
                }
                container bypass-attributes{
                    leaf setup-priority{
                        type uint8 {
                            range "0 .. 7";
                        }
                        default 7;
                    }
                    leaf holdup-priority{
                        type uint8 {
                            range "0 .. 7";
                        }
                        default 7;
                    }
                    leaf bandwidth{
                        type uint32 {
                            range "0..4000000000";
                        }
                        default 0;
                    }
                    leaf include-affinity-any{
                        type pce-type:affinity;
                    }
                    leaf include-affinity-all{
                            type pce-type:affinity;
                    }
                    leaf exclude-affinity{
                        type pce-type:affinity;
                    }
                    leaf te-attribute-ignore{
                        type bits {
                            bit ignore-affinity {
                                position 0;
                            }
                        }
                    }
                }
            }
        }

        container tunnel-service{
            leaf service-class{
                type bits{
                    bit be{
                        position 0;
                    }
                    bit af1{
                        position 1;
                    }
                    bit af2{
                        position 2;
                    }
                    bit af3{
                        position 3;
                    }
                    bit af4{
                        position 4;
                    }
                    bit ef{
                        position 5;
                    }
                    bit cs6{
                        position 6;
                    }
                    bit cs7{
                        position 7;
                    }
                    bit default{
                        position 8;
                    }
                }
            }
            leaf outbound-limit{
                type boolean;
                default false;
            }
            leaf reserved-for-binding{
                type boolean;
            }
            leaf statistic-enable{
                type boolean;
                default false;
                description "traffic statistic enable";
            }
            container igp-capabilities {
            description "The IGP capabilities of this tunnel interface";
                list igp-instance {
                description "The key of this IGP instance";
                    key "index";
                    leaf index{
                        type uint32;
                        description "The index of this object";
                    }
                    leaf protocol-type{
                        type protocol-type;
                        description "The protocol type of this tunnel interface";
                        mandatory true;
                    }
                    leaf igp-instance-id{
                        type uint32{
                            range 1..4294967295;
                        }
                        description "The id of this protocol instance";
                        default 1;
                    }
                    leaf ospf-area-id{
                        when protocol-type=ospf;
                        type uint32{
                            range 0..4294967295;
                        }
                        description "The id of OSPF area";
                    }
                    }
                leaf propagate-mode{
                    type propagate-mode;
                    description "The propagate mode";
                }
                    leaf advertise-hold-time {
                    when propagate-mode=forward-adjacency;
                           type uint32{
                        range 0..4294967295;
                    }
                    description "The time value of advertise hold timer when FA is enabled";
                       }
                leaf igp-metric-type{
                    type igp-metric-type;
                    description "The igp metric type";
                }
                       leaf relative-metric-value {
                    when igp-metric-type=relative;
                           type int32{
                        range -10..10;
                    }
                    description "The igp metric value when type is relative";
                       }
                       leaf absolute-metric-value {
                    when igp-metric-type=absolute;
                        type uint32{
                        range 1..65535;
                    }
                    description "The igp metric value when type is absolute";
                }
                }
        }
    }

    augment "/ute-tunnel:ute-tunnel-oper/ute-tunnel:p2p-tunnel/ute-tunnel:tunnels/ute-tunnel:tunnel" {
        when "ute-tunnel:tunnel-type='te'";
        leaf path-setup-type{
            config "false";
            type pce-type:path-setup-type;
            default rsvp-te;
        }
        leaf co-route-name{
            type string {
                length "1..64";
            }
        }
        leaf trigger-source{
            type pce-type:trigger-type;
        }
        container path-lists{
            list path-list{
                key "option-number";
                leaf option-number{
                    type uint16;
                    description "path option number , only support  1 and 65535, 65535 is for the best-effort path";
                }
                list paths{
                    key "path-role lsp-id";
                    leaf path-role{
                        type pce-type:lsp-role;
                    }
                    leaf lsp-id{
                        type uint32{
                            range 0..4294967295;
                        }
                    }
                    leaf active {
                        type boolean;
                    }
                                        uses path-constraint-inuse;
                    container hops{
                        list hop{
                            key "hop-index";
                            leaf hop-index{
                                type uint32{
                                    range 0..63;
                                }
                            }
                            leaf ne-id{
                                type yang:uuid;
                            }
                            leaf ltp-id{
                                type yang:uuid;
                            }
                            leaf ip-address{
                                type inet:ipv4-address;
                            }
                            leaf hop-inc-type{
                                type pce-type:hop-inc-type;
                            }
                        }
                    }
                    container sr-label-stack{
                    description "The label stack of this SR-TE tunnel";
                        list sr-label{
                        description "The SID information of this hop instance";
                            key "hop-index";
                            leaf hop-index{
                                type uint32{
                                    range 0..63;
                                }
                                description "The index of this hop instance";
                            }
                            leaf sid {
                                type uint32;
                                description "The SID of this hop instance";
                            }
                            leaf sid-type {
                                type sid-type;
                                description "The type of this SID";
                            }
                            container ipv4-node-info {
                            description "The information of this IPv4 node SID";
                                when sid-type=ipv4-node;
                                    leaf node-address {
                                        type inet:ipv4-address;
                                description "The address of this IPv4 node SID";
                                    }
                                }
                                container ipv6-node-info {
                            description "The information of this IPv6 node SID";
                                when sid-type=ipv6-node;
                                    leaf node-address {
                                        type inet:ipv6-address;
                                description "The address of this IPv6 node SID";
                                    }
                                }
                                container ipv4-adjacency-info {
                            description "The information of this IPv4 adj SID";
                                when sid-type=ipv4-adjacency;
                                    leaf local-address {
                                        type inet:ipv4-address;
                                description "The local address of this IPv4 adj SID";
                                    }
                                    leaf remote-address {
                                        type inet:ipv4-address;
                                description "The remote address of this IPv4 adj SID";
                                    }
                                }
                                container ipv6-adjacency-info {
                            description "The information of this IPv6 node SID";
                                when sid-type=ipv6-adjacency;
                                    leaf local-address {
                                        type inet:ipv6-address;
                                description "The local address of this IPv6 adj SID";
                                    }
                                    leaf remote-address {
                                        type inet:ipv6-address;
                                description "The remote address of this IPv6 adj SID";
                                    }
                                }
                                container lsr-id {
                            description "The information of this adhere node";
                                when sid-type=adhere-label;
                                    leaf node-lsr-id {
                                        type inet:ip-address;
                                description "The LSR-ID address of this adhere node";
                                    }
                                }
                        }
                    }
                }
            }
        }
    }

    grouping te-tunnel-brief-grouping{
            leaf total-record-num{
                type uint32;
            }
            list te-tunnel{
                leaf tunnel-name{
                    type pce-type:tunnel-name;
                    description "Tunnel Name";
                }
                leaf tunnel-type{
                    type identityref{
                        base ute-tunnel:tunl-type;
                    }
                }
                leaf user-label{
                    type string {
                        length "0..242";
                    }
                }
                container source{
                    uses ute-tunnel:src-or-dst;
                }
                container destination{
                    uses ute-tunnel:src-or-dst;
                }
                leaf bandwidth{
                    type uint32;
                }
                leaf min-latency{
                    type uint32 {
                        range "0..60000000";
                    }
                    description "Min latency of configuration";
                }
            }
    }
    grouping path-constraint-inuse{
                leaf bandwidth{
                        type pce-type:bandwidth;
                        description "bandwidth";
                }
                leaf request-latency{
                                        type uint32{
                        range 0..4294967295;
                    }
                    description "latency";
                                }
                                leaf path-latency{
                                        type uint32{
                        range 0..4294967295;
                    }
                                }
                                leaf path-metric{
                                    type uint32;
                    description "The metric value of this path";
                                }
                                leaf include-affinity-any{
                    type pce-type:affinity;
                }
                leaf include-affinity-all{
                    type pce-type:affinity;
                                        description "include-affinity-all";
                }
                leaf exclude-affinity{
                    type pce-type:affinity;
                }
                leaf setup-priority{
                        type uint8 {
                                 range "0 .. 7";
                        }
                }
                leaf holdup-priority{
                       type uint8 {
                                range "0 .. 7";
                        }
                }
    }
  /*************************************************************
  * rpc
  **************************************************************/
    rpc query-te-tunnels-nbi{
        description "Tunnels generated through NBI, E2E sync and adopted, state is up";
        input{
            leaf src-ne-id{
                type yang:uuid;
                mandatory true;
            }
            leaf dst-ne-id{
                type yang:uuid;
                mandatory true;
            }
            leaf tunnel-name{
                type pce-type:tunnel-name;
                description "Tunnel Name";
                mandatory false;
            }
        }
        output{
            container te-tunnel-brief{
            uses te-tunnel-brief-grouping;
            }
        }
    }

  /***************************************************************
  * notification
  ***************************************************************/
    notification tunnel-besteffort{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel downgrades to besteffort";
    }
    notification tunnel-besteffort-clear{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel upgrades to main LSP";
    }
    notification tunnel-unprotected{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel downgrades to non protection";
    }
    notification tunnel-unprotected-clear{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel upgrades to protection";
    }
    notification tunnel-overlap{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel's primary and secondary LSPs are overlap";
    }
    notification tunnel-overlap-clear{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel's primary and secondary LSPs completely separate";
    }
    notification tunnel-constraint-unsatisfied{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel new constraint is unsatisfied";
    }
    notification tunnel-constraint-unsatisfied-clear{
        leaf tunnel-name{
            type leafref{
                 path "/ute-tunnel:ute-tunnel-oper/ute-tunnel:p2p-tunnel/ute-tunnel:tunnels/ute-tunnel:tunnel/ute-tunnel:tunnel-name";
             }
             description "Tunnel Name";
        }
        description "Tunnel new constraint is satisfied";
    }
}
