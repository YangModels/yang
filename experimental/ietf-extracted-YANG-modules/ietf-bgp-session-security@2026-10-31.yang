module ietf-bgp-session-security {
  yang-version 1.1;
  namespace "urn:ietf:params:xml:ns:yang:ietf-bgp-session-security";
  prefix bss;

  import ietf-key-chain {
    prefix key-chain;
    reference
      "RFC 8177: YANG Data Model for Key Chains.";
  }
  import ietf-yang-semver {
    prefix ysv;
    reference
      "I-D.ietf-netmod-yang-semver: YANG Semantic Versioning";
  }
  organization
    "IETF IDR Working Group";
  contact
    "WG Web:   <http://datatracker.ietf.org/wg/idr>
     WG List:  <idr@ietf.org>

     Authors: Mahesh Jethanandani (mjethanandani at gmail.com),
              Keyur Patel (keyur at arrcus.com),
              Susan Hares (shares at ndzh.com),
              Jeffrey Haas (jeffrey.haas at hpe.com).";

  description
    "This module contains groupings particular to BGP session
     security.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-10-31 {
    description
      "Initial Version";
    ysv:version 0.0.9;
    reference
      "RFC XXXX: YANG Model for Border Gateway Protocol (BGP-4).";
  }

  /*
   * Features.
   */

  feature bgp-session-security-tcp-ao {
    description
      "Support for the TCP Authentication Option for neighbors.";
    reference
      "RFC 5925: The TCP Authentication Option.";
  }

  feature bgp-session-security-tcp-md5 {
    description
      "Support for TCP-MD5 for neighbors. Note that this option has
       been obsoleted by RFC 5925 but is included for backward
       compatibility for legacy BGP implementations.";
    reference
      "RFC 5925: The TCP Authentication Option.";
  }

  feature bgp-session-security-ipsec {
    description
      "Support for IPsec security for neighbors.";
    reference
      "RFC 4301: Security Architecture for the Internet Protocol.";
  }

  grouping bgp-session-security {
    description
      "Configuration parameters relating to BGP session security.";

    container secure-session {
      must "enabled = 'false' or " +
           "(enabled = 'true' and options)" {
        error-message "When secure-session is enabled " +
          "secure-session options MUST be set";
      }
      description
        "Container for describing how a particular BGP session
         is to be secured.";

      leaf enabled {
        type boolean;
        default "false";
        description
          "When set to true, session is secured with the
           configured options.";
      }

      container options {
        description
          "Options for securing the BGP session.";
        choice option {
          case ao {
            if-feature "bgp-session-security-tcp-ao";
            leaf ao-keychain {
              type key-chain:key-chain-ref;
              description
                "Reference to the key chain that will be used by this
                 model. Applicable for TCP-AO and TCP-MD5 only";
              reference
                "RFC 8177: YANG Data Model for Key Chains.";
            }
            description
              "Uses TCP-AO to secure the session. Parameters for
               those are defined as a grouping in the TCP YANG
               model.";
            reference
              "RFC 5925: The TCP Authentication Option.";
          }

          case md5 {
            if-feature "bgp-session-security-tcp-md5";
            leaf md5-keychain {
              type key-chain:key-chain-ref;
              description
                "Reference to the key chain that will be used by this
                 model. Applicable for TCP-AO and TCP-MD5 only";
              reference
                "RFC 8177: YANG Data Model for Key Chains.";
            }
            description
              "Uses TCP-MD5 to secure the session. Parameters for
               those are defined as a grouping in the TCP YANG
               model.";
            reference
              "RFC 5925: The TCP Authentication Option.";
          }

          case ipsec {
            if-feature "bgp-session-security-ipsec";
            leaf sa {
              type string;
              description
                "Security Association (SA) name.";
            }
            description
              "Currently, the IPsec/IKE YANG model has no
               grouping defined that this model can use. When
               such a grouping is defined, this model can import
               the grouping to add the key parameters
               needed to kick of IKE.";
          }

          description
            "Choice of authentication options.";
        }
      }
    }
  }
}
