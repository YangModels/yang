module ietf-dtnma-agent-acl {
  yang-version 1.1;
  namespace "ari://ietf/dtnma-agent-acl/";
  prefix acl;

  import ietf-amm {
    prefix amm;
  }
  import ietf-dtnma-agent {
    prefix da;
  }
  import ietf-network-base {
    prefix network-base;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module implements the DTN Management Architecture (DTNMA)
     Agent Access Control List (ACL) functionality.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2025-07-03 {
    description
      "Updated for latest ADM document.";
    reference
      "draft-ietf-dtn-adm-yang";
  }
  amm:enum 2;

  // Common types in this model
  amm:typedef entry-id {
    amm:enum 2;
    description
      "The identifier for an entry in any access control table.";
    amm:type "/ARITYPE/UINT";
  }
  amm:typedef optional-entry-id {
    amm:enum 3;
    description
      "An optional entry identifier (or a null value).";
    amm:union {
      amm:type "./TYPEDEF/entry-id";
      amm:type "/ARITYPE/null";
    }
  }

  // Atomic permission objects
  amm:ident permission {
    amm:enum 0;
    description
      "The base IDENT for objects usable as permissions in the
       access control table.
       Derived objects MUST define the specific conditions in which
       the permission is exercised.
       Derived objects MAY be parameterized as needed to control
       specific access granted by each permission.
       This object itself is abstract and provides not specific
       permission.";
    amm:abstract true;
  }
  amm:typedef permission-list {
    amm:enum 0;
    description
      "A list of permission object (IDENT) references.";
    amm:ulist {
      amm:type "/aritype/ident" {
        amm:base "./ident/permission";
      }
    }
  }

  // built-in permissions
  amm:ident execute {
    amm:enum 10;
    description
      "Permission to allow executing specific CTRL objects.
       This includes objects used directly as EXECSET targets,
       indirectly within macros, or as actions of TBR or SBR
       objects.";
    amm:base "./ident/permission";
  }
  amm:ident produce {
    amm:enum 11;
    description
      "Permission to allow producing values from CONST, VAR, or
       EDD objects.
       This includes production for use by reporting or evaluating
       procedures of the Agent.";
    amm:base "./ident/permission";
  }
  amm:ident modify-var {
    amm:enum 12;
    description
      "Permission to allow modifying state on VAR objects.";
    amm:base "./ident/permission";
  }
  amm:ident create-odm {
    amm:enum 13;
    description
      "Permission to allow creating a new ODM within an Agent.";
    amm:base "./ident/permission";
  }
  amm:ident delete-odm {
    amm:enum 14;
    description
      "Permission to allow deleting an ODM within an Agent.";
    amm:base "./ident/permission";
  }
  amm:ident create-object {
    amm:enum 15;
    description
      "Permission to allow creating a new object within an ODM.
       The permission itself does not restrict the type of object,
       but the access list can limit the item to specific object
       types and names.";
    amm:base "./ident/permission";
  }
  amm:ident delete-object {
    amm:enum 16;
    description
      "Permission to allow deleting an object within an ODM.
       The permission itself does not restrict the type of object,
       but the access list can limit the item to specific object
       types and names.";
    amm:base "./ident/permission";
  }

  // Default access permission
  amm:var default-access {
    amm:enum 1;
    description
      "The default permission for any object if no specific access
       are present in the <./EDD/access-list> table.";
    amm:type "./TYPEDEF/permission-list";
  }

  // Access control table and modifier controls
  amm:edd access-list {
    amm:enum 2;
    description
      "List the current group--object access.";
    amm:tblt {
      amm:key "access-id";
      amm:column access-id {
        description
          "A unique identifier for this access list item.";
        amm:type "./TYPEDEF/entry-id";
      }
      amm:column group-ids {
        description
          "A cross-reference to the groups getting access, or the
           empty list to match all groups.";
        amm:ulist {
          amm:type "./TYPEDEF/entry-id";
        }
      }
      amm:column objects {
        description
          "A pattern for objects being granted access, which may
           match all objects.";
        amm:type "//ietf/amm-base/typedef/ari-pattern";
      }
      amm:column permissions {
        description
          "Refernces to specific permissions being granted.
           Individual permission references MAY be parameterized
           as necessary.
           The absence of permissions does not grant any access.";
        amm:type "./TYPEDEF/permission-list";
      }
      amm:column added-at {
        description
          "Agent timestamp when this group was added.";
        amm:type "//ietf/amm-base/typedef/timestamp";
      }
      amm:column updated-at {
        description
          "Agent timestamp when this group was added or updated.";
        amm:type "//ietf/amm-base/typedef/timestamp";
      }
    }
  }
  amm:ctrl ensure-access {
    amm:enum 3;
    description
      "Ensures that an access control permission is set for the
       given group and ARI pattern.";
    amm:parameter access-id {
      description
        "A unique identifier for this access list item.";
      amm:type "./TYPEDEF/entry-id";
    }
    amm:parameter group-ids {
      description
        "Identify the groups being assigned the permission,
         or the empty list for all-groups.";
      amm:ulist {
        amm:type "./TYPEDEF/entry-id";
      }
    }
    amm:parameter objects {
      description
        "ARI pattern to determine which objects will be assigned
         the permissions.";
      amm:type "//ietf/amm-base/typedef/ari-pattern";
    }
    amm:parameter permissions {
      description
        "Permissions to grant to the associated group and objects";
      amm:type "./TYPEDEF/permission-list";
    }
  }
  amm:ctrl discard-access {
    amm:enum 4;
    description
      "Discard any access item with the given ID.";
    amm:parameter access-id {
      description
        "Uniquely identify the access";
      amm:type "./TYPEDEF/entry-id";
    }
  }

  //
  // Group management
  //
  amm:edd current-groups {
    amm:enum 3;
    description
      "Get the group IDs for the current execution context, which may
       incude the implicit Agent group ID zero.";
    amm:ulist {
      amm:type "./TYPEDEF/entry-id";
    }
  }
  amm:edd group-list {
    amm:enum 4;
    description
      "Get the defined access control groups.";
    amm:tblt {
      amm:key "group-id";
      amm:column group-id {
        description
          "The unique identifier for a group.
           The agent itself has implicit group ID zero which cannot
           be modified.";
        amm:type "./TYPEDEF/entry-id";
      }
      amm:column name {
        description
          "The human-friendly name of the group.";
        amm:type "//ietf/amm-base/typedef/id-text";
      }
      amm:column members {
        description
          "The list of members of the group, identified by matching
           transport endpoint.";
        amm:ulist {
          amm:type "//ietf/network-base/TYPEDEF/endpoint-pattern";
        }
      }
      amm:column added-at {
        description
          "Agent timestamp when this group was added.";
        amm:type "//ietf/amm-base/typedef/timestamp";
      }
      amm:column updated-at {
        description
          "Agent timestamp when this group was added or updated.";
        amm:type "//ietf/amm-base/typedef/timestamp";
      }
    }
  }
  amm:ctrl ensure-group {
    amm:enum 5;
    description
      "Ensure that after the control completes a group exists with
       the given information";
    amm:parameter group-id {
      description
        "Uniquely identify the group";
      amm:type "./TYPEDEF/entry-id";
    }
    amm:parameter name {
      description
        "Name of the group";
      amm:type "//ietf/amm-base/typedef/id-text";
    }
  }
  amm:ctrl ensure-group-members {
    amm:enum 7;
    description
      "Ensure that the membership of a group has a specific set of
       endpoint patterns.";
    amm:parameter group-id {
      description
        "Uniquely identify the group";
      amm:type "./TYPEDEF/entry-id";
    }
    amm:parameter members {
      amm:ulist {
        amm:type "//ietf/network-base/TYPEDEF/endpoint-pattern";
      }
    }
  }
  amm:ctrl discard-group {
    amm:enum 6;
    description
      "Discard any group with the given ID.";
    amm:parameter group-id {
      description
        "Uniquely identify the group";
      amm:type "./TYPEDEF/entry-id";
    }
  }
}
