module ietf-bfd-unsolicited {

  yang-version 1.1;

  namespace "urn:ietf:params:xml:ns:yang:ietf-bfd-unsolicited";
  prefix "bfd-unsol";

  // RFC Ed.: replace occurences of YYYY with actual RFC numbers
  // and remove this note

  import ietf-bfd-types {
    prefix "bfd-types";
    reference "RFC 9127: YANG Data Model for BFD";
  }

  import ietf-bfd {
    prefix "bfd";
    reference "RFC 9127: YANG Data Model for BFD";
  }

  import ietf-bfd-ip-sh {
    prefix "bfd-ip-sh";
    reference "RFC 9127: YANG Data Model for BFD";
  }

  import ietf-routing {
    prefix "rt";
    reference
      "RFC 8349: A YANG Data Model for Routing Management
       (NMDA version)";
  }

  organization "IETF BFD Working Group";

  contact
    "WG Web:   <https://tools.ietf.org/wg/bfd>
     WG List:  <rtg-bfd@ietf.org>

     Editors:  Enke Chen (enchen@paloaltonetworks.com),
               Naiming Shen (naiming@zededa.com),
               Robert Raszuk (robert@raszuk.net),
               Reshad Rahman (reshad@yahoo.com)";

  description
    "This module contains the YANG definition for BFD unsolicited
     as per RFC YYYY.

     Copyright (c) 2021 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC YYYY; see
     the RFC itself for full legal notices.";

  reference "RFC YYYY";

  revision 2021-10-24 {
    description "Initial revision.";
    reference "RFC YYYY: Unsolicited BFD for Sessionless Applications.";
  }

  /*
   * Feature definitions
   */
   feature unsolicited-params-global {
     description
       "This feature indicates that the server supports global
        parameters for unsolicited sessions.";
   }

  feature unsolicited-params-per-interface {
    description
      "This feature indicates that the server supports per-interface
       parameters for unsolicited sessions.";
  }

  /*
   * Type Definitions
   */
  typedef unsolicited-role {
    type enumeration {
      enum unsolicited-active {
        description "Active role";
      }
      enum unsolicited-passive {
        description "Passive role";
      }
    }
    description "Unsolicited role";
  }

  /*
   * Augments
   */
   augment "/rt:routing/rt:control-plane-protocols/"
         + "rt:control-plane-protocol/bfd:bfd/bfd-ip-sh:ip-sh" {
     description
       "Augmentation for BFD unsolicited parameters";
     container unsolicited {
       if-feature bfd-unsol:unsolicited-params-global;
       description
         "BFD unsolicited top level container";
       leaf enable {
         type boolean;
         default false;
         description
           "Enable BFD unsolicited globally for IP single-hop.";
       }
       uses bfd-types:base-cfg-parms;
     }
   }

   augment "/rt:routing/rt:control-plane-protocols/"
         + "rt:control-plane-protocol/bfd:bfd/bfd-ip-sh:ip-sh/"
         + "bfd-ip-sh:interfaces" {
     description
       "Augmentation for BFD unsolicited on IP single-hop interface";
     container unsolicited {
       if-feature bfd-unsol:unsolicited-params-per-interface;
       description
         "BFD IP single-hop interface unsolicited top level
          container";
       leaf enable {
         type boolean;
         default false;
         description "Enable BFD unsolicited on this interface.";
       }
       uses bfd-types:base-cfg-parms;
     }
   }

  augment "/rt:routing/rt:control-plane-protocols/"
        + "rt:control-plane-protocol/bfd:bfd/bfd-ip-sh:ip-sh/"
        + "bfd-ip-sh:sessions/bfd-ip-sh:session" {
    description
      "Augmentation for BFD unsolicited on IP single-hop session";
    container unsolicited {
      config false;
      description
        "BFD IP single-hop session unsolicited top level container";
      leaf role {
        type bfd-unsol:unsolicited-role;
        description "Role.";
      }
    }
  }
}
