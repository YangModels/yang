module ietf-nrp {
  yang-version 1.1;
  namespace "urn:ietf:params:xml:ns:yang:ietf-nrp";
  prefix nrp;

  import ietf-network {
    prefix nw;
    reference
      "RFC 8345: A YANG Data Model for Network Topologies,
                 Section 6.1";
  }
  import ietf-network-topology {
    prefix nt;
    reference
      "RFC 8345: A YANG Data Model for Network Topologies,
                 Section 6.2";
  }
  import ietf-routing-types {
    prefix rt-types;
    reference
      "RFC 8294: Common YANG Data Types for the Routing Area";
  }
  import ietf-vpn-common {
    prefix vpn-common;
    reference
      "RFC 9181: A Common YANG Data Model for Layer 2 and Layer 3
                 VPNs";
  }
  import ietf-te-packet-types {
    prefix te-packet-types;
    reference
      "RFC 8776: Traffic Engineering Common YANG Types";
  }
  import ietf-inet-types {
    prefix inet;
    reference
      "RFC 6991: Common YANG Data Types";
  }
  import ietf-access-control-list {
    prefix acl;
    reference
      "RFC 8519: YANG Data Model for Network Access Control Lists
                 (ACLs)";
  }
  import ietf-srv6-types {
    prefix srv6-types;
    reference
      "draft-ietf-spring-srv6-yang: YANG Data Model for SRv6 Base
       and Static";
  }
  import ietf-topology-filter {
    prefix topo-filt;
    reference
      "draft-bestbar-teas-yang-topology-filter: YANG Data Model
       for Topology Filter";
  }
  organization
    "IETF Traffic Engineering Architecture and Signaling (TEAS)
     Working Group";
  contact
    "WG Web:   <https://datatracker.ietf.org/wg/teas/>
     WG List:  <mailto:teas@ietf.org>

     Editor:   Bo Wu
            <mailto:lana.wubo@huawei.com>
     Editor:   Dhruv Dhody
            <mailto:dhruv.ietf@gmail.com>

     Editor:   Vishnu Pavan Beeram
               <mailto:vbeeram@juniper.net>

     Editor:   Tarek Saad
               <mailto:tsaad.net@gmail.com>

     Editor:   Shaofu Peng
               <mailto:peng.shaofu@zte.com.cn>";
  description
    "This YANG module defines a data model for
     Network Resource Partitions (NRPs) management.

     Copyright (c) 2025 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
        (https://trustee.ietf.org/license-info).

     This version of this YANG module is part of RFC XXXX
     (https://www.rfc-editor.org/info/rfcXXXX); see the RFC itself
     for full legal notices.";

  revision 2025-03-02 {
    description
      "Initial revision.";
    reference
      "RFC XXXX: YANG Data Models for Network Resource
                 Partitions (NRPs)";
  }

  /*
   * I D E N T I T I E S
   */

  identity nrp-partition-mode {
    description
      "Base identity for NRP partition type.";
  }

  identity control-plane-partition {
    base nrp-partition-mode;
    description
      "NRP control plane partition.";
  }

  identity data-plane-partition {
    base nrp-partition-mode;
    description
      "NRP data plane partition.";
  }

  identity hybrid-plane-partition {
    base nrp-partition-mode;
    description
      "Both control and data planes partitions of NRP.";
  }

  identity nrp-link-partition-type {
    description
      "Base identity for NRP interface partition type.";
  }

  identity virtual-sub-interface-partition {
    base nrp-link-partition-type;
    description
      "Identity for NRP virtual interface or sub-interface partition,
       e.g., FlexE.";
  }

  identity queue-partition {
    base nrp-link-partition-type;
    description
      "Identity for NRP queue partition type.";
  }

  /*
   * T Y P E D E F S
   */

  typedef acl-ref {
    type leafref {
      path "/acl:acls/acl:acl/acl:name";
    }
    description
      "Used to reference an ACL.";
  }

  typedef topo-filter-ref {
    type leafref {
      path "/nw:networks/topo-filt:topology-filters/"
         + "topo-filt:topology-filter/topo-filt:name";
    }
    description
      "This type is used to reference a Topology Filter.";
    reference
      "draft-bestbar-teas-yang-topology-filter: YANG Data Model
       for Topology Filter";
  }

  /*
   * Grouping - NRP Resource Reservation
   */

  grouping resource-reservation {
    description
      "Grouping for NRP resource reservation.";
    container resource-reservation {
      description
        "Container for NRP resource reservation.";
      choice max-bw-type {
        description
          "Choice of maximum bandwidth specification.";
        case bw-value {
          leaf maximum-bandwidth {
            type uint64;
            units "bits/second";
            description
              "The maximum bandwidth allocated to an NRP
               - specified as absolute value.";
          }
        }
        case bw-percentage {
          leaf maximum-bandwidth-percent {
            type rt-types:percentage;
            description
              "The maximum bandwidth allocated to an NRP
               - specified as percentage of link
               capacity.";
          }
        }
      }
    }
  }

  /*
   * Grouping - NRP Selector Identifier Configuration
   */

  grouping selector-id {
    description
      "Grouping for NRP selector identifier (NRP Selector ID)
       configuration.";
    container selector-id {
      description
        "Container for NRP selector ID.";
      container ipv4-derived {
        description
          "Container for IPv4 NRP selector ID.";
        leaf-list destination-prefix {
          type inet:ipv4-prefix;
          description
            "Any prefix from the specified set of IPv4
             destination prefixes can be the selector ID.";
        }
      }
      container ipv6 {
        description
          "Container for IPv6 NRP selector ID.";
        choice selector-type {
          description
            "Choices for IPv6 selector ID type.";
          case dedicated {
            leaf ipv6-hbh-eh {
              type uint32;
              description
                "The selector ID carried in Hop-by-Hop option of
                 IPv6 extension header.";
              reference
                "draft-ietf-6man-enhanced-vpn-vtn-id: Carrying
                 Network Resource (NRP) related Information in IPv6
                 Extension Header";
            }
          }
          case srv6-sid-derived {
            leaf-list srv6-sid {
              type srv6-types:srv6-sid;
              description
                "Any SID from the specified set of SRv6 SID can
                 be the NRP selector ID.";
              reference
                "draft-ietf-spring-sr-for-enhanced-vpn: Segment
                 Routing based Network Resource Partition (NRP) for
                 Enhanced VPN";
            }
          }
          case ipv6-destination-derived {
            leaf-list destination-prefix {
              type inet:ipv6-prefix;
              description
                "Any prefix from the specified set of IPv6
                 destination prefixes can be the NRP selector ID.";
            }
          }
        }
      }
      container mpls {
        description
          "Container for MPLS NRP selector ID. This is a placeholder
           for future updates based on the MPLS solutions.";
      }
      leaf-list acl-ref {
        type acl-ref;
        description
          "NRP selection is done based on the specified list of
           ACLs.";
        reference
          "RFC 8519: YANG Data Model for Network Access Control Lists
                     (ACLs)";
      }
    }
  }

  /*
   * Grouping - NRP QoS Per-Hop Behavior (PHB) profiles
   */

  grouping qos-profiles {
    description
      "Grouping for NRP QoS profiles.";
    container qos-profiles {
      description
        "Container for profiles.";
      list phb-profile-identifier {
        key "id";
        description
          "List of PHB profiles.";
        leaf id {
          type string;
          description
            "Uniquely identifies the PHB.
             The profile only has significance within the service
             provider's administrative domain";
        }
      }
    }
  }

  /*
   * Grouping - NRP QoS Per-Hop Behavior (PHB) profile
   */

  grouping qos-phb-profile {
    description
      "Grouping for NRP QoS Per-Hop Behavior (PHB) profile.";
    leaf phb-profile {
      type leafref {
        path "/nw:networks/nrp-policies/"
           + "qos-profiles/phb-profile-identifier/id";
      }
      description
        "PHB profile identifier, specifying the forwarding treatment
         of packets belonging to a specific NRP selector ID, such as
         bandwidth control, congestion control
         (e.g., Section 3.4 of [RFC3644]).
         The PHB may be standard PHB, such as Assured Forwarding (AF),
         Expedited Forwarding (EF), or a customized local policy,
         such as 'High', 'Low', 'Standard'.";
    }
  }

  /*
   * Grouping - NRP IGP congruent
   */

  grouping igp-congruent {
    description
      "Grouping for NRP IGP congruent attributes.";
    container igp-congruent {
      presence "Indicates NRP IGP congruency.";
      description
        "The presence of the container node describes NRP IGP
         congruent, which indicates that the NRP instance uses the
         same IGP topology with the specified 'multi-topology-id'
         and 'algo-id'. That is, the nodes and termination point of
         the NRP topology and the IGP topology are the same, while
         the link attributes of the NRP are different from those of
         the IGP.";
      leaf multi-topology-id {
        type uint32;
        description
          "Indicates the MT-id of the NRP IGP instance.";
        reference
          "RFC 5120:  M-ISIS: Multi Topology (MT) Routing in
           Intermediate System to Intermediate Systems (IS-ISs)
           RFC 4915:  Multi-Topology (MT) Routing in OSPF";
      }
      leaf algo-id {
        type uint32;
        description
          "Indicates the algo-id of the NRP IGP instance.";
        reference
          "RFC 9350: IGP Flexible Algorithm";
      }
      leaf sharing {
        type boolean;
        description
          "'true' if the NRP IGP instance can be shared with
           other NRPs;
           'false' if the NRP IGP instance is dedicated
           to this NRP.";
      }
    }
  }

  /*
   * Grouping - NRP Topology Filter
   */

  grouping topology-filter {
    description
      "Grouping for NRP filter topology.";
    container filters {
      description
        "Container for filters.";
      list filter {
        key "filter-ref";
        description
          "List of filters.";
        leaf filter-ref {
          type topo-filter-ref;
          description
            "Reference to a specific topology filter from the
             list of global topology filters.";
        }
        uses resource-reservation;
        uses selector-id;
        uses qos-phb-profile;
      }
    }
  }

  /*
   * Grouping - NRP Select Topology
   */

  grouping select-topology {
    description
      "NRP topology specified by selection.";
    container select {
      description
        "The container of NRP select topology.";
      list topology-group {
        key "group-id";
        description
          "List of groups for NRP topology elements (node or links)
           that share common attributes.";
        leaf group-id {
          type string;
          description
            "The NRP topology group identifier.";
        }
        container base-topology-ref {
          description
            "Container for the base topology reference.";
          uses nw:network-ref;
        }
        list link {
          key "link-ref";
          description
            "A list of links with common attributes";
          leaf link-ref {
            type leafref {
              path
                "/nw:networks/nw:network[nw:network-id=current()"
              + "/../../base-topology-ref/network-ref]"
              + "/nt:link/nt:link-id";
            }
            description
              "A reference to a link in the base topology.";
          }
        }
        uses resource-reservation;
        leaf link-partition-type {
          type identityref {
            base nrp-link-partition-type;
          }
          description
            "Indicates the resource reservation type of an NRP link.";
        }
        uses qos-phb-profile;
      }
    }
  }

  /*
   * Grouping - NRP Policy
   */

  grouping nrp-pol {
    description
      "Grouping for NRP policies.";
    container nrp-policies {
      description
        "Container for nrp policies.";
      uses qos-profiles;
      list nrp-policy {
        key "name";
        unique "nrp-id";
        description
          "List of NRP policies.";
        leaf name {
          type string;
          description
            "A string that uniquely identifies the NRP policy.";
        }
        leaf nrp-id {
          type uint32;
          description
            "A 32-bit ID that uniquely identifies the NRP
             created by the enforcement of this NRP policy.";
        }
        leaf mode {
          type identityref {
            base nrp-partition-mode;
          }
          description
            "Indicates the resource partition mode of the NRP, such
             as control plane partition, data plane partition,
             or hybrid partition.";
        }
        uses resource-reservation;
        uses selector-id;
        uses qos-phb-profile;
        container topology {
          description
            "Container for NRP topology.";
          uses igp-congruent;
          choice topology-type {
            description
              "Choice of NRP topology type.";
            case selection {
              uses select-topology;
            }
            case filter {
              uses topology-filter;
            }
          }
        }
      }
    }
  }

  /*
   * Grouping - NRP Selector ID State
   */

  grouping selector-id-state {
    description
      "The grouping of NRP selector ID state.";
    container selector-id {
      config false;
      description
        "The container of NRP selector ID.";
      leaf srv6 {
        type srv6-types:srv6-sid;
        description
          "Indicates the SRv6 SID value as the NRP selector ID.";
      }
    }
  }

  // nrp-link-statistics

  grouping statistics-per-link {
    description
      "Statistics attributes per NRP link.";
    container statistics {
      config false;
      description
        "Statistics for NRP link.";
      uses vpn-common:service-status;
      uses nrp-bandwidth-metrics;
      uses te-packet-types:one-way-performance-metrics-packet;
    }
  }

  /*
   * Grouping - NRP node attributes
   */

  grouping nrp-node-attributes {
    description
      "NRP node scope attributes.";
    container nrp-node-attributes {
      config false;
      description
        "Containing NRP attributes.";
      uses selector-id-state;
    }
  }

  /*
   * Grouping - NRP Link Attributes
   */

  grouping nrp-link-attributes {
    description
      "NRP link scope attributes.";
    container nrp-link-attributes {
      config false;
      description
        "Contains NRP link attributes.";
      leaf link-partition-type {
        type identityref {
          base nrp-link-partition-type;
        }
        description
          "Indicates the resource partition type of an NRP link.";
      }
      leaf bandwidth-value {
        type uint64;
        units "bits/second";
        description
          "Bandwidth allocation for the NRP as absolute value.";
      }
      uses selector-id-state;
      uses statistics-per-link;
    }
  }

  /*
   * Grouping - NRP Bandwidth Metrics
   */

  grouping nrp-bandwidth-metrics {
    description
      "Grouping for NRP bandwidth metrics.";
    leaf one-way-available-bandwidth {
      type uint64;
      units "bits/second";
      description
        "Available bandwidth that is defined to be NRP link
         bandwidth minus bandwidth utilization.";
    }
    leaf one-way-utilized-bandwidth {
      type uint64;
      units "bits/second";
      description
        "Bandwidth utilization that represents the actual
         utilization of the link (i.e., as measured in the router).";
    }
  }

  /*
   * Grouping - NRPs Node Attributes
   */

  grouping nrps-node-attributes {
    description
      "Grouping for NRPs nodes attributes.";
    container nrps-node-attributes {
      description
        "Containing NRPs attributes.";
      list nrp {
        key "nrp-id";
        config false;
        description
          "List of NRPs.";
        leaf nrp-id {
          type uint32;
          description
            "NRP identifier";
        }
        uses nrp-node-attributes;
      }
    }
  }

  /*
   * Grouping - NRPs Link Attributes
   */

  grouping nrps-link-attributes {
    description
      "Grouping for NRPs link attributes.";
    container nrps-link-attributes {
      config false;
      description
        "Contains NRPs link attributes.";
      list nrp {
        key "nrp-id";
        config false;
        description
          "List of NRPs.";
        leaf nrp-id {
          type uint32;
          description
            "NRP identifier";
        }
        uses nrp-link-attributes;
      }
    }
  }

  // nrp-network-type

  grouping nrp-network-type {
    description
      "Identifies the network type to be NRP.";
    container nrp {
      presence "Indicates NRP network topology.";
      description
        "The presence of the container node indicates NRP network.";
    }
  }

  /*
   * Augment - Network Resource Partition Policies.
   */

  augment "/nw:networks" {
    description
      "Augments networks with NRP policies.";
    uses nrp-pol;
  }

  /*
   * Augment - NRP type.
   */

  augment "/nw:networks/nw:network/nw:network-types" {
    description
      "Indicates the network type of NRP";
    uses nrp-network-type;
  }

  /*
   * Augment - NRP node operational status.
   */

  augment "/nw:networks/nw:network/nw:node" {
    when '../nw:network-types/nrp:nrp' {
      description
        "Augments only for NRP network topology.";
    }
    description
      "Augments node with NRP state attributes.";
    uses nrp-node-attributes;
  }

  /*
   * Augment - NRP link operational status.
   */

  augment "/nw:networks/nw:network/nt:link" {
    when '../nw:network-types/nrp:nrp' {
      description
        "Augments only for NRP network topology.";
    }
    description
      "Augments link with NRP state attributes.";
    uses nrp-link-attributes;
  }

  /*
   * Augment - Native topology with NRPs node operational status.
   */

  augment "/nw:networks/nw:network/nw:node" {
    description
      "Augments node with NRP list state attributes.";
    uses nrps-node-attributes;
  }

  /*
   * Augment - Native topology with NRPs link operational status.
   */

  augment "/nw:networks/nw:network/nt:link" {
    description
      "Augments link with NRP list state attributes.";
    uses nrps-link-attributes;
  }
}
