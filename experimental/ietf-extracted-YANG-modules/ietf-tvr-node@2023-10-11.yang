module ietf-tvr-node {
  yang-version 1.1;
  namespace "urn:ietf:params:xml:ns:yang:ietf-tvr-node";
  prefix tvr-node;

  import ietf-yang-types {
    prefix "yang";
  }

  import ietf-tvr-schedule {
    prefix "tvr-schd";
  }

  organization
    "IETF TVR - Time Variant Routing Working Group";
  contact
    "WG Web:   <http://datatracker.ietf.org/wg/tvr>
     WG List:  <mailto:tvr@ietf.org>

     Author:   Yingzhen Qu
               <mailto:yingzhen.ietf@gmail.com>
     Author:   Acee Lindem
               <mailto:acee.ietf@gmail.com>
     Author:   Marc Blanchet
               <mailto:marc.blanchet@viagenie.ca>
     Author:   Eric Kinzie
               <mailto:ekinzie@labn.net>
     Author:   Don Fedyk
               <mailto:dfedyk@labn.net>";

  description
    "The YANG module defines a schedule for changing
     attributes of a single node.

     This YANG model conforms to the Network Management
     Datastore Architecture (NMDA) as described in RFC 8342.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  reference
    "RFC XXXX: YANG Data Model for Scheduled Attributes";

  revision 2023-10-11 {
    description
      "Initial Version";
    reference
      "RFC XXXX: YANG Data Model for Scheduled Attributes.";
  }

  container node-schedule {
    description
      "This container defined time variant attributes
       for node's schedule.";

    leaf router-id {
      type yang:dotted-quad;
      description
        "A 32-bit number used to identify a router.";
    }

    list power-schedule {
      key "start-date-time";
      description
        "Power schedule for the node. The node's power is
         represented by a boolean value with 'true' indicating
         the node is powered on and 'false' indicating the node
         is powered off.";
      uses tvr-schd:schedule {
        augment value-default {
          description
            "Augment the default power state.";
          leaf default-power {
            type boolean;
            default false;
            description
              "This indicates the default node power when for
               time periods when no interval is defined. If
               unspecified, the node is powered down by default.";
          }
        }
        augment base-schedule/intervals/value {
          description
            "Augmment the scheduled power state.";
          leaf power {
            type boolean;
            description
              "Indicates whether the node is powered on.";
          }
        }
      }
    }

    container interface-schedule {
      description
        "Container for TVR node interface attributes.";

      list interfaces {
        key "name";
        description
          "List of interface with schedules.";
        leaf name {
          type string;
          description
            "Name of the interface.
             If used with the ietf-interfaces module, the name should
             match the name of the interface.";
        }

        list up-down-schedule {
          key "start-date-time";
          description
           "Scheduled times that the interface is up. This is to
           work with the leaf 'enabled' for the configured state
           of the interface.";

          uses tvr-schd:schedule {
            augment value-default {
              description
                "Augment default interface state.";
              leaf default-available {
                type boolean;
                default false;
                description
                  "By default, the link is not available.";
              }
            }
            augment base-schedule/intervals/value {
              description
                "Augment scheduled interface state.";
              leaf availble {
                type boolean;
                description
                  "Link availability.";
              }
            }
          }
        }
      }
    }
  }
}
