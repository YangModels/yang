module ietf-netconf-data-source {

  namespace "urn:ietf:params:xml:ns:yang:ietf-netconf-data-source";
  prefix datasrc;

  organization
    "IETF NETCONF (Network Configuration Protocol) Working Group";

  contact
    "WG Web:   <http://tools.ietf.org/wg/netconf/>
     WG List:  <mailto:netconf@ietf.org>

     WG Chair: Mehmet Ersue
               <mailto:mehmet.ersue@nsn.com>

     WG Chair: Bert Wijnen
               <mailto:bertietf@bwijnen.net>

     Editor:   Andy Bierman
               <mailto:andy@yumaworks.com>";

  description
    "This module contains a collection of YANG definitions for
     identifying the data source of operational data nodes.

     Copyright (c) 2012 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: remove this note
  // Note: extracted from draft-bierman-netconf-get2-02.txt

  // RFC Ed.: update the date below with the date of RFC publication
  // and remove this note.
  revision "2012-10-09" {
    description
      "Initial revision.";
    reference
      "RFC XXXX: The NETCONF <get2> Operation";
  }

  /* Extensions */

  extension data-source {
    description
      "This extension indicates that the data node containing it
       is expected to support the 'data-source' XML attribute
       in replies for the <get2> operation.

       This extension is ignored if it is not within a YANG
       data definition statement for an operational data node.";
  }

  /* Identities */

  identity data-sources {
    description
      "Base identity for all data sources.";
  }

  identity server {
    base data-sources;
    description
      "Indicates the server instrumentation as the data source.";
  }

  identity running {
    base data-sources;
    description
      "Indicates the running datastore as the data source.";
  }

  identity operation {
    base data-sources;
    description
      "Indicates a client-initiated protocol operation as
       the data source.";
  }

  identity ntp {
    base data-sources;
    description
      "Indicates the NTP protocol as the data source.";
    reference
      "RFC 5905: Network Time Protocol Version 4:
       Protocol and Algorithms Specification";
  }

  identity dns {
    base data-sources;
    description
      "Indicates the DNS protocol as the data source.";
    // reference TBD
  }

}
