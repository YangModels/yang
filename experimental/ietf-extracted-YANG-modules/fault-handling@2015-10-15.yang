submodule fault-handling {
  belongs-to sfc-control-planes {
    prefix sfc-fh;
  }
  organization "ETRI.";
  contact
  "M-K. Shin mkshin@etri.re.kr
   M-J Choi mjchoi@kangwon.ac.kr";
  description
  "This module first detects faults and handles the detected
   faults in accordance with the fault handling action. ";
  revision 2015-10-15 {
     reference
     "draft-shin-sfc-control-plane-yang-00 -
     Yang Data Model for Service Function Chaining Control Plane";
  }
  container fault-handling {
     description
      "This Container first detects faults and handles the detected
       faults in accordance with the fault handling action. ";

    list fault-handling {
      key fault-name;
      description
      "The name of occurred fault.";
      leaf fault-name {
        type string;
        description
        "The fault handing action: drop, bypass, use alternate
         node.";
      }
      leaf fault-type {
        type enumeration {
          enum node{
             description
             "Node";
          }
          enum link{
             description
             "Link";
          }
          enum path-failures{
             description
             "Path";
          }
        }
        description
        "The type of occurred fault.";
      }
      leaf fault-handling-action {
        type enumeration {
          enum bypass{
             description
             "Bypass";
          }
          enum use-alternate-node{
             description
             "Alternate node";
          }
          enum use-alternate-chain{
             description
             "Alternate chain";
          }
          enum drop-traffic{
             description
             "Drop the traffic";
          }
        }
        description
        "The fault handing action: drop, bypass, use alternate
         node.";
      }
   }
}
}
