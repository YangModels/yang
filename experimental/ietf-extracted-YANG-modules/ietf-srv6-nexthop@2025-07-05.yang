module ietf-srv6-nexthop {
  yang-version "1.1";
  namespace "urn:ietf:params:xml:ns:yang:ietf-srv6-nexthop";
  prefix "srv6-nexthop";
  import ietf-inet-types {
    prefix "inet";
    reference
      "RFC 6991: Common YANG Data Types";
  }
  import ietf-routing {
    prefix "rt";
    reference
      "RFC 8349: A YANG Data Model for Routing Management
       (NMDA Version).";
  }
  import ietf-ipv4-unicast-routing {
    prefix "v4ur";
    reference
      "RFC 8349: A YANG Data Model for Routing Management
       (NMDA Version).";
  }
  import ietf-ipv6-unicast-routing {
    prefix "v6ur";
    reference
      "RFC 8349: A YANG Data Model for Routing Management
       (NMDA Version).";
  }
  import ietf-sr-policy-types {
    prefix "sr-policy-types";
    reference
      "RFC XXXX: YANG Data Model for Segment Routing Policy.";
  }
  organization
    "IETF SPRING Working Group";
  contact
    "TBD";
  description
    "This module describes a YANG model for configuring and
     managing SRv6 next hop information for Routing.
     This YANG model conforms to the Network Management
     Datastore Architecture (NMDA) as described in RFC 8342.
     Copyright (c) 2025 IETF Trust and the persons identified as
     authors of the code.  All rights reserved.
     Redistribution and use in source and binary forms, with or
     without modification, is permitted pursuant to, and subject to
     the license terms contained in, the Revised BSD License set
     forth in Section 4.c of the IETF Trust's Legal Provisions
     Relating to IETF Documents
     (https://trustee.ietf.org/license-info).
     This version of this YANG module is part of RFC XXXX;
     see the RFC itself for full legal notices.
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  revision 2025-07-05 {
    description
      "Initial Version";
    reference
      "RFC XXXX, YANG Data Model for SRv6 Next Hop of Routing";
  }
  grouping srv6-nexthop-info {
    description
      "This group provides the information of SRv6 next hop for
       routing.";
    container srv6-te {
      description
        "The informaton of SRv6 Traffic Engineering forwarding.";
      leaf color {
        type sr-policy-types:color-type;
        description
          "The Color of a SRv6 Policy.";
      }
      leaf endpoint {
        type inet:ip-prefix;
        description
          "The endpoint of a SRv6 Policy.";
      }
      leaf srv6-sid {
        type inet:ipv6-prefix;
        description
          "The SRv6 SID value for SRv6 Traffic Engineering
           forwarding.";
      }
    }
    container srv6-be {
      description
        "The informaton of SRv6 Best Effort forwarding.";
      leaf srv6-sid {
        type inet:ipv6-prefix;
        description
          "The SRv6 SID value for SRv6 Best Effort forwarding.";
      }
    }
  }
  grouping srv6-nexthop-content {
    description
      "Generic parameters of SRv6 next hop in static routes.";
    container srv6-next-hop-list {
      description
        "Container for multiple SRv6 next hop.";
      list srv6-next-hop {
        key "index";
        description
          "An entry in a SRv6 next hop list.";
        leaf index {
          type string;
          description
            "A user-specified identifier utilized to uniquely
             reference the SRv6 next-hop entry in the SRv6
             next-hop list. The value of this index has no
             semantic meaning other than for referencing the
             entry.";
        }
        uses srv6-nexthop-info;
      }
    }
  }
  grouping srv6-nexthop-state-content {
    description
      "Generic state parameters of SRv6 next hop.";
    container srv6-next-hop-list {
      description
        "Container for multiple SRv6 next hop.";
      list srv6-next-hop {
        description
          "An entry in a SRv6 next hop list.";
        uses srv6-nexthop-info;
      }
    }
  }
  augment "/rt:routing/rt:control-plane-protocols/"
        + "rt:control-plane-protocol/rt:static-routes/v4ur:ipv4/"
        + "v4ur:route/v4ur:next-hop/v4ur:next-hop-options" {
    description
      "Augment 'next-hop-options' in IPv4 unicast route.";
    case srv6-next-hop-list {
      description
        "The case represents a SRv6 next hop list.";
      uses srv6-nexthop-content;
    }
  }
  augment "/rt:routing/rt:control-plane-protocols/"
        + "rt:control-plane-protocol/rt:static-routes/v6ur:ipv6/"
        + "v6ur:route/v6ur:next-hop/v6ur:next-hop-options" {
    description
      "Augment 'next-hop-options' in IPv6 unicast route.";
    case srv6-next-hop-list {
      description
        "The case represents a SRv6 next hop list.";
      uses srv6-nexthop-content;
    }
  }
  augment "/rt:routing/rt:ribs/rt:rib/rt:routes/rt:route/"
        + "rt:next-hop/rt:next-hop-options" {
    description
      "Augment 'next-hop-options' of a route in RIB.";
    case srv6-next-hop-list {
      description
        "The case represents a SRv6 next hop list.";
      uses srv6-nexthop-state-content;
    }
  }
  augment "/rt:routing/rt:ribs/rt:rib/rt:active-route/rt:output/"
        + "rt:route/rt:next-hop/rt:next-hop-options" {
    description
      "Augment 'next-hop-options' of an active-route in RIB.";
    case srv6-next-hop-list {
      description
        "The case represents a SRv6 next hop list.";
      uses srv6-nexthop-state-content;
    }
  }
}
