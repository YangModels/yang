module ietf-eth-te-topology {

  namespace "urn:ietf:params:xml:ns:yang:ietf-eth-te-topology";

  prefix "ethtetopo";

  import ietf-network {
    prefix "nw";
  }

  import ietf-network-topology {
    prefix "nt";
  }

  import ietf-te-topology {
    prefix "tet";
  }

  import ietf-yang-types {
    prefix "yang";
  }

  import ietf-eth-tran-types {
    prefix "etht-types";
  }

  organization
    "Internet Engineering Task Force (IETF) CCAMP WG";
  contact
    "
      WG List: <mailto:ccamp@ietf.org>

      ID-draft editor:
        Haomian Zheng (zhenghaomian@huawei.com);
        Italo Busi (italo.busi@huawei.com);
        Aihua Guo (aihuaguo@huawei.com);
        Yunbin Xu (xuyunbin@ritt.cn);
        Yang Zhao (zhaoyangyjy@chinamobile.com);
        Xufeng Liu (Xufeng_Liu@jabil.com);
    ";

  description
    "This module defines a YANG data model for describing
     layer-2 Ethernet transport topologies.";

  revision 2019-07-08 {
    description
      "Initial Revision";
    reference
      "RFC XXXX: A YANG Data Model for Client-layer Topology";
    // RFC Ed.: replace XXXX with actual RFC number, update date
    // information and remove this note
  }

  /*
   * Groupings
   */

  grouping eth-tran-topology-type {
    description
      "Identifies the Ethernet Transport topology type";

    container eth-tran-topology {
      presence "indicates a topology type of
                Ethernet Transport Network.";
      description "Eth transport topology type";
    }
  }

  grouping ltp-bandwidth-profiles {
    description
      "A grouping which represents the bandwidt profile(s) for the ETH LTP.";

    choice direction {
      description
        "Whether the bandwidth profiles are symmetrical or
         asymmetrical";
      case symmetrical {
        description
          "The same bandwidth profile is used to describe the ingress
           and the egress bandwidth profile.";

        container ingress-egress-bandwidth-profile {
          description
            "The bandwith profile used in the ingress and egress direction.";
          uses etht-types:etht-bandwidth-profiles;
        }
      }
      case asymmetrical {
        description
          "Different ingress and egress bandwidth profiles
           can be specified.";
        container ingress-bandwidth-profile {
          description
            "The bandwidth profile used in the ingress direction.";
          uses etht-types:etht-bandwidth-profiles;
        }
        container egress-bandwidth-profile {
          description
            "The bandwidth profile used in the egress direction.";
          uses etht-types:etht-bandwidth-profiles;
        }
      }
    }
  }

  grouping eth-ltp-attributes {
    description
      "Ethernet transport link termination point attributes";

    /*
     * Open Issue: should we remove this attribute (duplicates with I2RS L2 attributes)?
     */
    leaf ltp-mac-address {
      type yang:mac-address;
      description "the MAC address of the LTP.";
    }
    /*
     * Open Issue: should we remove this attribute (duplicates with I2RS L2 attributes)?
     */
    leaf port-vlan-id {
      type etht-types:vlanid;
      description "the port VLAN ID of the LTP.";
    }
    /*
     * Open Issue: should we remove this attribute (duplicates with I2RS L2 attributes)?
     */
    leaf maximum-frame-size {
      type uint16 {
        range "64 .. 65535";
      }
      description
        "Maximum frame size";
    }
      uses ltp-bandwidth-profiles;
  }

  grouping svc-vlan-classification {
    description
      "Grouping defining the capabilities for VLAN classification.";

    leaf-list supported-tag-types {
      type etht-types:eth-tag-classify;
      description
        "List of VLAN tag types that can be used for the VLAN classification.
         In case VLAN classification is not supported, the list is empty.";
    }
    leaf vlan-bundling {
      type boolean;
      description
        "In case VLAN classification is supported, indicates whether VLAN bundling classification is also supported.";
    }
    leaf vlan-range {
      type etht-types:vid-range-type;
      description
        "In case VLAN classification is supported, indicates the of available VLAN ID values.";
    }
  }

  grouping svc-vlan-push {
    description
      "Grouping defining the capabilities for VLAN push or swap operations.";
    leaf-list supported-tag-types {
      type etht-types:eth-tag-type;
      description
        "List of VLAN tag types that can be used to push or swap a VLAN tag.
         In case VLAN push/swap is not supported, the list is empty.";
    }
    leaf vlan-range {
      type etht-types:vid-range-type;
      description
        "In case VLAN push/swap operation is supported, the range of available VLAN ID values.";
    }
  }

  grouping eth-ltp-svc-attributes {
    description
      "Ethernet link termination point (LTP) service attributes.";

    container supported-classification {
      description
        "Service classification capabilities supported by the ETH LTP.";

      leaf transparent{
        type boolean;
        description
          "Indicates that the ETH LTP support transparent ETH client service.";
      }
      leaf port-classification {
        type boolean;
        description
          "Indicates that the ETH LTP support port-based service classification.";
      }
      container vlan-classification {
        description
          "Service classification capabilities based on the VLAN tag(s)
           supported by the ETH LTP.";

        leaf vlan-tag-classification {
          type boolean;
          description
            "Indicates that the ETH LTP supports VLAN service classification.";
        }
        container outer-tag {
          description
            "Service classification capabilities based on the outer VLAN tag,
             supported by the ETH LTP.";
          uses svc-vlan-classification;
        }
        container second-tag {
          description
            "Service classification capabilities based on the second VLAN tag,
             supported by the ETH LTP.";
          /*
           * Open issue: indicates that second-tag-classification can be True only if
           * outer-tag-classification is also True.
           */
          leaf second-tag-classification {
            type boolean;
            description
              "Indicates that the ETH LTP support  VLAN service classification
               based on the second VLAN tag.";
          }
          uses svc-vlan-classification;
        }
      }
    }

    container supported-vlan-operations {
      description
        "Reports the VLAN operations supported by the ETH LTP.";

      leaf asymmetrical-operations {
        type boolean;
        description
          "Indicates whether the ETH LTP supports also asymmetrical VLAN operations.
           It is assumed that symmetrical VLAN operations are alwyas supported.";
      }
      leaf transparent-vlan-operations {
        type boolean;
        description
          "Indicates that the ETH LTP supports transparent operations.";
      }
      container vlan-pop {
        description
          "Indicates VLAN pop or swap operations capabilities.";

        leaf vlan-pop-operations {
          type boolean;
          description
            "Indicates that the ETH LTP supports VLAN pop or swap operations.";
        }
        leaf max-pop-tags {
          type uint8 {
            range "1..2";
          }
          description
            "Indicates the maximum number of tags that can be popped/swapped.";
        }
      }
      container vlan-push {
        description
          "Indicates VLAN push or swap operations capabilities.";

        leaf vlan-push-operation {
          type boolean;
          description
            "Indicates that the ETH LTP supports VLAN push or swap operations.";
        }
        container outer-tag {
          description
            "Indicates the supported VLAN operation capabilities on the outer VLAN tag.";
          uses svc-vlan-push;
        }
        container second-tag {
          description
            "Indicates the supported VLAN operation capabilities on the second VLAN tag.";

          leaf push-second-tag {
            type boolean;
            description
              "Indicates that the ETH LTP supports VLAN push or swap operations
               for the second VLAN tag.";
          }
          uses svc-vlan-push;
        }
      }
    }
  }

  /*
   * Data nodes
   */

  augment "/nw:networks/nw:network/nw:network-types/tet:te-topology" {
    description
      "Augment network types to include ETH transport newtork";

    uses eth-tran-topology-type;
  }

  augment "/nw:networks/nw:network/nw:node/nt:termination-point" {
    when "../../nw:network-types/tet:te-topology/eth-tran-topology" {
      description
        "Augment only for ETH transport network";
    }
    description
      "Augment ETH LTP attributes";

    uses eth-ltp-attributes;

    container eth-svc {
      presence "client-facing LTP.";
      description
        "ETH LTP Service attributes.";

      leaf client-facing {
        type boolean;
        default "false";
        description
          "Indicates whether this LTP is a client-facing LTP.";
      }
      uses eth-ltp-svc-attributes;
    }
  }

  /*
   * Augment TE bandwidth
   */

  /* Augment maximum LSP bandwidth of link terminationpoint (LTP) */
  augment "/nw:networks/nw:network/nw:node/nt:termination-point/"
        + "tet:te/"
        + "tet:interface-switching-capability/tet:max-lsp-bandwidth/"
        + "tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }
  /* Augment bandwidth path constraints of connectivity-matrices */
  augment "/nw:networks/nw:network/nw:node/tet:te/"
        + "tet:te-node-attributes/tet:connectivity-matrices/"
        + "tet:path-constraints/tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }

  /* Augment bandwidth path constraints of connectivity-matrix */
  augment "/nw:networks/nw:network/nw:node/tet:te/"
        + "tet:te-node-attributes/tet:connectivity-matrices/"
        + "tet:connectivity-matrix/"
        + "tet:path-constraints/tet:te-bandwidth/tet:technology" {
    when "../../../../../../../nw:network-types/tet:te-topology/"
       + "ethtetopo:eth-tran-topology" {
      description "Ethernet TE bandwidth";
    }
    description "Ethernet bandwidth.";
    case eth {
      uses etht-types:eth-bandwidth;
    }
  }

  /* Augment bandwidth path constraints of connectivity-matrices information-source */
  augment "/nw:networks/nw:network/nw:node/tet:te/"
        + "tet:information-source-entry/tet:connectivity-matrices/"
        + "tet:path-constraints/tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }

  /* Augment bandwidth path constraints of connectivity-matrix information-source */
  augment "/nw:networks/nw:network/nw:node/tet:te/"
        + "tet:information-source-entry/tet:connectivity-matrices/"
        + "tet:connectivity-matrix/"
        + "tet:path-constraints/tet:te-bandwidth/tet:technology" {
    when "../../../../../../../nw:network-types/tet:te-topology/"
       + "ethtetopo:eth-tran-topology" {
      description "Ethernet TE bandwidth";
    }
    description "Ethernet bandwidth.";
    case eth {
      uses etht-types:eth-bandwidth;
    }
  }

  /* Augment client bandwidth of tunnel termination point (TTP) */
  augment "/nw:networks/nw:network/nw:node/tet:te/"
        + "tet:tunnel-termination-point/"
        + "tet:client-layer-adaptation/tet:switching-capability/"
        + "tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }

  /* Augment bandwidth path constraints of local-link-connectivities */
  augment "/nw:networks/nw:network/nw:node/tet:te/"
        + "tet:tunnel-termination-point/"
        + "tet:local-link-connectivities/tet:path-constraints/"
        + "tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }

  /* Augment bandwidth path constraints of local-link-connectivity (LLC) */
  augment "/nw:networks/nw:network/nw:node/tet:te/"
        + "tet:tunnel-termination-point/"
        + "tet:local-link-connectivities/"
        + "tet:local-link-connectivity/tet:path-constraints/"
        + "tet:te-bandwidth/tet:technology" {
    when "../../../../../../../nw:network-types/tet:te-topology/"
       + "ethtetopo:eth-tran-topology" {
      description "Ethernet TE bandwidth";
    }
    description "Ethernet bandwidth.";
    case eth {
      uses etht-types:eth-bandwidth;
    }
  }

  /* Augment maximum LSP bandwidth of TE link */
  augment "/nw:networks/nw:network/nt:link/tet:te/"
        + "tet:te-link-attributes/"
        + "tet:interface-switching-capability/tet:max-lsp-bandwidth/"
        + "tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }

  /* Augment maximum bandwidth of TE link */
  augment "/nw:networks/nw:network/nt:link/tet:te/"
        + "tet:te-link-attributes/"
        + "tet:max-link-bandwidth/"
        + "tet:te-bandwidth/tet:technology" {
    when "../../../../../nw:network-types/tet:te-topology/"
       + "ethtetopo:eth-tran-topology" {
      description "Ethernet TE bandwidth";
    }
    description "Ethernet bandwidth.";
    case eth {
      uses etht-types:eth-bandwidth;
    }
  }

  /* Augment maximum reservable bandwidth of TE link */
  augment "/nw:networks/nw:network/nt:link/tet:te/"
        + "tet:te-link-attributes/"
        + "tet:max-resv-link-bandwidth/"
        + "tet:te-bandwidth/tet:technology" {
    when "../../../../../nw:network-types/tet:te-topology/"
       + "ethtetopo:eth-tran-topology" {
      description "Ethernet TE bandwidth";
    }
    description "Ethernet bandwidth.";
    case eth {
      uses etht-types:eth-bandwidth;
    }
  }

  /* Augment unreserved bandwidth of TE Link */
  augment "/nw:networks/nw:network/nt:link/tet:te/"
        + "tet:te-link-attributes/"
        + "tet:unreserved-bandwidth/"
        + "tet:te-bandwidth/tet:technology" {
    when "../../../../../nw:network-types/tet:te-topology/"
       + "ethtetopo:eth-tran-topology" {
      description "Ethernet TE bandwidth";
    }
    description "Ethernet bandwidth.";
    case eth {
      uses etht-types:eth-bandwidth;
    }
  }
  /* Augment maximum LSP bandwidth of TE link information-source */
  augment "/nw:networks/nw:network/nt:link/tet:te/"
        + "tet:information-source-entry/"
        + "tet:interface-switching-capability/"
        + "tet:max-lsp-bandwidth/"
        + "tet:te-bandwidth/tet:technology" {
    when "../../../../../../nw:network-types/tet:te-topology/"
       + "ethtetopo:eth-tran-topology" {
      description "Ethernet TE bandwidth";
    }
    description "Ethernet bandwidth.";
    case eth {
      uses etht-types:eth-bandwidth;
    }
  }

  /* Augment maximum bandwidth of TE link information-source */
  augment "/nw:networks/nw:network/nt:link/tet:te/"
        + "tet:information-source-entry/"
        + "tet:max-link-bandwidth/"
        + "tet:te-bandwidth/tet:technology" {
    when "../../../../../nw:network-types/tet:te-topology/"
       + "ethtetopo:eth-tran-topology" {
      description "Ethernet TE bandwidth";
    }
    description "Ethernet bandwidth.";
    case eth {
      uses etht-types:eth-bandwidth;
    }
  }

  /* Augment maximum reservable bandwidth of TE link information-source */
  augment "/nw:networks/nw:network/nt:link/tet:te/"
        + "tet:information-source-entry/"
        + "tet:max-resv-link-bandwidth/"
        + "tet:te-bandwidth/tet:technology" {
    when "../../../../../nw:network-types/tet:te-topology/"
       + "ethtetopo:eth-tran-topology" {
      description "Ethernet TE bandwidth";
    }
    description "Ethernet bandwidth.";
    case eth {
      uses etht-types:eth-bandwidth;
    }
  }

  /* Augment unreserved bandwidth of TE link information-source */
  augment "/nw:networks/nw:network/nt:link/tet:te/"
        + "tet:information-source-entry/"
        + "tet:unreserved-bandwidth/"
        + "tet:te-bandwidth/tet:technology" {
    when "../../../../../nw:network-types/tet:te-topology/"
       + "ethtetopo:eth-tran-topology" {
      description "Ethernet TE bandwidth";
    }
    description "Ethernet bandwidth.";
    case eth {
      uses etht-types:eth-bandwidth;
    }
  }

  /* Augment maximum LSP bandwidth of TE link template */
  augment "/nw:networks/tet:te/tet:templates/"
        + "tet:link-template/tet:te-link-attributes/"
        + "tet:interface-switching-capability/"
        + "tet:max-lsp-bandwidth/"
        + "tet:te-bandwidth/tet:technology" {
/*
    when "../../../../../../nw:network-types/tet:te-topology/"
       + "ethtetopo:eth-tran-topology" {
      description "Ethernet TE bandwidth";
    }
*/
    description "Ethernet bandwidth.";
    case eth {
      uses etht-types:eth-bandwidth;
    }
  }

  /* Augment maximum bandwidth of TE link template */
  augment "/nw:networks/tet:te/tet:templates/"
        + "tet:link-template/tet:te-link-attributes/"
        + "tet:max-link-bandwidth/"
        + "tet:te-bandwidth/tet:technology" {
/*
    when "../../../../../nw:network-types/tet:te-topology/"
        + "ethtetopo:eth-tran-topology" {
      description "Ethernet TE bandwidth";
    }
*/
    description "Ethernet bandwidth.";
    case eth {
      uses etht-types:eth-bandwidth;
    }
  }

  /* Augment maximum reservable bandwidth of TE link template */
  augment "/nw:networks/tet:te/tet:templates/"
        + "tet:link-template/tet:te-link-attributes/"
        + "tet:max-resv-link-bandwidth/"
        + "tet:te-bandwidth/tet:technology" {
/*
    when "../../../../../nw:network-types/tet:te-topology/"
        + "ethtetopo:eth-tran-topology" {
      description "Ethernet TE bandwidth";
    }
*/
    description "Ethernet bandwidth.";
    case eth {
      uses etht-types:eth-bandwidth;
    }
  }

  /* Augment unreserved bandwidth of TE link template */
  augment "/nw:networks/tet:te/tet:templates/"
        + "tet:link-template/tet:te-link-attributes/"
        + "tet:unreserved-bandwidth/"
        + "tet:te-bandwidth/tet:technology" {
/*
    when "../../../../../../nw:network-types/tet:te-topology/"
        + "ethtetopo:eth-tran-topology" {
      description "Ethernet TE bandwidth";
    }
*/
    description "Ethernet bandwidth.";
    case eth {
      uses etht-types:eth-bandwidth;
    }
  }

  /*
   * Augment TE label.
   */

  /* Augment label restrictions of connectivity-matrices */
  augment "/nw:networks/nw:network/nw:node/tet:te/"
        + "tet:te-node-attributes/tet:connectivity-matrices/"
        + "tet:label-restrictions/tet:label-restriction" {
    when "../../../../../../nw:network-types/tet:te-topology/"
       + "ethtetopo:eth-tran-topology" {
      description "Ethernet TE label";
    }
    description "Ethernet label restriction.";
    uses etht-types:eth-label-restriction;
  }

  /* Augment label restrictions start of connectivity-matrices */
  augment "/nw:networks/nw:network/nw:node/tet:te/"
        + "tet:te-node-attributes/tet:connectivity-matrices/"
        + "tet:label-restrictions/tet:label-restriction/tet:label-start/"
        + "tet:te-label/tet:technology" {
    when "../../../../../../../../nw:network-types/tet:te-topology/"
       + "ethtetopo:eth-tran-topology" {
      description "Ethernet TE label";
    }
    description "Ethernet label.";
    case eth {
      uses etht-types:eth-label;
    }
  }

  /* Augment label restrictions end of connectivity-matrices */
  augment "/nw:networks/nw:network/nw:node/tet:te/"
        + "tet:te-node-attributes/tet:connectivity-matrices/"
        + "tet:label-restrictions/tet:label-restriction/tet:label-end/"
        + "tet:te-label/tet:technology" {
    when "../../../../../../../../nw:network-types/tet:te-topology/"
       + "ethtetopo:eth-tran-topology" {
      description "Ethernet TE label";
    }
    description "Ethernet label.";
    case eth {
      uses etht-types:eth-label;
    }
  }

  /* Augment label restrictions step of connectivity-matrices */
  augment "/nw:networks/nw:network/nw:node/tet:te/"
        + "tet:te-node-attributes/tet:connectivity-matrices/"
        + "tet:label-restrictions/tet:label-restriction/tet:label-step/"
        + "tet:technology" {
    when "../../../../../../../nw:network-types/tet:te-topology/"
       + "ethtetopo:eth-tran-topology" {
      description "Ethernet TE label";
    }
    description "Ethernet label.";
    case eth {
      uses etht-types:eth-label-step;
    }
  }

  /* Augment label hop of underlay primary path of connectivity-matrices */
  augment "/nw:networks/nw:network/nw:node/tet:te/"
        + "tet:te-node-attributes/tet:connectivity-matrices/"
        + "tet:underlay/tet:primary-path/tet:path-element/"
        + "tet:type/tet:label/tet:label-hop/"
        + "tet:te-label/tet:technology" {
    when "../../../../../../../../../"
       + "nw:network-types/tet:te-topology/"
       + "ethtetopo:eth-tran-topology" {
      description "Ethernet TE label";
    }
    description "Ethernet label.";
    case eth {
      uses etht-types:eth-label;
    }
  }
  /* Augment label hop of underlay backup path of connectivity-matrices */
  augment "/nw:networks/nw:network/nw:node/tet:te/"
        + "tet:te-node-attributes/tet:connectivity-matrices/"
        + "tet:underlay/tet:backup-path/tet:path-element/"
        + "tet:type/tet:label/tet:label-hop/"
        + "tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label hop of route-exclude of connectivity-matrices */
  augment "/nw:networks/nw:network/nw:node/tet:te/"
        + "tet:te-node-attributes/tet:connectivity-matrices/"
        + "tet:optimizations/tet:algorithm/tet:metric/"
        + "tet:optimization-metric/"
        + "tet:explicit-route-exclude-objects/"
        + "tet:route-object-exclude-object/"
        + "tet:type/tet:label/tet:label-hop/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of route-include of connectivity-matrices (added) */
  augment "/nw:networks/nw:network/nw:node/tet:te/"
        + "tet:te-node-attributes/tet:connectivity-matrices/"
        + "tet:optimizations/tet:algorithm/tet:metric/"
        + "tet:optimization-metric/"
        + "tet:explicit-route-include-objects/"
        + "tet:route-object-include-object/"
        + "tet:type/tet:label/tet:label-hop/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of path-route of connectivity-matrices */
  augment "/nw:networks/nw:network/nw:node/tet:te/"
        + "tet:te-node-attributes/tet:connectivity-matrices/"
        + "tet:path-properties/tet:path-route-objects/"
        + "tet:path-route-object/tet:type/tet:label/tet:label-hop/"
        + "tet:te-label/tet:technology"{
    when "../../../../../../../../../"
       + "nw:network-types/tet:te-topology/"
       + "ethtetopo:eth-tran-topology" {
      description "Ethernet TE label";
    }
    description "Ethernet label.";
    case eth {
      uses etht-types:eth-label;
    }
  }

  /* Augment ingress label restrictions of connectivity-matrix */
  augment "/nw:networks/nw:network/nw:node/tet:te/"
        + "tet:te-node-attributes/tet:connectivity-matrices/"
        + "tet:connectivity-matrix/tet:from/"
        + "tet:label-restrictions/tet:label-restriction" {
    when "../../../../../../../../nw:network-types/tet:te-topology/"
       + "ethtetopo:eth-tran-topology" {
      description "Ethernet TE label";
    }
    description "Ethernet label.";
    uses etht-types:eth-label-restriction;
  }

  /* Augment ingress label restrictions start of connectivity-matrix */
  augment "/nw:networks/nw:network/nw:node/tet:te/"
        + "tet:te-node-attributes/tet:connectivity-matrices/"
        + "tet:connectivity-matrix/tet:from/"
        + "tet:label-restrictions/tet:label-restriction/tet:label-start/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment ingress label restrictions end of connectivity-matrix */
  augment "/nw:networks/nw:network/nw:node/tet:te/"
        + "tet:te-node-attributes/tet:connectivity-matrices/"
        + "tet:connectivity-matrix/tet:from/"
        + "tet:label-restrictions/tet:label-restriction/tet:label-end/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }
  /* Augment ingress label restrictions step of connectivity-matrix */
  augment "/nw:networks/nw:network/nw:node/tet:te/"
        + "tet:te-node-attributes/tet:connectivity-matrices/"
        + "tet:connectivity-matrix/tet:from/"
        + "tet:label-restrictions/tet:label-restriction/tet:label-step/"
        + "tet:technology" {
    when "../../../../../../../../../"
       + "nw:network-types/tet:te-topology/"
       + "ethtetopo:eth-tran-topology" {
      description "Ethernet TE label";
    }
    description "Ethernet label.";
    case eth {
      uses etht-types:eth-label-step;
    }
  }

  /* Augment egress label restrictions of connectivity-matrix */
  augment "/nw:networks/nw:network/nw:node/tet:te/"
        + "tet:te-node-attributes/tet:connectivity-matrices/"
        + "tet:connectivity-matrix/tet:to/"
        + "tet:label-restrictions/tet:label-restriction" {
    when "../../../../../../../../nw:network-types/tet:te-topology/"
       + "ethtetopo:eth-tran-topology" {
      description "Ethernet TE label";
    }
    description "Ethernet label.";
    uses etht-types:eth-label-restriction;
  }

  /* Augment egress label restrictions start of connectivity-matrix */
  augment "/nw:networks/nw:network/nw:node/tet:te/"
        + "tet:te-node-attributes/tet:connectivity-matrices/"
        + "tet:connectivity-matrix/tet:to/"
        + "tet:label-restrictions/tet:label-restriction/tet:label-start/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment egress label restrictions end of connectivity-matrix */
  augment "/nw:networks/nw:network/nw:node/tet:te/"
        + "tet:te-node-attributes/tet:connectivity-matrices/"
        + "tet:connectivity-matrix/tet:to/"
        + "tet:label-restrictions/tet:label-restriction/tet:label-end/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment egress label restrictions step of connectivity-matrix */
  augment "/nw:networks/nw:network/nw:node/tet:te/"
        + "tet:te-node-attributes/tet:connectivity-matrices/"
        + "tet:connectivity-matrix/tet:to/"
        + "tet:label-restrictions/tet:label-restriction/tet:label-step/"
        + "tet:technology" {
    when "../../../../../../../../../"
       + "nw:network-types/tet:te-topology/"
       + "ethtetopo:eth-tran-topology" {
      description "Ethernet TE label";
    }
    description "Ethernet label.";
    case eth {
      uses etht-types:eth-label-step;
    }
  }

  /* Augment label hop of underlay primary path of connectivity-matrix */
  augment "/nw:networks/nw:network/nw:node/tet:te/"
        + "tet:te-node-attributes/tet:connectivity-matrices/"
        + "tet:connectivity-matrix/"
        + "tet:underlay/tet:primary-path/tet:path-element/"
        + "tet:type/tet:label/tet:label-hop/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of underlay backup path of connectivity-matrix */
  augment "/nw:networks/nw:network/nw:node/tet:te/"
        + "tet:te-node-attributes/tet:connectivity-matrices/"
        + "tet:connectivity-matrix/"
        + "tet:underlay/tet:backup-path/tet:path-element/"
        + "tet:type/tet:label/tet:label-hop/"
        + "tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of route-exclude of connectivity-matrix */
  augment "/nw:networks/nw:network/nw:node/tet:te/"
        + "tet:te-node-attributes/tet:connectivity-matrices/"
        + "tet:connectivity-matrix/tet:optimizations/"
        + "tet:algorithm/tet:metric/tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "ethtetopo:eth-tran-topology" {
      description "Ethernet TE label";
    }
    description "Ethernet label.";
    case eth {
      uses etht-types:eth-label;
    }
  }

  /* Augment label hop of route-include of connectivity-matrix */
  augment "/nw:networks/nw:network/nw:node/tet:te/"
        + "tet:te-node-attributes/tet:connectivity-matrices/"
        + "tet:connectivity-matrix/tet:optimizations/"
        + "tet:algorithm/tet:metric/tet:optimization-metric/"
        + "tet:explicit-route-include-objects/"
        + "tet:route-object-include-object/tet:type/"
        + "tet:label/tet:label-hop/tet:te-label/tet:technology" {
    when "../../../../../../../../../../../"
       + "nw:network-types/tet:te-topology/"
       + "ethtetopo:eth-tran-topology" {
      description "Ethernet TE label";
    }
    description "Ethernet label.";
    case eth {
      uses etht-types:eth-label;
    }
  }

  /* Augment label hop of path-route of connectivity-matrix */
  augment "/nw:networks/nw:network/nw:node/tet:te/"
        + "tet:te-node-attributes/tet:connectivity-matrices/"
        + "tet:connectivity-matrix/"
        + "tet:path-properties/tet:path-route-objects/"
        + "tet:path-route-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label restrictions of connectivity-matrices information-source */
  augment "/nw:networks/nw:network/nw:node/tet:te/"
        + "tet:information-source-entry/"
        + "tet:connectivity-matrices/tet:label-restrictions/tet:label-restriction" {
    when "../../../../../../nw:network-types/tet:te-topology/"
       + "ethtetopo:eth-tran-topology" {
      description "Ethernet TE label";
    }
    description "Ethernet label.";
    uses etht-types:eth-label-restriction;
  }

  /* Augment label restrictions start of connectivity-matrices information-source */
  augment "/nw:networks/nw:network/nw:node/tet:te/"
        + "tet:information-source-entry/"
        + "tet:connectivity-matrices/tet:label-restrictions/tet:label-restriction/"
        + "tet:label-start/tet:te-label/tet:technology" {
    when "../../../../../../../../"
       + "nw:network-types/tet:te-topology/"
       + "ethtetopo:eth-tran-topology" {
      description "Ethernet TE label";
    }
    description "Ethernet label.";
    case eth {
      uses etht-types:eth-label;
    }
  }

  /* Augment label restrictions end of connectivity-matrices information-source */
  augment "/nw:networks/nw:network/nw:node/tet:te/"
        + "tet:information-source-entry/"
        + "tet:connectivity-matrices/tet:label-restrictions/tet:label-restriction/"
        + "tet:label-end/tet:te-label/tet:technology" {
    when "../../../../../../../../"
       + "nw:network-types/tet:te-topology/"
       + "ethtetopo:eth-tran-topology" {
      description "Ethernet TE label";
    }
    description "Ethernet label.";
    case eth {
      uses etht-types:eth-label;
    }
  }

  /* Augment label restrictions step of connectivity-matrices information-source */
  augment "/nw:networks/nw:network/nw:node/tet:te/"
        + "tet:information-source-entry/"
        + "tet:connectivity-matrices/tet:label-restrictions/tet:label-restriction/"
        + "tet:label-step/tet:technology" {
    when "../../../../../../../"
       + "nw:network-types/tet:te-topology/"
       + "ethtetopo:eth-tran-topology" {
      description "Ethernet TE label";
    }
    description "Ethernet label.";
    case eth {
      uses etht-types:eth-label-step;
    }
  }

  /* Augment label hop of underlay primary path of connectivity-matrices information-source */
  augment "/nw:networks/nw:network/nw:node/tet:te/"
        + "tet:information-source-entry/tet:connectivity-matrices/"
        + "tet:underlay/tet:primary-path/tet:path-element/tet:type/"
        + "tet:label/tet:label-hop/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label hop of underlay backup path of connectivity-matrices information-source */
  augment "/nw:networks/nw:network/nw:node/tet:te/"
        + "tet:information-source-entry/tet:connectivity-matrices/"
        + "tet:underlay/tet:backup-path/tet:path-element/tet:type/"
        + "tet:label/tet:label-hop/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label hop of route-exclude of connectivity-matrices information-source */
  augment "/nw:networks/nw:network/nw:node/tet:te/"
        + "tet:information-source-entry/tet:connectivity-matrices/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of route-include of connectivity-matrices information-source */
  augment "/nw:networks/nw:network/nw:node/tet:te/"
        + "tet:information-source-entry/tet:connectivity-matrices/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of path-route of connectivity-matrices information-source */
  augment "/nw:networks/nw:network/nw:node/tet:te/"
        + "tet:information-source-entry/tet:connectivity-matrices/"
        + "tet:path-properties/tet:path-route-objects/"
        + "tet:path-route-object/tet:type/"
        + "tet:label/tet:label-hop/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment ingress label restrictions of connectivity-matrix information-source */
  augment "/nw:networks/nw:network/nw:node/tet:te/"
        + "tet:information-source-entry/tet:connectivity-matrices/"
        + "tet:connectivity-matrix/"
        + "tet:from/tet:label-restrictions/tet:label-restriction" {
    when "../../../../../../../../nw:network-types/tet:te-topology/"
       + "ethtetopo:eth-tran-topology" {
      description "Ethernet TE label";
    }
    description "Ethernet label.";
    uses etht-types:eth-label-restriction;
  }

  /* Augment ingress label restrictions start of connectivity-matrix information-source */
  augment "/nw:networks/nw:network/nw:node/tet:te/"
        + "tet:information-source-entry/tet:connectivity-matrices/"
        + "tet:connectivity-matrix/"
        + "tet:from/tet:label-restrictions/tet:label-restriction/"
        + "tet:label-start/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment ingress label restrictions end of connectivity-matrix information-source */
  augment "/nw:networks/nw:network/nw:node/tet:te/"
        + "tet:information-source-entry/tet:connectivity-matrices/"
        + "tet:connectivity-matrix/"
        + "tet:from/tet:label-restrictions/tet:label-restriction/"
        + "tet:label-end/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment ingress label restrictions step of connectivity-matrix information-source */
  augment "/nw:networks/nw:network/nw:node/tet:te/"
        + "tet:information-source-entry/tet:connectivity-matrices/"
        + "tet:connectivity-matrix/"
        + "tet:from/tet:label-restrictions/tet:label-restriction/"
        + "tet:label-step/tet:technology" {
    when "../../../../../../../../../"
       + "nw:network-types/tet:te-topology/"
       + "ethtetopo:eth-tran-topology" {
      description "Ethernet TE label";
    }
    description "Ethernet label.";
    case eth {
      uses etht-types:eth-label-step;
    }
  }

  /* Augment egress label restrictions of connectivity-matrix information-source */
  augment "/nw:networks/nw:network/nw:node/tet:te/"
        + "tet:information-source-entry/tet:connectivity-matrices/"
        + "tet:connectivity-matrix/"
        + "tet:to/tet:label-restrictions/tet:label-restriction" {
    when "../../../../../../../../nw:network-types/tet:te-topology/"
       + "ethtetopo:eth-tran-topology" {
      description "Ethernet TE label";
    }
    description "Ethernet label.";
    uses etht-types:eth-label-restriction;
  }

  /* Augment egress label restrictions start of connectivity-matrix information-source */
  augment "/nw:networks/nw:network/nw:node/tet:te/"
        + "tet:information-source-entry/tet:connectivity-matrices/"
        + "tet:connectivity-matrix/"
        + "tet:to/tet:label-restrictions/tet:label-restriction/"
        + "tet:label-start/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment egress label restrictions end of connectivity-matrix information-source */
  augment "/nw:networks/nw:network/nw:node/tet:te/"
        + "tet:information-source-entry/tet:connectivity-matrices/"
        + "tet:connectivity-matrix/"
        + "tet:to/tet:label-restrictions/tet:label-restriction/"
        + "tet:label-end/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment egress label restrictions step of connectivity-matrix information-source */
  augment "/nw:networks/nw:network/nw:node/tet:te/"
        + "tet:information-source-entry/tet:connectivity-matrices/"
        + "tet:connectivity-matrix/"
        + "tet:to/tet:label-restrictions/tet:label-restriction/"
        + "tet:label-step/tet:technology" {
    when "../../../../../../../../../"
       + "nw:network-types/tet:te-topology/"
       + "ethtetopo:eth-tran-topology" {
      description "Ethernet TE label";
    }
    description "Ethernet label.";
    case eth {
      uses etht-types:eth-label-step;
    }
  }

  /* Augment label hop of underlay primary path of connectivity-matrix information-source */
  augment "/nw:networks/nw:network/nw:node/tet:te/"
        + "tet:information-source-entry/tet:connectivity-matrices/"
        + "tet:connectivity-matrix/"
        + "tet:underlay/tet:primary-path/tet:path-element/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of underlay backup path of connectivity-matrix information-source */
  augment "/nw:networks/nw:network/nw:node/tet:te/"
        + "tet:information-source-entry/tet:connectivity-matrices/"
        + "tet:connectivity-matrix/"
        + "tet:underlay/tet:backup-path/tet:path-element/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of route-exclude of connectivity-matrix information-source */
  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "ethtetopo:eth-tran-topology" {
      description "Ethernet TE label";
    }
    description "Ethernet label.";
    case eth {
      uses etht-types:eth-label;
    }
  }

  /* Augment label hop of route-include of connectivity-matrix information-source */
  augment "/nw:networks/nw:network/nw:node/tet:te/"
        + "tet:information-source-entry/tet:connectivity-matrices/"
        + "tet:connectivity-matrix/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../../"
       + "nw:network-types/tet:te-topology/"
       + "ethtetopo:eth-tran-topology" {
      description "Ethernet TE label";
    }
    description "Ethernet label.";
    case eth {
      uses etht-types:eth-label;
    }
  }

  /* Augment label hop of path-route of connectivity-matrix information-source */
  augment "/nw:networks/nw:network/nw:node/tet:te/"
        + "tet:information-source-entry/tet:connectivity-matrices/"
        + "tet:connectivity-matrix/"
        + "tet:path-properties/tet:path-route-objects/"
        + "tet:path-route-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }
  /* Augment label restrictions of local-link-connectivities */
  augment "/nw:networks/nw:network/nw:node/tet:te/"
        + "tet:tunnel-termination-point/"
        + "tet:local-link-connectivities/"
        + "tet:label-restrictions/tet:label-restriction" {
    when "../../../../../../nw:network-types/tet:te-topology/"
       + "ethtetopo:eth-tran-topology" {
      description "Ethernet TE label";
    }
    description "Ethernet label.";
    uses etht-types:eth-label-restriction;
  }

  /* Augment label restrictions start of local-link-connectivities */
  augment "/nw:networks/nw:network/nw:node/tet:te/"
        + "tet:tunnel-termination-point/"
        + "tet:local-link-connectivities/"
        + "tet:label-restrictions/tet:label-restriction/tet:label-start/"
        + "tet:te-label/tet:technology" {
    when "../../../../../../../../nw:network-types/tet:te-topology/"
       + "ethtetopo:eth-tran-topology" {
      description "Ethernet TE label";
    }
    description "Ethernet label.";
    case eth {
      uses etht-types:eth-label;
    }
  }

  /* Augment label restrictions end of local-link-connectivities */
  augment "/nw:networks/nw:network/nw:node/tet:te/"
        + "tet:tunnel-termination-point/"
        + "tet:local-link-connectivities/"
        + "tet:label-restrictions/tet:label-restriction/tet:label-end/"
        + "tet:te-label/tet:technology"{
    when "../../../../../../../../nw:network-types/tet:te-topology/"
       + "ethtetopo:eth-tran-topology" {
      description "Ethernet TE label";
    }
    description "Ethernet label.";
    case eth {
      uses etht-types:eth-label;
    }
  }

  /* Augment label restrictions step of local-link-connectivities */
  augment "/nw:networks/nw:network/nw:node/tet:te/"
        + "tet:tunnel-termination-point/"
        + "tet:local-link-connectivities/"
        + "tet:label-restrictions/tet:label-restriction/tet:label-step/"
        + "tet:technology"{
    when "../../../../../../../nw:network-types/tet:te-topology/"
       + "ethtetopo:eth-tran-topology" {
      description "Ethernet TE label";
    }
    description "Ethernet label.";
    case eth {
      uses etht-types:eth-label-step;
    }
  }

  /* Augment label hop of underlay primary path of local-link-connectivities */
  augment "/nw:networks/nw:network/nw:node/tet:te/"
        + "tet:tunnel-termination-point/"
        + "tet:local-link-connectivities/"
        + "tet:underlay/tet:primary-path/tet:path-element/tet:type/"
        + "tet:label/tet:label-hop/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label hop of underlay backup path of local-link-connectivities */
  augment "/nw:networks/nw:network/nw:node/tet:te/"
        + "tet:tunnel-termination-point/"
        + "tet:local-link-connectivities/"
        + "tet:underlay/tet:backup-path/tet:path-element/tet:type/"
        + "tet:label/tet:label-hop/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label hop of route-exclude of local-link-connectivities */
  augment "/nw:networks/nw:network/nw:node/tet:te/"
        + "tet:tunnel-termination-point/"
        + "tet:local-link-connectivities/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of route-include of local-link-connectivities */
  augment "/nw:networks/nw:network/nw:node/tet:te/"
        + "tet:tunnel-termination-point/"
        + "tet:local-link-connectivities/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of path-route of local-link-connectivities */
  augment "/nw:networks/nw:network/nw:node/tet:te/"
        + "tet:tunnel-termination-point/"
        + "tet:local-link-connectivities/"
        + "tet:path-properties/tet:path-route-objects/"
        + "tet:path-route-object/tet:type/"
        + "tet:label/tet:label-hop/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label restrictions of local-link-connectivity (LLC) */
  augment "/nw:networks/nw:network/nw:node/tet:te/"
        + "tet:tunnel-termination-point/"
        + "tet:local-link-connectivities/"
        + "tet:local-link-connectivity/"
        + "tet:label-restrictions/tet:label-restriction" {
    when "../../../../../../../nw:network-types/tet:te-topology/"
       + "ethtetopo:eth-tran-topology" {
      description "Ethernet TE label";
    }
    description "Ethernet label.";
    uses etht-types:eth-label-restriction;
  }

  /* Augment label restrictions start of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-start/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label restrictions end of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-end/tet:te-label/tet:technology" {
    when "../../../../../../../../../"
       + "nw:network-types/tet:te-topology/"
       + "ethtetopo:eth-tran-topology" {
      description "Ethernet TE label";
    }
    description "Ethernet label.";
    case eth {
      uses etht-types:eth-label;
    }
  }

  /* Augment label restrictions step of local-link-connectivity (LLC) */
  augment "/nw:networks/nw:network/nw:node/tet:te/"
        + "tet:tunnel-termination-point/"
        + "tet:local-link-connectivities/"
        + "tet:local-link-connectivity/"
        + "tet:label-restrictions/tet:label-restriction/"
        + "tet:label-step/tet:technology" {
    when "../../../../../../../../"
       + "nw:network-types/tet:te-topology/"
       + "ethtetopo:eth-tran-topology" {
      description "Ethernet TE label";
    }
    description "Ethernet label.";
    case eth {
      uses etht-types:eth-label-step;
    }
  }

  /* Augment label hop of underlay primary path of local-link-connectivity (LLC) */
  augment "/nw:networks/nw:network/nw:node/tet:te/"
        + "tet:tunnel-termination-point/"
        + "tet:local-link-connectivities/"
        + "tet:local-link-connectivity/"
        + "tet:underlay/tet:primary-path/tet:path-element/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of underlay backup path of local-link-connectivity (LLC) */
  augment "/nw:networks/nw:network/nw:node/tet:te/"
        + "tet:tunnel-termination-point/"
        + "tet:local-link-connectivities/"
        + "tet:local-link-connectivity/"
        + "tet:underlay/tet:backup-path/tet:path-element/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of route-exclude of local-link-connectivity (LLC) */
  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-exclude-objects/"
        + "tet:route-object-exclude-object/tet:type/"
        + "tet:label/tet:label-hop/tet:te-label/tet:technology" {
    when "../../../../../../../../../../../"
       + "nw:network-types/tet:te-topology/"
       + "ethtetopo:eth-tran-topology" {
      description "Ethernet TE label";
    }
    description "Ethernet label.";
    case eth {
      uses etht-types:eth-label;
    }
  }
  /* Augment label hop of route-include of local-link-connectivity (LLC) */
  augment "/nw:networks/nw:network/nw:node/tet:te/"
        + "tet:tunnel-termination-point/"
        + "tet:local-link-connectivities/"
        + "tet:local-link-connectivity/"
        + "tet:optimizations/tet:algorithm/tet:metric/"
        + "tet:optimization-metric/"
        + "tet:explicit-route-include-objects/"
        + "tet:route-object-include-object/tet:type/"
        + "tet:label/tet:label-hop/tet:te-label/tet:technology" {
    when "../../../../../../../../../../../"
       + "nw:network-types/tet:te-topology/"
       + "ethtetopo:eth-tran-topology" {
      description "Ethernet TE label";
    }
    description "Ethernet label.";
    case eth {
      uses etht-types:eth-label;
    }
  }

  /* Augment label hop of path-route of local-link-connectivity (LLC) */
  augment "/nw:networks/nw:network/nw:node/tet:te/"
        + "tet:tunnel-termination-point/"
        + "tet:local-link-connectivities/"
        + "tet:local-link-connectivity/"
        + "tet:path-properties/tet:path-route-objects/"
        + "tet:path-route-object/tet:type/"
        + "tet:label/tet:label-hop/tet:te-label/tet:technology" {
    when "../../../../../../../../../../"
       + "nw:network-types/tet:te-topology/"
       + "ethtetopo:eth-tran-topology" {
      description "Ethernet TE label";
    }
    description "Ethernet label.";
    case eth {
      uses etht-types:eth-label;
    }
  }

  /* Augment label hop of underlay primary path of TE link */
  augment "/nw:networks/nw:network/nt:link/tet:te/"
        + "tet:te-link-attributes/"
        + "tet:underlay/tet:primary-path/tet:path-element/tet:type/"
        + "tet:label/tet:label-hop/tet:te-label/tet:technology" {
    when "../../../../../../../../"
       + "nw:network-types/tet:te-topology/"
       + "ethtetopo:eth-tran-topology" {
      description "Ethernet TE label";
    }
    description "Ethernet label.";
    case eth {
      uses etht-types:eth-label;
    }
  }

  /* Augment label hop of underlay backup path of TE link */
  augment "/nw:networks/nw:network/nt:link/tet:te/"
        + "tet:te-link-attributes/"
        + "tet:underlay/tet:backup-path/tet:path-element/tet:type/"
        + "tet:label/tet:label-hop/tet:te-label/tet:technology" {
    when "../../../../../../../../"
       + "nw:network-types/tet:te-topology/"
       + "ethtetopo:eth-tran-topology" {
      description "Ethernet TE label";
    }
    description "Ethernet label.";
    case eth {
      uses etht-types:eth-label;
    }
  }

  /* Augment label restrictions of TE link */
  augment "/nw:networks/nw:network/nt:link/tet:te/"
        + "tet:te-link-attributes/"
        + "tet:label-restrictions/tet:label-restriction" {
    when "../../../../../nw:network-types/tet:te-topology/"
       + "ethtetopo:eth-tran-topology" {
      description "Ethernet TE label";
    }
    description "Ethernet label.";
    uses etht-types:eth-label-restriction;
  }

  /* Augment label restrictions start of TE link */
  augment "/nw:networks/nw:network/nt:link/tet:te/"
        + "tet:te-link-attributes/"
        + "tet:label-restrictions/tet:label-restriction/"
        + "tet:label-start/tet:te-label/tet:technology" {
    when "../../../../../../../nw:network-types/tet:te-topology/"
       + "ethtetopo:eth-tran-topology" {
      description "Ethernet TE label";
    }
    description "Ethernet label.";
    case eth {
      uses etht-types:eth-label;
    }
  }

  /* Augment label restrictions end of TE link */
  augment "/nw:networks/nw:network/nt:link/tet:te/"
        + "tet:te-link-attributes/"
        + "tet:label-restrictions/tet:label-restriction/"
        + "tet:label-end/tet:te-label/tet:technology" {
    when "../../../../../../../nw:network-types/tet:te-topology/"
       + "ethtetopo:eth-tran-topology" {
      description "Ethernet TE label";
    }
    description "Ethernet label.";
    case eth {
      uses etht-types:eth-label;
    }
  }

  /* Augment label restrictions step of TE link */
  augment "/nw:networks/nw:network/nt:link/tet:te/"
        + "tet:te-link-attributes/"
        + "tet:label-restrictions/tet:label-restriction/"
        + "tet:label-step/tet:technology" {
    when "../../../../../../nw:network-types/tet:te-topology/"
       + "ethtetopo:eth-tran-topology" {
      description "Ethernet TE label";
    }
    description "Ethernet label.";
    case eth {
      uses etht-types:eth-label-step;
    }
  }

  /* Augment label restrictions of TE link information-source */
  augment "/nw:networks/nw:network/nt:link/tet:te/"
        + "tet:information-source-entry/"
        + "tet:label-restrictions/tet:label-restriction" {
    when "../../../../../nw:network-types/tet:te-topology/"
       + "ethtetopo:eth-tran-topology" {
      description "Ethernet TE label";
    }
    description "Ethernet label.";
    uses etht-types:eth-label-restriction;
  }

  /* Augment label restrictions start of TE link information-source */
  augment "/nw:networks/nw:network/nt:link/tet:te/"
        + "tet:information-source-entry/"
        + "tet:label-restrictions/tet:label-restriction/"
        + "tet:label-start/tet:te-label/tet:technology" {
    when "../../../../../../../nw:network-types/tet:te-topology/"
       + "ethtetopo:eth-tran-topology" {
      description "Ethernet TE label";
    }
    description "Ethernet label.";
    case eth {
      uses etht-types:eth-label;
    }
  }
  /* Augment label restrictions end of TE link information-source */
  augment "/nw:networks/nw:network/nt:link/tet:te/"
        + "tet:information-source-entry/"
        + "tet:label-restrictions/tet:label-restriction/"
        + "tet:label-end/tet:te-label/tet:technology" {
    when "../../../../../../../nw:network-types/tet:te-topology/"
       + "ethtetopo:eth-tran-topology" {
      description "Ethernet TE label";
    }
    description "Ethernet label.";
    case eth {
      uses etht-types:eth-label;
    }
  }

  /* Augment label restrictions step of TE link information-source */
  augment "/nw:networks/nw:network/nt:link/tet:te/"
        + "tet:information-source-entry/"
        + "tet:label-restrictions/tet:label-restriction/"
        + "tet:label-step/tet:technology" {
    when "../../../../../../nw:network-types/tet:te-topology/"
       + "ethtetopo:eth-tran-topology" {
      description "Ethernet TE label";
    }
    description "Ethernet label.";
    case eth {
      uses etht-types:eth-label-step;
    }
  }

  /* Augment label hop of underlay primary path of TE link template */
  augment "/nw:networks/tet:te/tet:templates/"
        + "tet:link-template/tet:te-link-attributes/"
        + "tet:underlay/tet:primary-path/tet:path-element/tet:type/"
        + "tet:label/tet:label-hop/tet:te-label/tet:technology" {
/*
    when "../../../../../../../../../../"
       + "nw:network-types/tet:te-topology/"
       + "ethtetopo:eth-tran-topology" {
      description "Ethernet TE label";
    }
*/
    description "Ethernet label.";
    case eth {
      uses etht-types:eth-label;
    }
  }

  /* Augment label hop of underlay backup path of TE link template */
  augment "/nw:networks/tet:te/tet:templates/"
        + "tet:link-template/tet:te-link-attributes/"
        + "tet:underlay/tet:backup-path/tet:path-element/tet:type/"
        + "tet:label/tet:label-hop/tet:te-label/tet:technology" {
/*
    when "../../../../../../../../../../nw:network-types/tet:te-topology/"
        + "ethtetopo:eth-tran-topology" {
      description "Ethernet TE label";
    }
*/
    description "Ethernet label.";
    case eth {
      uses etht-types:eth-label;
    }
  }

  /* Augment label restrictions of TE link template */
  augment "/nw:networks/tet:te/tet:templates/"
        + "tet:link-template/tet:te-link-attributes/"
        + "tet:label-restrictions/tet:label-restriction" {
/*
    when "../../../../../nw:network-types/tet:te-topology/"
        + "ethtetopo:eth-tran-topology" {
      description "Ethernet TE label";
    }
*/
    description "Ethernet label.";
    uses etht-types:eth-label-restriction;
  }

  /* Augment label restrictions start of TE link template */
  augment "/nw:networks/tet:te/tet:templates/"
        + "tet:link-template/tet:te-link-attributes/"
        + "tet:label-restrictions/tet:label-restriction/"
        + "tet:label-start/tet:te-label/tet:technology" {
/*
    when "../../../../../../../nw:network-types/tet:te-topology/"
        + "ethtetopo:eth-tran-topology" {
      description "Ethernet TE label";
    }
*/
    description "Ethernet label.";
    case eth {
      uses etht-types:eth-label;
    }
  }

  /* Augment label restrictions end of TE link template */
  augment "/nw:networks/tet:te/tet:templates/"
        + "tet:link-template/tet:te-link-attributes/"
        + "tet:label-restrictions/tet:label-restriction/"
        + "tet:label-end/tet:te-label/tet:technology" {
/*
    when "../../../../../../../nw:network-types/tet:te-topology/"
        + "ethtetopo:eth-tran-topology" {
      description "Ethernet TE label";
    }
*/
    description "Ethernet label.";
    case eth {
      uses etht-types:eth-label;
    }
  }

  /* Augment label restrictions step of TE link template */
  augment "/nw:networks/tet:te/tet:templates/"
        + "tet:link-template/tet:te-link-attributes/"
        + "tet:label-restrictions/tet:label-restriction/"
        + "tet:label-step/tet:technology" {
/*
    when "../../../../../../nw:network-types/tet:te-topology/"
        + "ethtetopo:eth-tran-topology" {
      description "Ethernet TE label";
    }
*/
    description "Ethernet label.";
    case eth {
      uses etht-types:eth-label-step;
    }
  }

}
