module ietf-dhcpv6-relay {
  yang-version 1.1;
  namespace "urn:ietf:params:xml:ns:yang:ietf-dhcpv6-relay";
  prefix "dhcpv6-relay";

  import ietf-inet-types {
    prefix inet;
  }

  import ietf-yang-types {
    prefix yang;
  }

  import ietf-dhcpv6-common {
    prefix dhcpv6-common;
  }

  import ietf-interfaces {
    prefix if;
  }

  organization
    "IETF DHC (Dynamic Host Configuration) Working group";

  contact
    "cuiyong@tsinghua.edu.cn
    lh.sunlinh@gmail.com
    ian.farrer@telekom.de
    sladjana.zechlin@telekom.de
    hezihao9512@gmail.com
    godfryd@isc.org";

  description
    "This YANG module defines components necessary for the
    configuration and management of DHCPv6 relays.

    Copyright (c) 2018 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8513; see
    the RFC itself for full legal notices.";

  revision 2020-05-26 {
    description "Version update for draft -11 publication and
      to align revisions across the different modules.";
    reference "I-D: draft-ietf-dhc-dhcpv6-yang-11";
  }

  revision 2019-09-20 {
    description "";
    reference "I-D: draft-ietf-dhc-dhcpv6-yang-10";
  }

  revision 2018-03-04 {
    description "Resolved most issues on the DHC official
      github";
    reference "I-D: draft-ietf-dhc-dhcpv6-yang";
  }

  revision 2017-12-22 {
    description
      "Resolve most issues on Ians Github.";
    reference
      "I-D: draft-ietf-dhc-dhcpv6-yang";
  }

  revision 2017-11-24 {
    description
      "First version of the separated relay specific
      YANG model.";
    reference
      "I-D: draft-ietf-dhc-dhcpv6-yang";
  }

  /*
   * Indentities
   */

  identity relay {
    base "dhcpv6-common:dhcpv6-node";
    description "DHCPv6 relay agent identity.";
  }

  leaf dhcpv6-node-type {
    description "Type for a DHCPv6 relay.";
    type identityref {
      base "dhcpv6-relay:relay";
    }
  }

  /*
   * Features
   */

  feature prefix-delegation {
    description "Enable if the relay functions as a delegating router
      for DHCPv6 prefix delegation.";
  }

  /*
   * Groupings
   */

  grouping pd-lease-state {
    description "State data for the relay.";
    list pd-leases {
      config false;
      key ia-pd-prefix;
      description "Information about an active IA_PD prefix
        delegation.";
     leaf ia-pd-prefix {
        description "Prefix that is delegated.";
        type inet:ipv6-prefix;
      }
      leaf last-renew {
        description "Time of the last successful refresh or renew
          of the delegated prefix.";
        type yang:date-and-time;
      }
      leaf client-peer-address {
        description "Peer-address of the client.";
        type inet:ipv6-address;
      }
      leaf client-duid {
        description "DUID of the leasing client.";
        type binary;
      }
      leaf server-duid {
        description "DUID of the delegating server.";
        type binary;
      }
    }
  }

  grouping message-statistics {
    description "Contains counters for the different DHCPv6
      message types.";
    leaf solicit-received-count {
      config "false";
      type uint32;
      description "Number of Solicit (1) messages received.";
    }
    leaf advertise-sent-count {
      config "false";
      type uint32;
      description "Number of Advertise (2) messages sent.";
    }
    leaf request-received-count {
      config "false";
      type uint32;
      description "Number of Request (3) messages received.";
    }
    leaf confirm-received-count {
      config "false";
      type uint32;
      description "Number of Confirm (4) messages received.";
    }
    leaf renew-received-count {
      config "false";
      type uint32;
      description "Number of Renew (5) messages received.";
    }
    leaf rebind-received-count {
      config "false";
      type uint32;
      description "Number of Rebind (6) messages received.";
    }
    leaf reply-sent-count {
      config "false";
      type uint32;
      description "Number of Reply (7) messages received.";
    }
    leaf release-received-count {
      config "false";
      type uint32;
      description "Number of Release (8) messages sent.";
    }
    leaf decline-received-count {
      config "false";
      type uint32;
      description "Number of Decline (9) messages sent.";
    }
    leaf reconfigure-sent-count {
      config "false";
      type uint32;
      description "Number of Reconfigure (10) messages sent.";
    }
    leaf information-request-received-count {
      config "false";
      type uint32;
      description "Number of Information-request (11) messages
        received.";
    }
    leaf unknown-message-received-count {
      config "false";
      type uint32;
      description
        "Number of messages of unknown type that have been
           received.";
    }
    leaf unknown-message-sent-count {
      config "false";
      type uint32;
      description
        "Number of messages of unknown type that have been sent.";
    }
    leaf discarded-message-count {
      config "false";
      type uint32;
      description
        "Number of messages that have been discarded for any
           reason.";
    }
  }

  grouping global-statistics {
    leaf relay-forward-sent-count {
      config "false";
      type uint32;
      description "Number of Relay-forward (12) messages sent.";
    }
    leaf relay-forward-received-count {
      config "false";
      type uint32;
      description "Number of Relay-forward (12) messages received.";
    }
    leaf relay-reply-received-count {
      config "false";
      type uint32;
      description "Number of Relay-reply (13) messages received.";
    }
    leaf relay-forward-unknown-sent-count {
      config "false";
      type uint32;
      description "Number of Relay-forward (12) messages containing
        a message of unknown type sent.";
    }
    leaf relay-forward-unknown-received-count {
      config "false";
      type uint32;
      description "Number of Relay-forward (12) messages containing
        a message of unknown type received.";
    }
    leaf discarded-message-count {
      config "false";
      type uint32;
      description "Number of messages that have been discarded
        for any reason.";
    }
  }

  /*
   * Data Nodes
   */

  container dhcpv6-relay {
    description
      "This container contains the configuration data nodes for
      the relay.";
    list relay-if {
      key if-name;
      leaf if-name {
        type if:interface-ref;
      }
      leaf-list destination-addresses {
        type inet:ipv6-address;
        description "Each DHCPv6 relay agent may be configured with
          a list of destination addresses for relayed messages.
          The list may include unicast addresses, multicast addresses
          or other valid addresses.";
      }
      leaf link-address {
        description "An address that may be used by the server
          to identify the link on which the client is located.";
        type binary {
          length "0..16";
        }
      }
      container relay-options {
        description "Definitions for DHCPv6 options that can be sent
          by the relay are augmented to this location from other YANG
          modules as required.";
      }
      uses message-statistics;
      container prefix-delegation {
        description "Controls and holds state information for prefix
          delegation.";
        presence "Enables prefix delegation for this interface.";
        if-feature prefix-delegation;
        uses pd-lease-state;
      }
    }
    uses global-statistics;
  }

  /*
   * Notifications
   */

  notification relay-event {
    description
      "DHCPv6 relay event notifications.";
    container topology-change {
      description "Raised if the entry for and interface with DHCPv6
        related configuration or state is removed from
        if:interface-refs.";
      leaf relay-if-name {
        description "Name of the interface that has been removed.";
        type leafref {
          path "/dhcpv6-relay/relay-if/if-name";
        }
      }
      leaf last-ipv6-addr {
        type inet:ipv6-address;
        description "Last IPv6 address configured on the interface.";
      }
    }
  }
}
