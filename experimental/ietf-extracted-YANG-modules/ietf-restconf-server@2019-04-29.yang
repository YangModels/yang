module ietf-restconf-server {
  yang-version 1.1;
  namespace "urn:ietf:params:xml:ns:yang:ietf-restconf-server";
  prefix rcs;

  import ietf-yang-types {
    prefix yang;
    reference
      "RFC 6991: Common YANG Data Types";
  }

  import ietf-x509-cert-to-name {
    prefix x509c2n;
    reference
      "RFC 7407: A YANG Data Model for SNMP Configuration";
  }

  import ietf-tcp-client {
    prefix tcpc;
    reference
      "RFC AAAA: YANG Groupings for TCP Clients and TCP Servers";
  }

  import ietf-tcp-server {
    prefix tcps;
    reference
      "RFC AAAA: YANG Groupings for TCP Clients and TCP Servers";
  }

  import ietf-tls-server {
    prefix tlss;
    reference
      "RFC BBBB: YANG Groupings for TLS Clients and TLS Servers";
  }

  import ietf-http-server {
    prefix https;
    reference
      "RFC CCCC: YANG Groupings for HTTP Clients and HTTP Servers";
  }

  organization
    "IETF NETCONF (Network Configuration) Working Group";

  contact
    "WG Web:   <http://datatracker.ietf.org/wg/netconf/>
     WG List:  <mailto:netconf@ietf.org>
     Author:   Kent Watsen <mailto:kent+ietf@watsen.net>
     Author:   Gary Wu <mailto:garywu@cisco.com>
     Author:   Juergen Schoenwaelder
               <mailto:j.schoenwaelder@jacobs-university.de>";

  description
    "This module contains a collection of YANG definitions
     for configuring RESTCONF servers.

     Copyright (c) 2019 IETF Trust and the persons identified
     as authors of the code. All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.;

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2019-04-29 {
    description
      "Initial version";
    reference
      "RFC XXXX: RESTCONF Client and Server Models";
  }

  // Features

  feature https-listen {
    description
      "The 'https-listen' feature indicates that the RESTCONF server
       supports opening a port to listen for incoming RESTCONF
       client connections.  This feature exists as HTTPS might not
       be a mandatory to implement transport in the future.";
    reference
      "RFC 8040: RESTCONF Protocol";
  }

  feature https-call-home {
    description
      "The 'https-call-home' feature indicates that the RESTCONF
       server supports initiating connections to RESTCONF clients.
       This feature exists as not all RESTCONF servers may
       support RESTCONF call home.";
    reference
      "RFC 8071: NETCONF Call Home and RESTCONF Call Home";
  }

  // Groupings

  grouping restconf-server-grouping {
    description
      "Top-level grouping for RESTCONF server configuration.";
    container listen {
      if-feature "https-listen";
      presence
        "Enables the RESTCONF server to listen for RESTCONF
         client connections.";
      description "Configures listen behavior";
      list endpoint {
        key "name";
        min-elements 1;
        description
          "List of endpoints to listen for RESTCONF connections.";
        leaf name {
          type string;
          description
            "An arbitrary name for the RESTCONF listen endpoint.";
        }
        choice transport {
          mandatory true;
          description
            "Selects between available transports. This is a
             'choice' statement so as to support additional
             transport options to be augmented in.";
          case https {
            if-feature "https-listen";
            container https {
              description
                "HTTPS-specific listening configuration for inbound
                 connections.";
              container tcp-server-parameters {
                description
                  "A wrapper around the TCP server parameters
                   to avoid name collisions.";
                uses tcps:tcp-server-grouping {
                  refine "local-port" {
                    default "443";
                    description
                      "The RESTCONF server will listen on the IANA-
                       assigned well-known port value for 'https'
                       (443) if no value is specified.";
                  }
                }
              }
              container tls-server-parameters {
                description
                  "A wrapper around the TLS server parameters
                   to avoid name collisions.";
                uses tlss:tls-server-grouping {
/*
                  refine
                    "client-authentication" {
                    //must 'pinned-ca-certs or pinned-client-certs';
                    //presence "Enables TLS-level authentication
                    //          using client certificates.";
                    description
                      "RESTCONF servers MUST be able to validate
                       clients.";
                  }
*/
                  augment
                    "client-authentication/local-or-external/local" {
                    description
                      "Augments in the cert-to-name structure,
                       so the RESTCONF server can map TLS-layer
                       client certificates to RESTCONF usernames.";
                    container cert-maps {
                      /*must '../pinned-ca-certs
                              or ../pinned-client-certs'; */
                      uses x509c2n:cert-to-name;
                      description
                        "The cert-maps container is used by a TLS-
                         based RESTCONF server to map the RESTCONF
                         client's presented X.509 certificate to
                         a RESTCONF username.  If no matching and
                         valid cert-to-name list entry can be found,
                         then the RESTCONF server MUST close the
                         connection, and MUST NOT accept RESTCONF
                         messages over it.";
                      reference
                        "RFC 7407: A YANG Data Model for SNMP
                                   Configuration.";
                    }
                    //leaf optional {
                    //  type empty;
                    //}
                  }
                }
              }
              container http-server-parameters {
                description
                  "A wrapper around the HTTP server parameters
                   to avoid name collisions.";
                uses https:http-server-grouping;
                /* {
                  augment "http-server-parameters" {   // HELP!!!
                    description
                      "Augments in a flag indicating that the
                       RESCONF server MUST authenticate the
                       RESTCONF client using the HTTP 'basic'
                       authentication scheme.  How the RESTCONF
                       server defines users and passwords is
                       outside the scope of this data model.";
                    container client-authentication {
                      leaf optional {
                        type empty;
                      }
                      choice configured-or-external {
                        mandatory true;
                        case external {
                          leaf user-auth-defined-elsewhere {
                            type empty;
                          }
                        }
                      }
                    }
                  }
                }
                */
              }
            } // https container
          } // tls case
        } // transport
      } // endpoint
    } // listen

    container call-home {
      if-feature "https-call-home";
      presence
        "Enables the RESTCONF server to initiate the underlying
         transport connection to RESTCONF clients.";
      description "Configures call-home behavior";
      list restconf-client {
        key "name";
        min-elements 1;
        description
          "List of RESTCONF clients the RESTCONF server is to
           initiate call-home connections to in parallel.";
        leaf name {
          type string;
          description
            "An arbitrary name for the remote RESTCONF client.";
        }
        container endpoints {
          description
            "Container for the list of endpoints.";
          list endpoint {
            key "name";
            min-elements 1;
            ordered-by user;
            description
              "User-ordered list of endpoints for this RESTCONF
               client.  Defining more than one enables high-
               availability.";
            leaf name {
              type string;
              description
                "An arbitrary name for this endpoint.";
            }
            choice transport {
              mandatory true;
              description
                "Selects between available transports. This is a
                 'choice' statement so as to support additional
                 transport options to be augmented in.";
              case https {
                if-feature "https-call-home";
                container https {
                  description
                    "Specifies HTTPS-specific call-home transport
                     configuration.";
                  container tcp-client-parameters {
                    description
                      "A wrapper around the TCP client parameters
                       to avoid name collisions.";
                    uses tcpc:tcp-client-grouping {
                      refine "remote-port" {
                        default "4336";
                        description
                          "The RESTCONF server will attempt to
                           connect to the IANA-assigned well-known
                           port for 'restconf-ch-tls' (4336) if no
                           value is specified.";
                      }
                    }
                  }
                  container tls-server-parameters {
                    description
                      "A wrapper around the TLS server parameters
                       to avoid name collisions.";
                    uses tlss:tls-server-grouping {
                      refine "client-authentication" {
                        /*must 'pinned-ca-certs
                                or pinned-client-certs'; */
                        description
                          "RESTCONF servers MUST be able to validate
                           clients.";
                      }
                      augment "client-authentication" {
                        description
                          "Augments in the cert-to-name structure,
                           so the RESTCONF server can map TLS-layer
                           client certificates to RESTCONF
                           usernames.";
                        container cert-maps {
                          uses x509c2n:cert-to-name;
                          description
                            "The cert-maps container is used by a
                             TLS-based RESTCONF server to map the
                             RESTCONF client's presented X.509
                             certificate to a RESTCONF username. If
                             no matching and valid cert-to-name list
                             entry can be found, then the RESTCONF
                             server MUST close the connection, and
                             MUST NOT accept RESTCONF messages over
                             it.";
                          reference
                            "RFC 7407: A YANG Data Model for SNMP
                             Configuration.";
                        }
                      }
                    }
                  }
                  container http-server-parameters {
                    description
                      "A wrapper around the HTTP server parameters
                       to avoid name collisions.";
                    uses https:http-server-grouping;
                  }
                }
              }
            } // transport
          } // endpoint
        } // endpoints
        container connection-type {
          description
            "Indicates the RESTCONF server's preference for how the
             RESTCONF connection is maintained.";
          choice connection-type {
            mandatory true;
            description
              "Selects between available connection types.";
            case persistent-connection {
              container persistent {
                presence "Indicates that a persistent connection is
                          to be maintained.";
                description
                  "Maintain a persistent connection to the RESTCONF
                   client. If the connection goes down, immediately
                   start trying to reconnect to the RESTCONF server,
                   using the reconnection strategy.

                   This connection type minimizes any RESTCONF
                   client to RESTCONF server data-transfer delay,
                   albeit at the expense of holding resources
                   longer.";
              }
            }
            case periodic-connection {
              container periodic {
                presence "Indicates that a periodic connection is
                          to be maintained.";
                description
                  "Periodically connect to the RESTCONF client.

                   This connection type increases resource
                   utilization, albeit with increased delay in
                   RESTCONF client to RESTCONF client interactions.

                   The RESTCONF client SHOULD gracefully close
                   the underlying TLS connection upon completing
                   planned activities.  If the underlying TLS
                   connection is not closed gracefully, the
                   RESTCONF server MUST immediately attempt
                   to reestablish the connection.

                   In the case that the previous connection is
                   still active (i.e., the RESTCONF client has not
                   closed it yet), establishing a new connection
                   is NOT RECOMMENDED.";

                leaf period {
                  type uint16;
                  units "minutes";
                  default "60";
                  description
                    "Duration of time between periodic connections.";
                }
                leaf anchor-time {
                  type yang:date-and-time {
                    // constrained to minute-level granularity
                    pattern '\d{4}-\d{2}-\d{2}T\d{2}:\d{2}'
                          + '(Z|[\+\-]\d{2}:\d{2})';
                  }
                  description
                    "Designates a timestamp before or after which a
                     series of periodic connections are determined.
                     The periodic connections occur at a whole
                     multiple interval from the anchor time.  For
                     example, for an anchor time is 15 minutes past
                     midnight and a period interval of 24 hours, then
                     a periodic connection will occur 15 minutes past
                     midnight everyday.";
                }
                leaf idle-timeout {
                  type uint16;
                  units "seconds";
                  default 120; // two minutes
                  description
                    "Specifies the maximum number of seconds that
                     the underlying TCP session may remain idle.
                     A TCP session will be dropped if it is idle
                     for an interval longer than this number of
                     seconds.  If set to zero, then the server
                     will never drop a session because it is idle.";
                }
              }
            }
          }
        }
        container reconnect-strategy {
          description
            "The reconnection strategy directs how a RESTCONF server
             reconnects to a RESTCONF client after discovering its
             connection to the client has dropped, even if due to a
             reboot.  The RESTCONF server starts with the specified
             endpoint and tries to connect to it max-attempts times
             before trying the next endpoint in the list (round
             robin).";
          leaf start-with {
            type enumeration {
              enum first-listed {
                description
                  "Indicates that reconnections should start with
                   the first endpoint listed.";
              }
              enum last-connected {
                description
                  "Indicates that reconnections should start with
                   the endpoint last connected to.  If no previous
                   connection has ever been established, then the
                   first endpoint configured is used.   RESTCONF
                   servers SHOULD be able to remember the last
                   endpoint connected to across reboots.";
              }
              enum random-selection {
                description
                  "Indicates that reconnections should start with
                   a random endpoint.";
              }
            }
            default "first-listed";
            description
              "Specifies which of the RESTCONF client's endpoints
               the RESTCONF server should start with when trying
               to connect to the RESTCONF client.";
          }
          leaf max-attempts {
            type uint8 {
              range "1..max";
            }
            default "3";
            description
              "Specifies the number times the RESTCONF server tries
               to connect to a specific endpoint before moving on to
               the next endpoint in the list (round robin).";
          }
        }
      } // restconf-client
    } // call-home
  } // restconf-server-grouping

  // Protocol accessible node, for servers that implement this
  // module.

  container restconf-server {
    uses restconf-server-grouping;
    description
      "Top-level container for RESTCONF server configuration.";
  }
}
