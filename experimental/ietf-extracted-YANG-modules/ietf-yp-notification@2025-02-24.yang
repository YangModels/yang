module ietf-yp-notification {
  yang-version 1.1;
  namespace "urn:ietf:params:xml:ns:yang:ietf-yp-notification";
  prefix inotenv;
  import ietf-yang-types {
    prefix yang;
    reference
      "RFC 6991: Common YANG Data Types";
  }
  import ietf-inet-types {
    prefix inet;
    reference
      "RFC 6991: Common YANG Data Types";
  }
  import ietf-subscribed-notifications {
    prefix sn;
    reference
      "RFC 8639: Subscription to YANG Notifications";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }
  import ietf-yang-structure-ext {
    prefix sx;
    reference
      "RFC 8791: YANG Data Structure Extensions";
  }

  organization "IETF NETCONF (Network Configuration) Working Group";
  contact
    "WG Web:   <https://datatracker.ietf.org/group/netconf/>
     WG List:  <mailto:netconf@ietf.org>

     Authors:  Alex Huang Feng
               <mailto:alex.huang-feng@insa-lyon.fr>
               Pierre Francois
               <mailto:pierre.francois@insa-lyon.fr>
               Thomas Graf
               <mailto:thomas.graf@swisscom.com>
               Benoit Claise
               <mailto:benoit.claise@huawei.com>";

  description
    "Defines a notification header for Subscribed Notifications
    [RFC8639] and YANG-Push [RFC8641]. When this notification header
    is enabled through configuration, the root container of the 
    notification is encoded as defined in RFCXXX.

    This module can be used to validate XML encoded notifications
    [RFC7950], JSON encoded messages [RFC7951] and CBOR encoded
    messages [RFC9254]. Refer to Section Y of RFC XXXX for more
    details.

    Copyright (c) 2025 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.";

  revision 2025-02-24 {
    description
      "First revision";
    reference
      "RFC XXXX: YANG-Push Notification Envelope";
  }

  identity notif-envelope-error {
    description 
      "Base identify for errors found while attempting to
      change the value of the leaf 'enable-notification-envelope'.";
  }

  grouping notif-env-capabilities {
    description
      "This grouping defines the capabilities for
      the notification-envelope defined in RFC XXXX
      and the different supported metadata.";
    leaf notification-envelope {
      type boolean;
      default false;
      description
        "Supports YANG-Push to use the notification-envelope 
        defined in RFC XXXX.";
    }
    container metadata {
      description 
        "Container with the supported optional metadata by the
        YANG-Push publisher.";
      leaf hostname-sequence-number {
        type boolean;
        default false;
        description
          "Supports hostname and sequence-number
          in the YANG-Push notifications as defined in the
          YANG-Push notification-envelope in RFC XXXX.";
      }
    }
  }

  sx:structure envelope {
    leaf event-time {
      type yang:date-and-time;
      mandatory true;
      description
        "The date and time the event was generated by the event
        source. This parameter is of type dateTime and compliant
        to [RFC3339].";
    }
    leaf hostname {
      type inet:host;
      description
        "The hostname of the network node according to
        [RFC1213]. This value is usually configured on the node
        by the administrator to uniquely identify the node in
        the network.";
    }
    leaf sequence-number {
      type yang:counter32;
      description
        "Unique sequence number as described in [RFC9187] for each
        published message.";
    }
    anydata contents {
      description 
        "This contains the values defined by the 'notification'
        statement unchanged.";
    }
  }

  // Subscription container
  augment "/sn:subscriptions" {
    description
      "This augmentation adds the configuration switches for
      enabling the notification envelope and metadatas.";
    leaf enable-notification-envelope {
      type boolean;
      default false;
      description
        "Enables YANG-Push to use the notification-envelope 
        defined in RFC XXXX.";
    }
    container metadata {
      description 
        "Container for configuring optional metadata.";
    }
  }

  // YANG-Push Capabilities extension
  augment "/sysc:system-capabilities/notc:subscription-capabilities" {
    description
      "Extension to the subscription-capabilities model to enable
      clients to learn whether the publisher supports the 
      notification-envelope";

    container notification-metadata {
      description 
        "Adds the notification metadata capabilities to subscription
        capabilities.";
      uses notif-env-capabilities;
    }
  }
}
