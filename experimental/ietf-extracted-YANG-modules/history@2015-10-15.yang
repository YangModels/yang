submodule history {
  belongs-to sfc-control-planes {
    prefix sfc-h;
  }
  import ietf-yang-types {
    prefix yang;
    revision-date 2013-07-15;
  }
  organization "ETRI.";
  contact
  "M-K. Shin mkshin@etri.re.kr
   M-J Choi mjchoi@kangwon.ac.kr";
  description
  "This module shows statistical information related performance
   and faults in accordance with SFCs and SFPs.";
  revision 2015-10-15 {
      reference
      "draft-shin-sfc-control-plane-yang-00 -
      Yang Data Model for Service Function Chaining Control Plane";
  }
  container performance {
    description
    "It monitors and stores time series data related performance."
    ;
    list Performance {
      key name;
      description
      "The name of service function.";
      leaf name {
        type string;
        description
        "The name of service function.";
      }
      leaf time {
        type yang:date-and-time;
        description
        "The performance monitoring date.";
      }
      leaf aliveness {
        type boolean;
        description
        "The aliveness flag of the service function.";
      }
      container resource-utilization {
        description
        "To be defined.";
        leaf packet-rate {
          type uint8;
          description
          "Percentage of current package rate utilization.";
        }
        leaf bandwidth {
          type uint8;
          description
          "Percentage of bandwidth utilization.";
        }
        leaf cpu-usage {
          type uint8;
          description
          "Percentage of CPU utilization.";
        }
        leaf memory-usage {
          type uint8;
          description
          "Percentage of memory utilization.";
        }
        leaf available-memory {
          type uint8;
          description
          "Available memory size of the service function in MB.";
        }
        leaf rib {
          type uint8;
          description
          "Percentage of Routing Information Table utilization.";
        }
        leaf fib {
          type uint8;
          description
          "Percentage of Forwarding Information Table
           utilization.";
        }
        leaf sf-ports-bandwidth {
          type uint8;
          description
          "Percentage of the port's supported bandwidth
           utilization.";
        }
      }
    }
  }
  container fault {
    description
    "It monitors and stores time series data related to faults
     and events." ;
    list fault {
      key fault-name;
      description
      "The name occurred fault.";
      leaf fault-name {
        type string;
        description
        "The name occurred fault.";
      }
      leaf fault-occurrence-time {
      type yang:date-and-time;
        description
        "The time of the fault occurrence.";
      }
      leaf fault-type {
        type string;
        description
        "The type of occurred fault.";
      }
      leaf fault-occurrence-location {
        type string;
        description
        "The location of fault occurrence.";
      }
      leaf fault-handling-action {
        type string;
        description
        "The fault handing action: drop, bypass, use alternate
         node.";
      }
   }
}
}
