submodule ietf-snmp-target {

  belongs-to ietf-snmp {
    prefix snmp;
  }

  import ietf-inet-types {
    prefix inet;
  }

  include ietf-snmp-common;

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";

  description
    "This submodule contains a collection of YANG definitions
     for configuring SNMP targets.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  reference
    "RFC3413: Simple Network Management Protocol (SNMP)
              Applications";

  // RFC Ed.: update the date below with the date of RFC publication
  // and remove this note.

  revision 2012-06-05 {
    description
      "Initial revision.";
    reference
      "RFC XXXX: A YANG Data Model for SNMP Configuration";
  }

  augment /snmp:snmp {

    list target {
      key name;
      description
        "List of targets.";
      reference "SNMP-TARGET-MIB.snmpTargetAddrTable";

      leaf name {
        type snmp:identifier;
        description
          "Identifies the target.";
        reference "SNMP-TARGET-MIB.snmpTargetAddrName";
      }
      choice transport {
        mandatory true;
        description
          "Transport address of the target.

           The snmpTargetAddrTDomain and snmpTargetAddrTAddress
           objects are mapped to transport-specific YANG nodes.  Each
           transport is configured as a separate case in this
           choice. Submodules providing configuration for additional
           transports are expected to augment this choice.";
        reference "SNMP-TARGET-MIB.snmpTargetAddrTDomain
                   SNMP-TARGET-MIB.snmpTargetAddrTAddress";
        case udp {
          reference "SNMPv2-TM.snmpUDPDomain
                     TRANSPORT-ADDRESS-MIB.transportDomainUdpIpv4
                     TRANSPORT-ADDRESS-MIB.transportDomainUdpIpv4z
                     TRANSPORT-ADDRESS-MIB.transportDomainUdpIpv6
                     TRANSPORT-ADDRESS-MIB.transportDomainUdpIpv6z";
          container udp {
            leaf ip {
              type inet:ip-address;
              mandatory true;
              reference "SNMP-TARGET-MIB.snmpTargetAddrTAddress";
            }
            leaf port {
              type inet:port-number;
              default 162;
              description
                "UDP port number";
              reference "SNMP-TARGET-MIB.snmpTargetAddrTAddress";
            }
            leaf prefix-length {
              type uint8;
              description
                "The value of this leaf must match the value of
                 ../snmp:ip. If ../snmp:ip contains an ipv4 address,
                 this leaf must be less than or equal to 32.  If it
                 contains an ipv6 address, it must be less than or
                 equal to 128.

                 Note that the prefix-length is currently only used
                 by the Community-based Security Model to filter
                 incoming messages. Furthermore, the prefix-length
                 filtering does not cover all possible filters
                 supported by the corresponding MIB object.";
              reference "SNMP-COMMUNITY-MIB.snmpTargetAddrTMask";
            }
          }
        }
      }
      leaf-list tag {
        type snmp:identifier;
        description
          "List of tag values used to select target address.";
        reference "SNMP-TARGET-MIB.snmpTargetAddrTagList";
      }
      leaf timeout {
        type uint32;
        units "0.01 seconds";
        default 1500;
        description
          "Needed only if this target can receive
           InformRequest-PDUs.";
        reference "SNMP-TARGET-MIB.snmpTargetAddrTimeout";
      }
      leaf retries {
        type uint8;
        default 3;
        description
          "Needed only if this target can receive
           InformRequest-PDUs.";
        reference "SNMP-TARGET-MIB.snmpTargetAddrRetryCount";
      }
      choice params {
        description
          "This choice is augmented with case nodes containing
           security model specific configuration parameters.  Each
           such case represents one entry in the
           snmpTargetParamsTable.

           When the snmpTargetAddrParams object contains a reference
           to a non-existing snmpTargetParamsEntry, this choice does
           not contain any case, and vice versa.";
        reference "SNMP-TARGET-MIB.snmpTargetAddrParams
                   SNMP-TARGET-MIB.snmpTargetParamsTable";
      }
    }
  }
}
