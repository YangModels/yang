module ietf-network-inventory-sw-ext {
  yang-version 1.1;
  namespace
    "urn:ietf:params:xml:ns:yang:ietf-network-inventory-sw-ext";
  prefix nwis;

  import ietf-yang-types {
    prefix yang;
    reference
      "RFC 6991: Common YANG Data Types";
  }
  import ietf-network-inventory {
    prefix nwi;
    reference
      "RFCAAAA: A YANG Data Model for Network Inventory";
  }

  organization
    "IETF Network Inventory YANG (ivy) Working Group";
  contact
    "WG Web:   <https://datatracker.ietf.org/wg/ivy>
     WG List:  <mailto:inventory-yang@ietf.org>

     Editor: Bo Wu
             <lana.wubo@huawei.com>
     Editor: Cheng Zhou
          <zhouchengyjy@chinamobile.com>
     Editor: Qin Wu
             <bill.wu@huawei.com>
     Editor: Mohamed Boucadair
             <mohamed.boucadair@orange.com>";
  description
    "This YANG module defines a model for network inventory software
     extensions.

     Copyright (c) 2025 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2025-06-10 {
    description
      "Initial version";
    reference
      "RFC XXXX: A YANG Data Model for Network Inventory Software
                 Extensions.";
  }

  identity ne-nonphysical {
    base nwi:ne-type;
    description
      "A non-physical network element (NE) is a network device that
       support network protocols and functions, e.g., router,
       firewall, and controller, which can reside in any network or
       compute devices, such as a server in Data Center (DC),
       server-based virtual machine (VM), or server-based
       container.";
  }

  identity ne-software {
    base ne-nonphysical;
    description
      "A software NE refers to a a network device residing in any
       network or compute devices, such as a physical server
       (or 'bare metal') in DC. Examples of software NEs are
       network controllers.";
  }

  identity ne-virtual {
    base ne-nonphysical;
    description
      "A virtual NE refers to a network device residing within
       server-based Virtual Machine (VM) implementing a virtual
       network function (VNF). Examples of virtual NEs are
       virtual routers, virtual firewalls.";
  }

  identity ne-container {
    base ne-nonphysical;
    description
      "A container NE refers to a network device residing within
       server-based container implementing a Containerized
       network function (CNF).";
  }

  identity software-component {
    base nwi:non-hardware-component-class;
    description
      "Base identity for software components in a managed
       device.";
  }

  identity operating-system {
    base software-component;
    description
      "OS software type.";
  }

  identity operating-system-patch {
    base software-component;
    description
      "An operating system update - which should be a subcomponent
       of the `operating-system` running on a component. A patch is
       defined to be a set of software changes that are atomically
       installed (and uninstalled) together. ";
  }

  identity bios {
    base software-component;
    description
      "Legacy BIOS or UEFI firmware interface responsible for
       initializing hardware components and first stage boot
       loader.";
  }

  identity boot-loader {
    base software-component;
    description
      "Software layer responsible for loading and booting the
       device OS or network OS.";
  }

  identity software-module {
    base software-component;
    description
      "A base identity for software modules installed and/or
       running on the device.  Modules include user-space programs
       and kernel modules that provide specific functionality.";
  }

  identity software-status {
    description
      "Base identity for software status.";
  }

  identity software-installed {
    base software-status;
    description
      "Software status is Installed.";
  }

  identity software-activated {
    base software-status;
    description
      "Software status is Activated.";
  }

  grouping software-info-grouping {
    description
      "Specific attributes applicable to Software.";
    leaf status {
      type identityref {
        base software-status;
      }
      description
        "Software status.";
    }
    leaf installation-time {
      type yang:date-and-time;
      description
        "Date and time the current revision last changed.";
    }
    leaf activation-time {
      type yang:date-and-time;
      description
        "Date and time the current revision last changed.";
    }
  }

  /* Main blocks */

  augment "/nwi:network-inventory/nwi:network-elements"
        + "/nwi:network-element" {
    description
      "Augment network element (NE) attributes.";
    container software-attributes {
      when "derived-from-or-self(../nwi:ne-type,'ne-software')";
      config false;
      description
        "Container for the attributes applicable only to software
         Network Elements (NEs).";
      uses software-info-grouping;
    }
  }

  augment "/nwi:network-inventory/nwi:network-elements/"
        + "nwi:network-element/nwi:components/nwi:component" {
    description
      "Augment software component attributes.";
    container software-module-attributes {
      when
        "derived-from-or-self(../nwi:class,'software-module')";
      config false;
      description
        "This container contains some attributes belong to
         software modules only.";
      uses software-info-grouping;
    }
  }
}
