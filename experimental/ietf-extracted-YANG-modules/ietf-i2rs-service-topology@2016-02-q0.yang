module ietf-i2rs-service-topology{
 namespace "urn:ietf:params:xml:ns:yang:ietf-i2rs-service-topology";
 prefix i2rs-st;

   import ietf-inet-types {
   prefix inet;
 }

  import ietf-network {
    prefix nw;
  }
  import ietf-network-topology {
    prefix "nt";
  }

   organization "IETF";
         contact
    "email: shares@ndzh.com;
     email: linda.dunbar@huawei.com;
        ";

  description
    "This module defines a model for the service topology.
         This service model imports
         - ietf-network and ietf-network-topology from
            draft-ietf-i2rs-yang-network-topo-02.txt,
         - ietf-routing from draft-ietf-netmod-routing-cfg,
         - ietf-l3vpn-svc from
             draft-ietf-l3sm-l3vpn-service-model.
                 (not defined yet )
         ";

 revision 2016-02-12 {
   description
     "Version 1 - initial version;
          Version 2 - yang format fixed
          Version 3 - errro in xml file
          version 4 - remove next-hops attribute.
          version 5- links to top-level attributes.
           version 6 - Remove extra parameters.";

    reference "draft-hares-i2rs-service-topo-dm-05.txt";
 }

     identity svc-topo-flag-identity {
       description "Base type for svc flags";
       }
     identity l3vpn-svc-topo {
       base svc-topo-flag-identity;
       description "L3VPN service type";
      }
     identity l2vpn-svc-topo {
       base svc-topo-flag-identity;
       description "L2VPN service type";
      }
      identity EVPN-svc-topo {
       base svc-topo-flag-identity;
       description "EVPN service type";
      }
       identity Seamless-MPLS-svc-topo {
       base svc-topo-flag-identity;
       description "Seamless MPLS service type";
      }
       identity Etree-svc-topo {
       base svc-topo-flag-identity;
       description "Seamless MPLS service type";
      }
       identity I2rs-svc-topo {
       base svc-topo-flag-identity;
       description "I2RS create service topo";
      }

     identity svc-tp-type {
       description "Base type for service
         termination-point type flags";
       }
     identity svc-tp-type-service {
       base svc-tp-type;
       description "service type";
      }
     identity svc-tp-type-ip {
       base svc-tp-type;
       description "service IP";
      }
     identity svc-tp-type-unnum {
               base svc-tp-type;
       description "service unnumbered link";
      }

          identity svc-link-type {
           description "Base type for composite
                 service link attribute flags";
           }
               identity svc-link-ip-te {
                 base svc-link-type;
                 description "service link
                 that support IP traffic engineering";
               }

               identity svc-link-ip-multicast {
                 base svc-link-type;
                 description "service link that
                 supports IP multicast.";
               }

          identity tdsvc-support-identity {
       description "Base type for svc flags";
       }

               identity td-L3sm-hub-spoke {
                   base tdsvc-support-identity;
       description "Supports L3SM hub-spoke";
       }
           identity td-L3sm-hub-spoke-disjoint {
                   base tdsvc-support-identity;
       description "Supports L3SM hub-spoke disjoint";
       }

               identity td-L3sm-any-any {
                   base tdsvc-support-identity;
       description "Supports L3SM any-any";
       }

      grouping svc-combo-network-type {
        description "Identify the topology type to be
                 composite service topology.";
        container svc-combo-network {
          presence "indicates Service layer Network";
          description
          "The presence of the container node indicates
           Service layer which combines networks
                       L3VPN, L2VPN, and others";
                 }
      }

     grouping service-topology-attributes {
       leaf name {
                 type string;
         description "name of service
         topology";
               }
       leaf description {
                 type string;
                 description "description
                 of service attribute";
           }
               leaf composite-flag {
          type identityref {
             base svc-topo-flag-identity;
                  }
         description "other topologies
         this topology is configured to
          be a composite of
             (L3VPN, L2VPN, I2RS only)";
       }

               list tdsvc-supports-attributes {
                  key tdsvc-attr-name;
                  leaf tdsvc-attr-name {
                   type string;
                       description "top-down
                       service support attribute name";
                  }
                 leaf tdsvc-supports-attribute {
            type identityref {
             base tdsvc-support-identity;
                     }
                     description "top-down service
                    attribute this topology supports.";

                  }
                  description "supporting top-down
          service attributes. ";
               }
               description  "Group of attributes for
             service topology";

     }

     grouping node-svc-attribute {
       leaf c-svc-node-name{
          type inet:domain-name;
          description "Domain name for node";
       }
       leaf c-svc-flag {
         type identityref {
            base svc-topo-flag-identity;
                 }
         description "virtual network
          node can be composite of the
          topologies list
          (L3VPN, L2VPN, I2RS only)";
       }

               list tdsvc-node-supports-attributes {
                  key tdsvc-node-attr-name;
                  leaf tdsvc-node-attr-name {
                       type string;
                       description "name of top-down
                        service attribute ";
                   }
                   leaf tdsvc-node-supports-attribute {
            type identityref {
             base tdsvc-support-identity;
                     }
                     description "top-down service
                    attribute this topology supports.";

                  }
                  description "list of top-down service
                  attributes this node supports";
               }

          description
          "grouping of composite flag";
     }

       grouping service-link-attributes {
       leaf c-svc-link-name {
                 type string;
         description "name of
           service link";
               }
       leaf c-svc-link-type {
         type identityref {
            base svc-link-type;
                 }
         description "other topologies
           this link is current a
                       composite of
           (L3VPN, L2VPN, I2RS only)";
       }
       leaf c-svc-link-metric {
         type uint32;
         description "link metric
                   for servicest to
                       allow TE loading at composite
                       service level";
       }
               list tdsvc-link-supports-attributes {
                  key tdsvc-link-attr-name;
                  leaf tdsvc-link-attr-name {
                   type string;
                       description "top-down
                       service support attribute name";
                  }
                 leaf c-svc-link-td-support-attribute {
            type identityref {
             base tdsvc-support-identity;
                     }
                     description "top-down service
                    attribute this link supports.";
                  }
                 description "list of service level
                  link attributes";
               }
           description "grouping of
                service link attribute";
     }

 grouping service-termination-point-attributes {
       leaf svc-tp-name {
                type string;
                description "name of service
                 termination point";
               }
       leaf svc-tp-type {
           type identityref {
             base svc-topo-flag-identity;
                       }
         description "other topologies
           this link termination point is
           part of (L3VPN, L2VPN,
                   or I2RS only)";
                 }
       list tdsvc-tp-support-attributes {
                  key tdsvc-tp-attr-name;
                  leaf tdsvc-tp-attr-name {
                   type string;
                       description "top-down
                       service support attribute name";
                  }
                 leaf tdsvc-tp-support-attribute {
            type identityref {
             base tdsvc-support-identity;
                     }
                     description "top-down service
                    attribute this link supports.";
                  }
                 description "list of service level
                  link attributes";
               }
           description "grouping of
                service link attribute";

     }

           augment "/nw:networks/nw:network/nw:network-types" {
       uses svc-combo-network-type;
               description
               "augment the network-tpyes with
               the service-topology-types grouping";
               }

               augment "/nw:networks/nw:network" {
        when "nw:network-types/svc-combo-network" {
          description
            "Augmentation parameters apply only for
                        service network with bottoms up topology";
        }
        description
          "Augment with combo service
                  topology attributes";
        uses service-topology-attributes;
      }

   augment "/nw:networks/nw:network/nw:node"{
           when "nw:network-types/svc-combo-network" {
          description
            "Augmentation parameters apply only for
                        service network with bottoms up topology";
        }
        uses node-svc-attribute;
            description
           "augment the node with the node-svc-attribute";
         }

       augment "/nw:networks/nw:network/nt:link" {
           when "nw:network-types/svc-combo-network" {
          description
            "Augmentation parameters apply only for
                        service network with bottoms up topology";
       }
               uses service-link-attributes;
               description
               "augment the link with
               service-link-attributes";
       }
  augment "/nw:networks/nw:network/nw:node/nt:termination-point"{
           when "nw:network-types/svc-combo-network" {
          description
            "Augmentation parameters apply only for
                        service network with bottoms up topology";
        }
               uses service-termination-point-attributes;
               description
               "augment the termination-point with
               service-termination-point-attributes";
       }

} // module i2rs-service-topology
