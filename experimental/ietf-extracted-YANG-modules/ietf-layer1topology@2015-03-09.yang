module ietf-layer1topology { 
  yang-version 1; 

  namespace  
    "urn:ietf:params:xml:ns:yang:ietf-layer1topology"; 
  prefix "l1topo"; 

  import ietf-inet-types { 
    prefix "inet";  
  } 
  import ietf-interfaces { 
    prefix "if"; 
  } 

  organization  
    "Internet Engineering Task Force (IETF) I2RS WG"; 
  contact 
    "ID-draft editor: zhang.xian@huawei.com"; 

  description 
    "This module defines a data-plan technology/protocol  
    independent Layer One topology data model."; 

  revision 2015-03-09 { 
    description 
      "Initial version."; 
    reference 
      "draft-zhang-i2rs-l1-topo-yang-model-01.txt"; 
  } 

  /* 
  * Typedefs 
  */ 

  typedef topology-id { 
    type inet:uri; 
    description "the identifier for a topology"; 
  } 

  typedef node-id { 
    type inet:ip-address; 
    description 
      "the identifier for a node"; 
  } 

  typedef interface-id { 
    type union {  
      type inet:ip-address; // IPv4 or IPv6 address 
      type int32;          // Un-numbered   
    }  
  description  
    "the identifier of an interface within a node, supporting both  
    numbered/unnumbered"; 
  } 

  typedef link-id { 
    type inet:ip-address; // IPv4 or IPv6 address  
    description "the identifier of a link"; 
  } 

  typedef switching-capabilities { 
    type enumeration { 
      enum "psc-1" { 
        value 1;  
        description  
          "Packet-Switch Capable-1 (PSC-1)";  
      } 
      enum "evpl" {  
        value 30;  
        description  
          "Ethernet Virtual Private Line (EVPL)";  
      } 

      enum "pbb-te"{ 
        value 40; 
        description  
          "802_1 PBB-TE"; 
      } 

      enum "l2sc" {  
        value 51;  
        description  
          "Layer-2 Switch Capable (L2SC)";  
      }  
      enum "tdm" {  
        value 100;  
        description  
          "Time-Division-Multiplex Capable (TDM)";  
      }  
      enum "otn-tdm" {  
        value 110;  
        description  
          "OTN-TDM Capable";  
      } 
      enum "lsc" {  
        value 150;  
        description  
          "Lambda-Switch Capable (LSC)";  
      }  
      enum "fsc" {  
        value 200;  
        description 
          "Fiber-Switch Capable (FSC)";  
      }  
    }  

    description 
      "Switching capability of an interface.  
      Only a subset of the above-mentioned values are applicable  
      to Layer 1 network. 
      Here it is included for completeness and will later be  
      updated if a base model is augmented to create layer 1  
      network topology YANG data model."; 

    reference 
      "The definition of switching types, their values and the  
      relevant RFCs can be found at: 
      http://www.iana.org/assignments/gmpls-sig-parameters/gmpls 
      -sig-parameters.xhtml#gmpls-sig-parameters-3"; 
  }  

  typedef encoding-types { 
    type enumeration { 
      enum "packet" { 
        value 1;  
        description "Packet"; 
      } 
      enum "ethernet" { 
        value 2;  
        description "Ethernet";  
      } 
      enum "pdh" { 
        value 3;  
        description "PDH";  
      } 
      enum "sdh-sonet" { 
        value 5;  
        description "SDH/SONET";  
      } 
      enum "digital-wrapper" { 
        value 7;  
        description "Digital Wrapper";  
      } 
      enum "lambda" { 
        value 8;  
        description "Lambda(photonic)";  
      }  
      enum "fiber" {  
        value 9;  
        description "Fiber"; 
      }  
      enum "fiber-channel" { 
        value 11;  
        description "FiberChannel";  
      }  
      enum "oduk" { 
        value 12;  
        description  
          "G.709 OKUk (Digital Path)";  
      } 
      enum "optical-channel" { 
        value 13; 
        description "G.709 Optical Channel";  
      } 
      enum "line" { 
        value 14;  
        description "Line (e.g., 8B/10B)";  
      } 
    } 
    description  
      "The encoding type supported by an interface or link.  
      Not all encoding types are applicable to Layer one network  
      nodes. They are included here for completeness and will be  
      updated if a base model is available to augment 
      so as to build a layer-one specific YANG data model.";  
    reference 
      "The definition of encoding types, their values and the  
      relevant RFCs can be found at http://www.iana.org/ 
      assignments/gmpls-sig-parameters/gmpls-sig-parameters.xhtml# 
      gmpls-sig-parameters-3"; 
  } 

  /* 
   * Groupings 
  */ 

  grouping srlg-attribute {  
    description  
      "Shared Risk Link Group Attributes";  
    reference  
      "RFC 4203: OSPF Extensions in Support of Generalized  
      Multi-Protocol Label Switching (GMPLS)";  
    list srlg-values {  
      key "srlg-value";  
      leaf srlg-value {  
        type uint32;  
        description "SRLG value"; 
      } 
    description 
      "the SRLG value list";  
    } 
  }  

  /* 
   * Configuration data nodes 
   */ 

  container layer-one-topology { 
    description  
      "this container holds all the inforamtion to layer 
      one network. It includes one or multiple topologies"; 

    list topology { 
      key "topology-id"; 

      description  
        "This contains all the information to one topoogy"; 

      leaf topology-id { 
        type topology-id; 
        description "topology identifier"; 
      } 

      leaf name { 
        type string; 
        description "topology name"; 
      } 

      list supporting-topology { 
        key "topo-ref"; 
        leaf topo-ref { 
          type leafref { 
            path "/layer-one-topology/topology/topology-id"; 
          } 
          description 
            "a Layer-One network might be supported by a lower  
            layer network and this is a pointer to the suporting 
            topology if there is one"; 
        } 
        description "underlaying topology information"; 
      } 

      list node { 
        key "node-id";    
        description "the list of nodes within the topology"; 

        leaf node-id { 
          type node-id; 
          description "node identifier"; 
        } 

        list interface { 
          key "interface-id"; 
          leaf interface-id { 
            type interface-id; 
            description "interface identifier"; 
          } 
          leaf interface-name { 
            type if:interface-state-ref;  
            description  
            "Name of the incoming interface."; 
          } 
          container adaptation-capability { 
            description 
            "TBD -to add for technology specific information"; 
          } 
          description "interface list pertaining to a node"; 
        } 

        list connectivity-matrix { 
          key "id"; 

          description 
            "This describes the connectivity contraints within  
            a node in the network. It can be one matrix or a set 
            of matrixes. Further details, read the reference 
            provided below."; 
          reference 
            "https://tools.ietf.org/html/draft-ietf-ccamp-general 
            -constraint-encode-16 Section 2.1"; 

          leaf id { 
            type uint32; 
            description "matrix id"; 
          } 
          leaf type { 
            type enumeration { 
              enum fixed { 
                value 0; 
                description "Fixed"; 
              } 
              enum dynamic { 
                value 1; 
                description "Dynamic/changeable"; 
              } 
            } 
            description 
              "This field describes the attribute of a  
              connectivity matrix, i.e., whether it is  
              fixed or switched."; 
          } 
          list in-interface { 
            key "interface-ref"; 

            description  
              "This list describes a (sub)-set of ingoing 
              interfaces within a node that may have  
              connectivity constraints. 
              Note: directionality may not be relevant 
               and it is decided by the dir parameter."; 

            leaf interface-ref {             
              type leafref { 
                path "/layer-one-topology/topology/node/" +  
                "interface/interface-id"; 
              } 
              description "reference to an incoming interface"; 
            } 
          } 
          list out-interface { 
            key "interface-ref"; 

            description 
              "This list describes a (sub)-set of outgoing 
              interfaces within a node that may have  
              connectivity constraints. 
              Note: directionality may not be relevant and 
              it is decided by the dir parameter."; 
            leaf interface-ref { 
              type leafref { 
                path "/layer-one-topology/topology/node/"+ 
                "interface/interface-id"; 
              } 
              description "reference to an outgoing interface"; 
            } 
          } 
          leaf dir{ 
            type enumeration{ 
              enum "uni-dir"{ 
                description 
                "the matrix is unidirectional."; 
              } 
              enum "bi-dir"{ 
                description 
                "this matrix is bidirecdtional."; 
              } 
            } 
            description 
             "the directionality attribute of a connc. matrix."; 
          } 
        } 
      }// end of node data node 

      list link { 
        key "link-id"; 

        description "list of the links within a topology"; 

        leaf link-id { 
          type link-id; 
          description 
            "remaining issue: if there is no IP addresses 
             associated with this link, what would be the key?"; 
        } 

        container local { 
          description "near end information for this link"; 

          leaf local-node { 
            type leafref { 
              path "/l1topo:layer-one-topology/topology"+ 
              "/node/node-id"; 
            } 
            mandatory true; 
            description "refence to the local node"; 
          } 
          leaf local-interface { 
            type leafref { 
              path "/l1topo:layer-one-topology/topology/node/" 
              +"interface/interface-id"; 
            } 
            mandatory true; 
            description "reference to the local interface"; 
          } 
        } 
        container remote { 
          description "far end information of this link"; 

          leaf remote-node { 
            type leafref { 
              path "/l1topo:layer-one-topology/topology"+ 
              "/node/node-id"; 
            } 
            mandatory true; 
            description "reference to the remote node"; 
          } 
          leaf remote-interface { 
            type leafref { 
              path "/l1topo:layer-one-topology/topology/node/" 
              + "interface/interface-id"; 
            } 
            mandatory true; 
            description "reference to the remote interface"; 
          } 
        } 
        list supporting-path { 
          key "supporting-path-index"; 

          description  
            "information pertaining to the underlying path if 
             there is any"; 

          leaf supporting-path-index { 
            type uint32; 
            description "the identifer of the supporting path"; 
          } 
          leaf topo-ref { 
            type leafref { 
              path "/l1topo:layer-one-topology/"+ 
              "topology/topology-id"; 
            } 
            description "reference to the underlying topology"; 
          } 
          container server-path-identifier { 
            description "TBD"; 
          } 
          container server-path-srlg { 
            uses srlg-attribute; 
            description "the SRLG values of the server path"; 
          } 
        } 

        container attributes { 

          description "additional information of the link"; 

          leaf information-source { 
            type enumeration {  
              enum "unknown" {  
                description "The source is unknown";  
              }  
              enum "locally-configured" {  
                description "Configured TE link";  
              }  
              enum "ospfv2" {  
                description "OSPFv2";  
              }  
              enum "ospfv3" {  
                description "OSPFv3";  
              }  
              enum "isis" {  
                description "ISIS";  
              }  
            } 
            config false;  

            description   
              "Indicates the source of the information about 
              the link. remaining issue: if configuration of 
              a link is allowed, what additional types are 
              needed to add?";  
          } 
          leaf credibility-preference { 
            type uint16; 
            config false; 
            description "the level of credibility"; 
          } 
          leaf admin-status {  
            type enumeration {  
              enum up {  
                value 1;  
                description "up";  
              }  
              enum down {  
                value 2;  
                description "down";  
              }  
              enum testing {  
                value 3;  
                description "testing - in some test mode.";  
              }  
            }  
            description  
              "The adminstrative state of the link.";  
            reference 
              "RFC2863: The Interfaces Group MIB."; 
          }  
          leaf oper-status {  
            type enumeration {  
              enum up {  
                value 1;  
                description "up";  
              }  
              enum down {  
                value 2;  
                description "down";  
              }  
              enum testing {  
                value 3;  
                description "testing - in some test mode";  
              }  
              enum unknown {  
                value 4;  
                description "unknown - status cannot be  
                determined for some reason.";  
              } 
              enum dormant{ 
                value 5; 
                description "dormant";  
              } 
            }  
            config false; 
            description  
              "The current operational state of the link.";  
            reference 
              "RFC2863: The Interfaces Group MIB."; 
          }  
          leaf area-id {  
            type binary {  
              length 1..13;  
            }  
            description  
              "This object indicates the area identifier of  
              the IGP. If OSPF is used to advertise LSA,  
              this represents an ospfArea. If IS-IS is used, 
               this represents an area address.  
               Otherwise, this is zero.";  
            reference 
              "RFC4920: Crankback Signaling Extensions for MPLS 
              and GMPLS RSVP-TE."; 
          } 

          leaf max-link-bandwidth { 
            type decimal64 { 
              fraction-digits 2; 
            } 
            description 
              "the max bandwidth supported by this link"; 
          } 

          list unreserved-bandwidth { 
            key "priority"; 
            max-elements "8"; 

            description 
              "This describes the unreserved bandwidth (in  
              Bytes/second) on a level basis ( level 0-7)."; 

            leaf priority { 
              type uint8{ 
                range "0..7"; 
              } 
              description "priority level"; 
            } 
            leaf bandwidth { 
              type decimal64 { 
                fraction-digits 2; 
              } 
              description "badnwidth per priority"; 
            } 
          } 

          leaf distance { 
            type  uint32; 
            units "kilometers"; 

            config false; 
            description 
              "the distance this link spans."; 
          } 
          leaf te-metric { 
            type uint32; 
            description "the metric supported by the link"; 
          } 

          leaf link-protection-type { 
            type enumeration {  
              enum "extra-traffic" { 
                value 1; 
                description "Extra traffic";  
              }  
              enum "unprotected" {  
                value 2; 
                description "unprotected";  
              }  
              enum "shared" { 
                 value 4; 
                description "Shared";  
              }  
              enum "1-for-1" { 
                value 8; 
                description "Dedicated one for one protection";  
              }  
              enum "1-plus-1" { 
                value 16;  
               description "Dedicated one plus one protection";  
              }  
              enum "enhanced" {  
                value 32; 
                description "a protection type that is  
                more reliable than Dedicated 1+1,  
                e.g.,4 fiber BLSR/MS-SPRING.";  
              }  
            }  
            description  
              "Link Protection Type configured for this link"; 
            reference 
              "RFC3471: Generalized MUlti-Protocol Label 
               Switching (GMPLS) Signaling Functional  
               Description.";  
          } 

          leaf switching-capability { 
            type switching-capabilities; 
            description  
              "the switching capability supported by the link"; 
          } 
          leaf encoding { 
            type encoding-types; 
            description 
              "the encoding type supported by this link."; 
          } 

          container switching-capability-specific { 
            description 
            "TBD - to add for technology specific information"; 
          } 
          container srlg { 
            uses srlg-attribute; 
            description " the SRLG values of a link"; 
          } 
        }// end of link attributes 
      }// end of link leaf data node 
    } 
  }// end of configuring data nodes 

  /* 
  * notifications - only provide operational change information. 
  * reply to topology/node/link creation is acked via rpc-reply. 
  */   

  notification link-failure { 
    leaf topology-id { 
      type leafref { 
        path "/layer-one-topology/topology/topology-id"; 
      } 
      mandatory true; 
      description "";  
    } 
    leaf link-id { 
      type leafref { 
        path  
          "/layer-one-topology/topology[topology-id="+ 
          "current ()/../topology-id]/link/link-id"; 
      } 
      mandatory true; 
      description ""; 
    } 
    leaf admin-status { 
      type leafref { 
        path 
          "/layer-one-topology/topology/link[link-id =" + 
          "current()/../link-id]/attributes/admin-status"; 
      } 
      description ""; 
    } 
    leaf oper-status { 
      type leafref { 
        path 
          "/layer-one-topology/topology/" + 
          "link[link-id = current()/../link-id]" 
          + "/attributes/oper-status"; 
      } 
      mandatory true; 
      description ""; 
    } 
    description 
      "link failure information"; 
  } //notification 

  notification node-failure { 
    leaf topology-id { 
      type leafref { 
        path "/layer-one-topology/topology/topology-id"; 
      } 
      mandatory true; 
      description ""; 
    } 
    leaf link-id { 
      type leafref { 
        path  
          "/layer-one-topology/topology[topology-id= " 
          + "current ()/../topology-id]/node/node-id"; 
      } 
      mandatory true; 
      description ""; 
    } 
    description 
    "node failure information"; 
  } //notification 
}//module
