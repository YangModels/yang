module ietf-event-trigger {
  yang-version 1.1;
  namespace "urn:ietf:params:xml:ns:yang:ietf-event-trigger";
  prefix trig;

  import ietf-yang-types {
    prefix yang;
  }

  organization
    "IETF xxx Working Group";
  contact
    "Zitao Wang: wangzitao@huawei.com
     Qin Wu: bill.wu@huawei.com";
  description
    "This module defines a reusable grouping for event trigger.";

  revision 2018-12-18 {
    description
      "Initial revision.";
    reference "foo";
  }

  typedef match-value {
    type union {
      type yang:xpath1.0;
      type yang:object-identifier;
      type string;
    }
    description
      "This type is used to match resources of type 'target'.
       Since the type 'target' is a union of different types,
       the 'match-value' type is also a union of corresponding
       types.";
  }

  typedef target {
    type union {
      type instance-identifier;
      type yang:object-identifier;
      type yang:uuid;
      type string;
    }
    description
      "If the target is modelled in YANG, this type will
       be an instance-identifier.
       If the target is an SNMP object, the type will be an
       object-identifier.
       If the target is anything else, for example a distinguished
       name or a CIM path, this type will be a string.
       If the target is identified by a UUID use the uuid
       type.
       If the server supports several models, the presedence should
       be in the order as given in the union definition.";
  }

  grouping trigger-grouping {
    description
      "A grouping that provides event trigger.";
    choice test {
      description
        "Choice test";
      container existences {
        leaf-list target {
          type target;
          description
            "List for target objects";
        }
        description
          "Container for existence";
      }
      container boolean {
         leaf comparison {
          type enumeration {
            enum "unequal" {
              description
                "Indicates that the comparision type is unequal to.";
            }
            enum "equal" {
              description
                "Indicates that the comparision type is equal to.";
            }
            enum "less" {
              description
                "Indicates that the comparision type is less than.";
            }
            enum "less-or-equal" {
              description
                "Indicates that the comparision type is less than
                or equal to.";
            }
            enum "greater" {
              description
                "Indicates that the comparision type is greater than.";
            }
            enum "greater-or-equal" {
              description
                "Indicates that the comparision type is greater than
                 or equal to.";
            }
          }
          description
            "Comparison type.";
        }
        leaf value {
          type match-value;
          description
            "Compartion value which is static threshold value.";
        }
        leaf target {
          type target;
          description
            "List for target management objects.";
        }
        description
          "Container for boolean test.";
      }
      container threshold {
        leaf rising-value {
          type match-value;
          description
            "Sets the rising threshold to the specified value,
             when the current sampled value is greater than or equal to
             this threshold, and the value at the last sampling interval
             was less than this threshold, the event is triggered. ";
        }
        leaf-list rising-target {
          type target;
          description
            "List for target objects.";
        }
        leaf falling-value {
          type match-value;
          description
            "Sets the falling threshold to the specified value.";
        }
        leaf-list falling-target {
          type target;
          description
            "List for target objects.";
        }
        leaf delta-rising-value {
          type match-value;
          description
            "Sets the delta rising threshold to the specified value.";
        }
        leaf-list delta-rising-target {
          type target;
          description
            "List for target objects.";
        }
        leaf delta-falling-value {
          type match-value;
          description
            "Sets the delta falling threshold to the specified value.";
        }
        leaf-list delta-falling-target {
          type target;
          description
            "List for target objects.";
        }
        leaf startup {
          type enumeration {
            enum "rising" {
              description
                "If the first sample after this
                 managed object becomes active is greater than or equal
                  to 'rising-value' and the 'startup' is equal to
                  'rising' then one threshold rising event is
                 triggered for that managed object.";
            }
            enum "falling" {
              description
                "If the first sample after this managed object becomes
               active is less than or equal to 'falling-value' and
               the 'startup' is equal to 'falling' then one
               threshold falling event is triggered for that managed
               object.";
            }
            enum "rising-or-falling" {
              description
                "That event may be triggered when the
                 'startup' is equal to 'rising-or-falling'.
                 'rising-or-falling' indicate the state value of the
                  managed object may less than or greater than the
                 specified thrshold value.";
            }
          }
          description
            "Startup setting.";
        }
        description
          "Container for the threshold trigger condition.
           Note that the threshold here  may change over time
           or the state value changes in either ascend order
           or descend order.";
      }
    }
  }
}
