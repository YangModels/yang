module ietf-ospf-two-part-metric {
  yang-version 1.1;
  namespace "urn:ietf:params:xml:ns:yang:ietf-ospf-two-part-metric";

  prefix ospf-two-metric;

  import ietf-routing {
    prefix "rt";
  }

  import ietf-ospf {
    prefix "ospf";
  }

  import ietf-ospfv3-te {
    prefix "ospfv3-te";
  }

  organization
    "IETF LSR - Link State Routing Working Group";

  contact
     "WG Web:   <http://tools.ietf.org/wg/lsr>
      WG List:  <mailto:lsr@ietf.org>

      Author:   Yingzhen Qu
                <mailto:yqu@futurewei.com>
      Author:   Acee Lindem
                <mailto:acee@cisco.com>";

  description
    "This YANG module defines the configuration and operational
    state for OSPF Two-Part Metric feature as defined in RFC 8042.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  reference "RFC XXXX";

  revision 2019-08-13 {
    description
      "Initial version";
    reference
      "RFC XXXX: A YANG Data Model for OSPF.";
  }

  identity two-part-metric {
    base ospf:informational-capability;
    description
      "When set, the router is capable of supporting OSPF
       two-part metrics.";
    reference
      "RFC 8042: OSPF Two-Part Metric";
  }

  /* RFC 8042 */
  augment "/rt:routing/rt:control-plane-protocols/"
        + "rt:control-plane-protocol/ospf:ospf/"
        + "ospf:areas/ospf:area/ospf:interfaces/ospf:interface" {
    when "../../../../../rt:type = 'ospf:ospfv2' or "
       + "../../../../../rt:type = 'ospf:ospfv3'" {
      description
        "This augments the OSPF interface configuration
         when used.";
    }
    description
      "This augments the OSPF protocol interface
       configuration with two-part metric.";

    container two-part-metric {
      when "enum-value(../ospf:interface-type) = 2" {
        description
          "Two-part metric when link type is multi-access.";
      }
      leaf enable {
        type boolean;
        default false;
        description
          "Enable two-part metric.";
      }
      leaf int-input-cost {
        type ospf:ospf-link-metric;
        description
          "Link state metric from the two-part-metric network
           to this router.";
      }
      description
        "Interface two part metric configuration.";
    }
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "../../../../../../../../../../../../"
       + "rt:type = 'ospf:ospfv2'" {
      description
        "This augmentation is only valid for OSPFv2.";
    }
    description
      "Network-to-Router metric sub tlv for OSPFv2 extended link TLV
       in type 10 opaque LSA.";

       container network-to-router-metric-sub-tlvs {
         description "Network-to-Router metric sub TLV.";
         list net-to-rtr-sub-tlv {
           leaf mt-id {
             type uint8;
             description "Multi-Topology Identifier (MT-ID).";
           }
           leaf mt-metric {
             type uint16;
             description "Network-to-router metric.";
           }
           description
             "Network-to-Router metric sub-TLV.";
         }
       }
    }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/ospf:te-opaque/"
        + "ospf:link-tlv" {
    when "../../../../../../../../../../../../"
       + "rt:type = 'ospf:ospfv2'" {
      description
        "This augmentation is only valid for OSPFv2.";
    }
    description
      "Traffic Engineering Network-to-Router Sub-TLV.";
      leaf network-to-router-te-metric {
        type uint32;
        description "Network to Router TE metric.";
        reference
          "RFC 8042 - OSPF Two-Part Metric";
      }
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body/ospfv3-te:ospfv3-intra-area-te/"
        + "ospfv3-te:link-tlv" {
    when "../../../../../../../../../../../"
       + "rt:type = 'ospf:ospfv3'" {
      description
        "This augmentation is only valid for OSPFv3.";
    }
    description
      "Traffic Engineering Network-to-Router Sub-TLV.";
      leaf network-to-router-te-metric {
        type uint32;
        description "Network to Router TE metric.";
        reference
          "RFC 8042 - OSPF Two-Part Metric";
      }
  }
}
