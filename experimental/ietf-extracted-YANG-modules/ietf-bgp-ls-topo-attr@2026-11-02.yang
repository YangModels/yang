submodule ietf-bgp-ls-topo-attr {
  yang-version 1.1;

  belongs-to ietf-bgp-lsdb {
    prefix "bgp-lsdb";
  }

  import ietf-inet-types {
    prefix inet;
    reference
      "RFC 9911: Common YANG Data Types.";
  }

  import ietf-yang-types {
    prefix yang;
    reference
      "RFC 9911: Common YANG Data Types.";
  }

  import ietf-bgp-ls-topo-types {
    prefix bgp-ls-topo-t;
    reference
      "RFC XXXX: BGP Model for Link State Distribution.";
  }

  import ietf-routing-types {
    prefix ietf-rt-t;
    reference
      "RFC 8294: Common YANG Data Types for the Routing Area.";
  }

  import ietf-isis {
    prefix ietf-isis-t;
    reference
      "RFC 9130: YANG Data Model for IS-IS Protocol.";
  }

  organization
    "IETF LSVR Working Group";

  contact
    "WG Web:   <https://datatracker.ietf.org/wg/lsvr>
     WG List:  <lsvr@ietf.org>

     Authors: Mahesh Jethanandani (mjethanandani at gmail.com),
              Keyur Patel (keyur at arrcus.com),
              Aravind Babu MahendraBabu (aramahen at cisco.com)";

  description
    "This submodule contains structural data definitions associated
     BGP-LS topology attributes.

     Copyright (c) 2025 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-11-02 {
    description
      "Initial Version";
    reference
      "RFC XXXX, BGP Model for Link State Distribution.";
  }

  grouping bgp-ls-topo-ipv4-router-id-attr {
    description
      "Grouping for the BGP-LS topology IPv4 router-id attribute";

    leaf-list router-id {
      type ietf-rt-t:router-id;
      description
        "List of IPv4 Router ID";
    }
  }
  grouping bgp-ls-topo-ipv6-router-id-attr {
    description
      "Grouping for the BGP-LS topology IPv6 router-id attribute";

    leaf-list router-id {
      type inet:ipv6-address;
      description
        "List of IPv6 Router ID";
    }
  }

  grouping bgp-ls-topo-msd-attr {
    description
      "Grouping for the BGP-LS topology Maximum SID Depth (MSD)
       attribute";

    list msd {
      key "msd-type";

      description
        "List of MSDs";

      leaf msd-type {
        type uint8;
        description
          "MSD type. One of the values defined in the
           'IGP MSD-Types' registry.";
        reference
          "RFC 8491: Signaling Maximum SID Depth (MSD) Using
           IS-IS.";
      }

      leaf msd-value {
        type uint8;
        description
          "MSD value. A number in the range of 0-255";
      }
    }
  }

  grouping bgp-ls-topo-opaque-attribute {
    description
      "Grouping for the BGP-LS topology opaque attribute";

    leaf opaque-attrs {
      type yang:hex-string;
      description
        "Opaque attribute";
    }
  }

  grouping bgp-ls-topo-eag-attr {
    description
      "Grouping for the BGP-LS topology EAG attribute";

    leaf-list eag {
      type uint32;
      description
        "Extended Administrative Group (EAG) value for link affinity
         constraints to be used in traffic engineering";
    }
  }

  grouping bgp-ls-topo-srlg-attr {
    description
      "Grouping for the BGP-LS topology SRLG attribute";

    leaf-list srlg {
      type uint32;
      description
        "Shared Risk Link Group (SRLG) value representing links that
         share a common resource and may fail together";
    }
  }

  grouping bgp-ls-topo-delay-attr {
    description
      "Grouping for the BGP-LS topology delay attribute";

    leaf delay {
      type uint32;
      units microseconds;
      description
        "Average link delay over a configurable interval";
    }
  }

  grouping bgp-ls-topo-bw-attr {
    description
      "Grouping for the BGP-LS topology bandwidth attribute";

    leaf bw {
      type ietf-rt-t:bandwidth-ieee-float32;
      description
        "Bandwidth in IEEE 754 floating point format. BGP-LS defines
         various bandwidth types.";
      reference
        "IEEE 754: IEEE Standard for Floating-Point Arithmetic.";
    }
  }

  grouping bgp-ls-topo-adj-sid-attr {
    description
      "Grouping for the BGP-LS topology adjacency SID attribute";

    leaf label-index {
      type uint32;
      description
        "Label or index";
    }

    leaf format {
      type bgp-ls-topo-t:sid-format;
      description
        "Format of the SID";
    }

    leaf flags {
      type binary {
        length "1";
      }
      description
        "Flags associated with the SID. IS-IS flags are
         defined in RFC 8667. OSPFv2 flags are defined in
         RFC 8665. OSPFv3 flags are defined in RFC 8666.";
    }

    leaf weight {
      type uint8;
      description
        "Weight used for load balancing purposes";
    }
  }

  grouping bgp-ls-topo-common-link-asla-l2-bundle-member-attr {
    description
      "Grouping for the BGP-LS topology attributes common for link,
       ASLA and L2 bundle member";

    container te-default-metric {
      when "derived-from-or-self(../type, " +
           "'bgp-ls-topo-t:bgp-ls-topo-attr-te-default-metric')" {
        description
          "Only include the te-default-metric container when the
           type is bgp-ls-topo-attr-te-default-metric";
      }
      description
        "This container specifies the Traffic Engineering (TE)
         metric of a link";
      reference
        "RFC 9552: Distribution of Link-State and Traffic
         Engineering Information Using BGP. TLV 1092";

      leaf metric {
        type uint32;
        description
          "Traffic Engineering metric";
      }
    }

    container unidirectional-link-delay {
      when "derived-from-or-self(../type, " +
           "'bgp-ls-topo-t:" +
           "bgp-ls-topo-attr-unidir-link-delay')" {
        description
          "Only include the unidirectional-link-delay container
           when the type is bgp-ls-topo-attr-unidir-link-delay";
      }
      description
        "This container specifies the average link delay between
         two directly connected IGP link-state neighbors";
      reference
        "RFC 8571: Link State (BGP-LS) Advertisement of IGP Traffic
         Engineering Performance Metric Extensions. TLV 1114";

      uses bgp-ls-topo-delay-attr;

      leaf anomaly {
        type boolean;
        description
          "Anomalous?";
      }
    }

    container min-max-unidirectional-link-delay {
      when "derived-from-or-self(../type, " +
           "'bgp-ls-topo-t:" +
           "bgp-ls-topo-attr-min-max-unidir-link-delay')" {
        description
          "Only include the min-max-unidirectional-link-delay
           container when the type is
           bgp-ls-topo-attr-min-max-unidir-link-delay";
      }
      description
        "This container specifies the minimum and maximum link delay
         between two directly connected IGP link-state neighbors";
      reference
        "RFC 8571: Link State (BGP-LS) Advertisement of IGP Traffic
         Engineering Performance Metric Extensions. TLV 1115";

      container min {
        description
          "Enclosing container for minimum delay";
        uses bgp-ls-topo-delay-attr;
      }

      container max {
        description
          "Enclosing container for maximum delay";
        uses bgp-ls-topo-delay-attr;
      }

      leaf anomaly {
        type boolean;
        description
          "Anomalous?";
      }
    }

    container unidirectional-delay-variation {
      when "derived-from-or-self(../type, " +
           "'bgp-ls-topo-t:" +
           "bgp-ls-topo-attr-unidir-delay-variation')" {
        description
          "Only include the unidirectional-delay-variation container
           when the type is
           bgp-ls-topo-attr-unidir-delay-variation";
      }
      description
        "This container specifies the average link delay variation
         between two directly connected IGP link-state neighbors";
      reference
        "RFC 8571: Link State (BGP-LS) Advertisement of IGP Traffic
         Engineering Performance Metric Extensions. TLV 1116";

      uses bgp-ls-topo-delay-attr;
    }

    container unidirectional-link-loss {
      when "derived-from-or-self(../type, " +
           "'bgp-ls-topo-t:" +
           "bgp-ls-topo-attr-unidir-link-loss')" {
        description
          "Only include the unidirectional-link-loss container when
           the type is bgp-ls-topo-attr-unidir-link-loss";
      }
      description
        "This container specifies the loss (as a packet percentage)
         between two directly connected IGP link-state neighbors";
      reference
        "RFC 8571: Link State (BGP-LS) Advertisement of IGP Traffic
         Engineering Performance Metric Extensions. TLV 1117";

      leaf link-loss {
        type uint32;
        description
          "Link packet loss as a percentage of the total traffic
           sent over a configurable interval. The basic unit is
           0.000003%, where (2^24 - 2) is 50.331642%.";
      }

      leaf anomaly {
        type boolean;
        description
          "Anomalous?";
      }
    }

    container unidirectional-residual-bw {
      when "derived-from-or-self(../type, " +
           "'bgp-ls-topo-t:" +
           "bgp-ls-topo-attr-unidir-residual-bw')" {
        description
          "Only include the unidirectional-residual-bw container
           when the type is bgp-ls-topo-attr-unidir-residual-bw";
      }
      description
        "This container specifies the residual bandwidth between
         two directly connected IGP link-state neighbors";
      reference
        "RFC 8571: Link State (BGP-LS) Advertisement of IGP Traffic
         Engineering Performance Metric Extensions. TLV 1118";

      uses bgp-ls-topo-bw-attr;
    }

    container unidirectional-available-bw {
      when "derived-from-or-self(../type, " +
           "'bgp-ls-topo-t:" +
           "bgp-ls-topo-attr-unidir-available-bw')" {
        description
          "Only include the unidirectional-available-bw container
           when the type is bgp-ls-topo-attr-unidir-available-bw";
      }
      description
        "This container specifies the available bandwidth between
         two directly connected IGP link-state neighbors";
      reference
        "RFC 8571: Link State (BGP-LS) Advertisement of IGP Traffic
         Engineering Performance Metric Extensions. TLV 1119";

      uses bgp-ls-topo-bw-attr;
    }

    container unidirectional-utilized-bw {
      when "derived-from-or-self(../type, " +
           "'bgp-ls-topo-t:" +
           "bgp-ls-topo-attr-unidir-utilized-bw')" {
        description
          "Only include the unidirectional-utilized-bw container
           when the type is bgp-ls-topo-attr-unidir-utilized-bw";
      }
      description
        "This container specifies the utilized bandwidth between
         two directly connected IGP link-state neighbors";
      reference
        "RFC 8571: Link State (BGP-LS) Advertisement of IGP Traffic
         Engineering Performance Metric Extensions. TLV 1120";

      uses bgp-ls-topo-bw-attr;
    }

    container extended-admin-group {
      when "derived-from-or-self(../type, " +
           "'bgp-ls-topo-t:" +
           "bgp-ls-topo-attr-extended-admin-group')" {
        description
          "Only include the extended-admin-group container when the
           type is bgp-ls-topo-attr-extended-admin-group";
      }
      description
        "This container contains the bit mask of administrative
         groups assigned by the network administrator";
      reference
        "RFC 9552: Distribution of Link-State and Traffic
         Engineering Information Using BGP. TLV 1173";
      uses bgp-ls-topo-eag-attr;
    }

    container unknowns {
      when "derived-from-or-self(../type, " +
          "'bgp-ls-topo-t:bgp-ls-topo-attr-unknowns')" {
      description
          "Only include the unknowns container when the type is
          bgp-ls-topo-attr-unknowns";
      }
      description
        "This container describes the unknown attributes.";
      reference
        "RFC 9552: Distribution of Link-State and Traffic
         Engineering Information Using BGP.";

      uses bgp-ls-topo-unknown-attr;
    }
  }

  grouping bgp-ls-topo-common-link-l2-bundle-member-attr {
    description
      "Grouping for the BGP-LS topology attributes common for link
       and L2 bundle member";

    container maximum-link-bw {
      when "derived-from-or-self(../type, " +
           "'bgp-ls-topo-t:bgp-ls-topo-attr-maximum-link-bw')" {
        description
          "Only include the maximum-link-bw container when the
           type is bgp-ls-topo-attr-maximum-link-bw";
      }
      description
        "This container specifies the maximum bandwidth that can be
         used on a link";
      reference
        "RFC 9552: Distribution of Link-State and Traffic
         Engineering Information Using BGP. TLV 1089";

      uses bgp-ls-topo-bw-attr;
    }

    container maximum-reservable-link-bw {
      when "derived-from-or-self(../type, " +
           "'bgp-ls-topo-t:" +
           "bgp-ls-topo-attr-maximum-reservable-link-bw')" {
        description
          "Only include the maximum-reservable-link-bw container
           when the type is
           bgp-ls-topo-attr-maximum-reservable-link-bw";
      }
      description
        "This container specifies the maximum bandwidth that can be
         reserved on a link";
      reference
        "RFC 9552: Distribution of Link-State and Traffic
         Engineering Information Using BGP. TLV 1090";

      uses bgp-ls-topo-bw-attr;
    }

    container unreserved-bws {
      when "derived-from-or-self(../type, " +
           "'bgp-ls-topo-t:bgp-ls-topo-attr-unreserved-bw')" {
        description
          "Only include the unreserved-bws container when the type
           is bgp-ls-topo-attr-unreserved-bw";
      }
      description
        "This container specifies the bandwidth reservable on a
         link on a per priority basis";
      reference
        "RFC 9552: Distribution of Link-State and Traffic
         Engineering Information Using BGP. TLV 1091";

      list unreserved-bw {
        key "priority";

        description
          "List of unreserved bandwidths";

        leaf priority {
          type uint8 {
            range "0..7";
          }
          description
            "Priority level";
        }

        leaf bandwidth {
          type ietf-rt-t:bandwidth-ieee-float32;
          description
            "Bandwidth reservable on the link for a particular
             priority";
        }
      }
    }

    container link-protection-type {
      when "derived-from-or-self(../type, " +
           "'bgp-ls-topo-t:" +
           "bgp-ls-topo-attr-link-protection-type')" {
        description
          "Only include the link-protection-type container when the
           type is bgp-ls-topo-attr-link-protection-type";
      }
      description
        "This container describes the protection capabilities of a
         link";
      reference
        "RFC 9552: Distribution of Link-State and Traffic
         Engineering Information Using BGP. TLV 1093";

      leaf type {
        type uint16;
        description
          "Bit mask of protection capabilities";
      }
    }

    container adjacency-sids {
      when "derived-from-or-self(../type, " +
           "'bgp-ls-topo-t:bgp-ls-topo-attr-adjacency-sid')" {
        description
          "Only include the adjacency-sids container when the type
           is bgp-ls-topo-attr-adjacency-sid";
      }
      description
        "This container contains the Adjacency Segment Identifiers
         (SIDs) of an adjacency";
      reference
        "RFC 9085: Border Gateway Protocol - Link State (BGP-LS)
         Extensions for Segment Routing. TLV 1099";

      list adjacency-sid {
        key "label-index format";

        description
          "List of adjacency SID";

        uses bgp-ls-topo-adj-sid-attr;
      }
    }

    container lan-adjacency-sids {
      when "derived-from-or-self(../type, " +
           "'bgp-ls-topo-t:bgp-ls-topo-attr-lan-adjacency-sid')" {
        description
          "Only include the lan-adjacency-sids container when the
           type is bgp-ls-topo-attr-lan-adjacency-sid";
      }
      description
        "This container contains the Adjacency Segment Identifiers
         (SIDs) of an adjacency to any node in a LAN other than the
         pseudonode";
      reference
        "RFC 9085: Border Gateway Protocol - Link State (BGP-LS)
         Extensions for Segment Routing. TLV 1100";

      list adjacency-sid {
        key "label-index format";

        description
          "List of LAN adjacency SID";

        uses bgp-ls-topo-adj-sid-attr;

        leaf neighbor-id {
          type union {
            type inet:ipv4-address;
            type ietf-isis-t:system-id;
          }
          description
            "Neighbor ID";
        }
      }
    }

    container aslas {
      when "derived-from-or-self(../type, " +
           "'bgp-ls-topo-t:bgp-ls-topo-attr-asla')" {
        description
          "Only include the aslas container when the type is
           bgp-ls-topo-attr-asla";
      }
      description
        "This container acts as a container for link attributes
         that require application-specific definition";
      reference
        "RFC 9294: Application-Specific Link Attributes
         Advertisement Using the Border Gateway Protocol - Link
         State (BGP-LS). TLV 1122";
      list asla {
        key "sabm udabm";

        description
          "List of Application Specific Link Attributes (ASLA)";

        leaf sabm {
          type binary {
            length "0|4|8";
          }
          description
            "Standard Application Identifier Bit Mask (SABM).
             Optional bit mask of length 0, 4, or 8 octets where
             each bit represents a single standard application.";
          reference
            "RFC 9294: Application-Specific Link Attributes
             Advertisement Using the Border Gateway Protocol - Link
             State (BGP-LS), Section 2";
        }

        leaf udabm {
          type binary {
            length "0|4|8";
          }
          description
            "User-Defined Application Identifier Bit Mask (UDABM).
             Optional bit mask of length 0, 4, or 8 octets where
             each bit represents a single user-defined
             application.";
          reference
            "RFC 9294: Application-Specific Link Attributes
             Advertisement Using the Border Gateway Protocol - Link
             State (BGP-LS), Section 2;";
        }

        list asla-attribute {
          key "type";

          description
            "List of ASLA attribute types.";

          leaf type {
            type identityref {
              base bgp-ls-topo-t:bgp-ls-topo-attr-type;
            }
            description
              "The type of ASLA attribute";
          }
          container srlgs {
            when "derived-from-or-self(../type, " +
                 "'bgp-ls-topo-t:bgp-ls-topo-attr-srlg')" {
              description
                "Only include the srlgs container when the type is
                 bgp-ls-topo-attr-srlg";
            }
            description
              "This container specifies the Shared Risk Link Groups
               (SRLGs) of a link";
            reference
              "RFC 9552: Distribution of Link-State and Traffic
               Engineering Information Using BGP. TLV 1096";

            uses bgp-ls-topo-srlg-attr;
          }

          uses bgp-ls-topo-common-link-asla-l2-bundle-member-attr;
        }
      }
    }
  }

  grouping bgp-ls-topo-srv6-sid-struct-attr {
    description
      "Grouping for the BGP-LS topology SRv6 SID
       structure attribute";

    leaf locator-block-len {
      type uint8;
      units "bits";
      description
        "Locator block length";
    }

    leaf locator-node-len {
      type uint8;
      units "bits";
      description
        "Locator node length";
    }

    leaf function-len {
      type uint8;
      units "bits";
      description
        "Function length";
    }
    leaf arg-len {
      type uint8;
      units "bits";
      description
        "Argument length";
    }
  }

  grouping bgp-ls-topo-srv6-endpoint-behavior-attr {
    description
      "Grouping for the BGP-LS topology SRv6 endpoint
       behavior attribute";

    leaf endpoint-behavior {
      type uint8;
      description
        "Endpoint behavior of the SID";
    }

    leaf flags {
      type binary {
        length "1";
      }
      description
        "Flags associated with the SRv6 endpoint behavior";
    }

    leaf algorithm {
      type uint8;
      description
        "Algorithm associated with the SID";
    }
  }

  grouping bgp-ls-topo-srv6-end-x-sid-attr {
    description
      "Grouping for the BGP-LS topology SRv6 End.X SID
       attribute";

    leaf sid {
      type inet:ipv6-address;
      description
        "SRv6 SID as a 128-bit value";
    }

    leaf weight {
      type uint8;
      description
        "Weight associated with the SID for load balancing purpose";
    }

    uses bgp-ls-topo-srv6-endpoint-behavior-attr;
    uses bgp-ls-topo-srv6-sid-struct-attr;
  }

  grouping bgp-ls-topo-unknown-attr {
    description
      "Grouping for the BGP-LS topology unknown attributes";

    list unknown {
      key "type";

      description
        "List of node FAD attribute types.";

      leaf type {
        type uint16;
        description
          "Attribute type.";
        reference
          "RFC 9552: Distribution of Link-State and Traffic
           Engineering Information Using BGP, Section 5.3.";
      }

      leaf value {
        type yang:hex-string;
        description
          "Attribute value.";
        reference
          "RFC 9552: Distribution of Link-State and Traffic
           Engineering Information Using BGP, Section 5.3.";
      }
    }
  }

  grouping bgp-ls-topo-node-attr {
    description
      "Grouping for the BGP-LS topology node attributes";

    container node-attributes {
      description
        "Enclosing container for node attributes list";

      list node-attribute {
        key "type";

        description
          "List of node attribute types.";

        leaf type {
          type identityref {
            base bgp-ls-topo-t:bgp-ls-topo-attr-type;
          }
          description
            "The type of node attribute";
        }

        container local-ipv4-router-ids {
          when "derived-from-or-self(../type, " +
               "'bgp-ls-topo-t:" +
               "bgp-ls-topo-attr-local-ipv4-routerid')" {
            description
              "Only include the local-ipv4-router-ids container
               when the type is
               bgp-ls-topo-attr-local-ipv4-routerid";
          }
          description
            "This container describes the auxiliary Router-IDs used
             by the IGP.";
          reference
            "RFC 9552: Distribution of Link-State and Traffic
             Engineering Information Using BGP. TLV 1028";

          uses bgp-ls-topo-ipv4-router-id-attr;
        }

        container local-ipv6-router-ids {
          when "derived-from-or-self(../type, " +
               "'bgp-ls-topo-t:" +
               "bgp-ls-topo-attr-local-ipv6-routerid')" {
            description
              "Only include the local-ipv6-router-ids container
               when the type is
               bgp-ls-topo-attr-local-ipv6-routerid";
          }
          description
            "This container describes the auxiliary Router-IDs used
             by the IGP.";
          reference
            "RFC 9552: Distribution of Link-State and Traffic
             Engineering Information Using BGP. TLV 1029";

          uses bgp-ls-topo-ipv6-router-id-attr;
        }
        container unknowns {
          when "derived-from-or-self(../type, " +
              "'bgp-ls-topo-t:bgp-ls-topo-attr-unknowns')" {
          description
              "Only include the unknowns container when the type is
              bgp-ls-topo-attr-unknowns";
          }
          description
            "This container describes the unknown attributes.";
          reference
            "RFC 9552: Distribution of Link-State and Traffic
             Engineering Information Using BGP.";

          uses bgp-ls-topo-unknown-attr;
        }

        container multi-topology-ids {
          when "derived-from-or-self(../type, " +
               "'bgp-ls-topo-t:" +
               "bgp-ls-topo-attr-multi-topology-id')" {
            description
              "Only include the multi-topology-ids container
               when the type is
               bgp-ls-topo-attr-multi-topology-id";
          }
          description
            "This container defines topologies.";
          reference
            "RFC 9552: Distribution of Link-State and Traffic
             Engineering Information Using BGP. TLV 263";

          leaf-list multi-topology-id {
            type uint16;
            description
              "List of Multi-Topology ID";
          }
        }

        container node-flag-bits {
          when "derived-from-or-self(../type, " +
                "'bgp-ls-topo-t:bgp-ls-topo-attr-node-flag-bits')" {
            description
              "Only include the node-flag-bits container when
               the type is bgp-ls-topo-attr-node-flag-bits";
          }
          description
            "This container defines node attributes as a bit mask.";
          reference
            "RFC 9552: Distribution of Link-State and Traffic
             Engineering Information Using BGP. TLV 1024";

          leaf flags {
            type bgp-ls-topo-t:node-flag-bits;
            description
              "Node flags";
          }
        }

        container opaque-node-attribute {
          when "derived-from-or-self(../type, " +
              "'bgp-ls-topo-t:bgp-ls-topo-attr-opaque-node')" {
          description
              "Only include the opaque-node-attribute container when
               the type is bgp-ls-topo-attr-opaque-node";
          }
          description
            "This container defines an envelope that transparently
             carries optional Node Attribute TLVs advertised by a
             router";
          reference
            "RFC 9552: Distribution of Link-State and Traffic
             Engineering Information Using BGP. TLV 1025";

          uses bgp-ls-topo-opaque-attribute;
        }

        container node-name {
          when "derived-from-or-self(../type, " +
              "'bgp-ls-topo-t:bgp-ls-topo-attr-node-name')" {
          description
              "Only include the node-name container when the
               type is bgp-ls-topo-attr-node-name";
          }
          description
            "This container identifies the symbolic name of
             the router node";
          reference
            "RFC 9552: Distribution of Link-State and Traffic
             Engineering Information Using BGP. TLV 1026";

          leaf name {
            type string {
              length "1..255";
            }
            description
              "Node name";
          }
        }

        container sr-capabilities {
          when "derived-from-or-self(../type, " +
              "'bgp-ls-topo-t:bgp-ls-topo-attr-sr-capabilities')" {
          description
              "Only include the sr-capabilities container when
               the type is bgp-ls-topo-attr-sr-capabilities";
          }
          description
            "This container defines node's Segment Routing (SR)
             capabilities including its Segment Routing Global Base
             (SRGB) range(s)";
          reference
            "RFC 9085: Border Gateway Protocol - Link State (BGP-LS)
             Extensions for Segment Routing. TLV 1034";

          list srgb {
            key "start-label";

            description
              "List of SRGB";

            leaf start-label {
              type ietf-rt-t:mpls-label;
              description
                "First label in the range";
            }
            leaf range-size {
              type uint32;
              description
                "Number of labels in the range";
            }
          }

          leaf isis-flags {
            type binary {
              length "1";
            }
            description
              "ISIS flags for IS-IS.";
            reference
              "RFC 8667: IS-IS Extensions for Segment Routing,
               Section 3.1.";
          }
        }

        container sr-local-block {
          when "derived-from-or-self(../type, " +
              "'bgp-ls-topo-t:bgp-ls-topo-attr-srlb')" {
          description
              "Only include the sr-local-block container when
               the type is bgp-ls-topo-attr-srlb";
          }
          description
            "This container contains the range(s) of labels
             reserved by the node for local SIDs (Segment
             Identifiers)";
          reference
            "RFC 9085: Border Gateway Protocol - Link State (BGP-LS)
             Extensions for Segment Routing. TLV 1036";

          list srlb {
            key "start-label";

            description
              "List of SRLB";

            leaf start-label {
              type ietf-rt-t:mpls-label;
              description
                "First label in the range";
            }
            leaf range-size {
              type uint32;
              description
                "Number of labels in the range";
            }
          }
        }

        container sr-algorithm {
          when "derived-from-or-self(../type, " +
              "'bgp-ls-topo-t:bgp-ls-topo-attr-sr-algorithm')" {
          description
              "Only include the sr-algorithm container when the
               type is bgp-ls-topo-attr-sr-algorithm";
          }
          description
            "This container defines Segment Routing (SR) algorithms
             supported by the node";
          reference
            "RFC 9085: Border Gateway Protocol - Link State (BGP-LS)
             Extensions for Segment Routing. TLV 1035";

          leaf-list algorithm {
            type uint8;
            description
              "List of SR algorithms";
          }
        }

        container node-msd {
          when "derived-from-or-self(../type, " +
              "'bgp-ls-topo-t:bgp-ls-topo-attr-node-msd')" {
          description
              "Only include the node-msd container when the type is
              bgp-ls-topo-attr-node-msd";
          }
          description
            "This container defines node Maximum SID Depth (MSD).";
          reference
            "RFC 8814: Signaling Maximum SID Depth (MSD) Using the
            Border Gateway Protocol - Link State. TLV 266";

          uses bgp-ls-topo-msd-attr;
        }

        container fads {
          when "derived-from-or-self(../type, " +
              "'bgp-ls-topo-t:bgp-ls-topo-attr-fad')" {
          description
              "Only include the fads container when the type is
              bgp-ls-topo-attr-fad";
          }
          description
            "This container defines the Flexible Algorithms
             supported by the node";
          reference
            "RFC 9351: Border Gateway Protocol - Link State (BGP-LS)
             Extensions for Flexible Algorithm Advertisement.
             TLV 1039";

          list fad {
            key "algorithm";

            description
              "List of FADs";

            leaf algorithm {
              type uint8 {
                range "128..255";
              }
              description
                "Flexible algorithm";
            }

            leaf metric-type {
              type uint8;
              description
                "Metric type";
            }

            leaf calc-type {
              type uint8;
              description
                "Calculation type";
            }

            leaf priority {
              type uint8;
              description
                "Priority of the FAD advertisement";
            }

            container node-fad-attributes {
              description
                "Enclosing container for node FAD attributes list";

              list node-fad-attribute {
                key "type";

                description
                  "List of node FAD attribute types.";

                leaf type {
                  type identityref {
                    base bgp-ls-topo-t:bgp-ls-topo-attr-fad-type;
                  }
                  description
                    "The type of node FAD attribute";
                }

                container exclude-any-affinity {
                  when "derived-from-or-self(../type, " +
                       "'bgp-ls-topo-t:" +
                       "bgp-ls-topo-attr-fad-excl-any-aff')" {
                    description
                      "Only include the exclude-any-affinity
                       container when the type is
                       bgp-ls-topo-attr-fad-excl-any-aff";
                  }
                  description
                    "This container contains the affinity constraints
                     associated with the FAD and enables the exclusion
                     of links carrying any of the specified affinities
                     from the computation of the specific algorithm";
                  reference
                    "RFC 9351: Border Gateway Protocol - Link State
                     (BGP-LS) Extensions for Flexible Algorithm
                     Advertisement. TLV 1040";

                  uses bgp-ls-topo-eag-attr;
                }

                container include-any-affinity {
                  when "derived-from-or-self(../type, " +
                       "'bgp-ls-topo-t:" +
                       "bgp-ls-topo-attr-fad-incl-any-aff')" {
                    description
                      "Only include the include-any-affinity container
                       when the type is
                       bgp-ls-topo-attr-fad-incl-any-aff";
                  }
                  description
                    "This container contains the affinity constraints
                     associated with the FAD and enables the
                     inclusion of links carrying any of the specified
                     affinities from the computation of the specific
                     algorithm";
                  reference
                    "RFC 9351: Border Gateway Protocol - Link State
                     (BGP-LS) Extensions for Flexible Algorithm
                     Advertisement. TLV 1041";

                  uses bgp-ls-topo-eag-attr;
                }

                container include-all-affinity {
                  when "derived-from-or-self(../type, " +
                       "'bgp-ls-topo-t:" +
                       "bgp-ls-topo-attr-fad-incl-all-aff')" {
                    description
                      "Only include the include-all-affinity
                       container when the type is
                       bgp-ls-topo-attr-fad-incl-all-aff";
                  }
                  description
                    "This container contains the affinity constraints
                     associated with the FAD and enables the inclusion
                     of links carrying all of the specified affinities
                     from the computation of the specific algorithm";
                  reference
                    "RFC 9351: Border Gateway Protocol - Link State
                     (BGP-LS) Extensions for Flexible Algorithm
                     Advertisement. TLV 1042";

                  uses bgp-ls-topo-eag-attr;
                }

                container flags {
                  when "derived-from-or-self(../type, " +
                       "'bgp-ls-topo-t:bgp-ls-topo-attr-fad-flags')" {
                    description
                      "Only include the flags container when the type is
                      bgp-ls-topo-attr-fad-flags";
                  }
                  description
                    "This container contains the flags associated with
                     the FAD";
                  reference
                    "RFC 9351: Border Gateway Protocol - Link State
                     (BGP-LS) Extensions for Flexible Algorithm
                     Advertisement. TLV 1043";

                  leaf flags {
                    type binary {
                      length "1..65535";
                    }
                    description
                      "Bit mask representing the FAD flags. The
                       flags are derived from the IS-IS and OSPF
                       protocol-specific Flexible Algorithm
                       Definition Flags sub-TLV.";
                    reference
                      "RFC 9350: IGP Flexible Algorithm.";
                  }
                }

                container exclude-srlg {
                  when "derived-from-or-self(../type, " +
                       "'bgp-ls-topo-t:" +
                       "bgp-ls-topo-attr-fad-excl-srlg')" {
                    description
                      "Only include the exclude-srlg container when the
                       type is bgp-ls-topo-attr-fad-excl-srlg";
                  }
                  description
                    "This container contains the affinity constraints
                     associated with the FAD and enables the
                     exclusion of links associated with any of the
                     specified SRLG from the computation of the
                     specific algorithm";
                  reference
                    "RFC 9351: Border Gateway Protocol - Link State
                     (BGP-LS) Extensions for Flexible Algorithm
                     Advertisement. TLV 1045";

                  uses bgp-ls-topo-srlg-attr;
                }

                container exclude-minimum-bw {
                  when "derived-from-or-self(../type, " +
                       "'bgp-ls-topo-t:" +
                       "bgp-ls-topo-attr-fad-excl-minimum-bw')" {
                    description
                      "Only include the exclude-minimum-bw container
                       when the type is
                       bgp-ls-topo-attr-fad-excl-minimum-bw";
                  }
                  description
                    "This container enables the exclusion of links not
                     having a minimum specified bandwidth from the
                     computation of the specific algorithm";
                  reference
                    "RFC TBD: BGP-LS extensions for IP Flexible
                     Algorithms and Bandwidth, Delay, Metrics and
                     Constraints. TLV TBD (1049)";

                  uses bgp-ls-topo-bw-attr;
                }

                container exclude-maximum-delay {
                  when "derived-from-or-self(../type, " +
                       "'bgp-ls-topo-t:" +
                       "bgp-ls-topo-attr-fad-excl-maximum-delay')" {
                    description
                      "Only include the exclude-maximum-delay
                       container when the type is
                       bgp-ls-topo-attr-fad-excl-maximum-delay";
                  }
                  description
                    "This container enables the exclusion of links
                     having delay above a maximum specified delay
                     from the computation of the specific algorithm";
                  reference
                    "RFC TBD: BGP-LS extensions for IP Flexible
                     Algorithms and Bandwidth, Delay, Metrics and
                     Constraints. TLV TBD (1050)";

                  uses bgp-ls-topo-delay-attr;
                }

                container exclude-any-reverse-affinity {
                  when "derived-from-or-self(../type, " +
                       "'bgp-ls-topo-t:" +
                       "bgp-ls-topo-attr-fad-excl-any-rev-aff')" {
                    description
                      "Only include the exclude-any-reverse-affinity
                       container when the type is
                       bgp-ls-topo-attr-fad-excl-any-rev-aff";
                  }
                  description
                    "This container contains the affinity constraints
                     associated with the FAD and enables the exclusion
                     of links carrying any of the specified affinities
                     in the reverse direction from the computation of
                     the specific algorithm";
                  reference
                    "RFC TBD: BGP-LS extensions for Flexible
                     Algorithms Reverse Affinity Constraint.
                     TLV TBD (1053)";

                  uses bgp-ls-topo-eag-attr;
                }

                container include-any-reverse-affinity {
                  when "derived-from-or-self(../type, " +
                       "'bgp-ls-topo-t:" +
                       "bgp-ls-topo-attr-fad-incl-any-rev-aff')" {
                    description
                      "Only include the include-any-reverse-affinity
                       container when the type is
                       bgp-ls-topo-attr-fad-incl-any-rev-aff";
                  }
                  description
                    "This container contains the affinity constraints
                     associated with the FAD and enables the
                     inclusion of links carrying any of the specified
                     affinities in the reverse direction from the
                     computation of the specific algorithm";
                  reference
                    "RFC TBD: BGP-LS extensions for Flexible
                     Algorithms Reverse Affinity Constraint.
                     TLV TBD (1054)";

                  uses bgp-ls-topo-eag-attr;
                }

                container include-all-reverse-affinity {
                  when "derived-from-or-self(../type, " +
                       "'bgp-ls-topo-t:" +
                       "bgp-ls-topo-attr-fad-incl-all-rev-aff')" {
                    description
                      "Only include the include-all-reverse-affinity
                       container when the type is
                       bgp-ls-topo-attr-fad-incl-all-rev-aff";
                  }
                  description
                    "This container contains the affinity constraints
                     associated with the FAD and enables the
                     inclusion of links carrying all of the specified
                     affinities in the reverse direction from the
                     computation of the specific algorithm";
                  reference
                    "RFC TBD: BGP-LS extensions for Flexible
                     Algorithms Reverse Affinity Constraint.
                     TLV TBD (1055)";

                  uses bgp-ls-topo-eag-attr;
                }

                container fa-unsupported-tlvs {
                  when "derived-from-or-self(../type, " +
                       "'bgp-ls-topo-t:" +
                       "bgp-ls-topo-attr-fa-unsupported')" {
                    description
                      "Only include the fa-unsupported-tlvs container
                       when the type is
                       bgp-ls-topo-attr-fa-unsupported";
                  }
                  description
                    "Indicates the presence of unsupported Flexible
                     Algorithm Definition (FAD) TLVs";
                  reference
                    "RFC 9351: Border Gateway Protocol - Link State
                     (BGP-LS) Extensions for Flexible Algorithm
                     Advertisement. TLV 1046";

                  leaf protocol-id {
                    type bgp-ls-topo-t:protocol;
                    description
                      "BGP-LS protocol advertising the FAD";
                  }

                  leaf-list type {
                    type uint16;
                    description
                      "List of unsupported TLV types.";
                  }
                }
              }
            }
          }
        }

        container isis-area-identifiers {
          when "derived-from-or-self(../type, " +
               "'bgp-ls-topo-t:" +
               "bgp-ls-topo-attr-isis-area-identifier')" {
          description
              "Only include the isis-area-identifiers
               container when the type is
               bgp-ls-topo-attr-isis-area-identifier";
          }
          description
            "This container contains the ISIS area addresses";
          reference
            "RFC 9552: Distribution of Link-State and Traffic
             Engineering Information Using BGP. TLV 1027";

          leaf-list area-address {
            type ietf-isis-t:area-address;
            description
            "List of ISIS area addresses";
          }
        }

        container srv6-capabilities-flags {
          when "derived-from-or-self(../type, " +
               "'bgp-ls-topo-t:bgp-ls-topo-attr-srv6-cap-flags')" {
            description
              "Only include the srv6-cap-flags container when the
               type is bgp-ls-topo-attr-srv6-cap-flags";
          }
          description
            "This container defines SRv6 capability flags.";
          reference
            "RFC 9514: SRv6 BGP-LS extensions.";
          leaf flags {
            type binary {
              length "1";
            }
            description
              "SRv6 capability flags.";
          }
        }
      }
    }
  }

  grouping bgp-ls-topo-igp-link-attr {
    description
      "Grouping for the BGP-LS topology link attributes";

    container link-attributes {
      description
        "Enclosing container for link attributes list";

      list link-attribute {
        key "type";

        description
          "List of link attribute types.";

        leaf type {
          type identityref {
            base bgp-ls-topo-t:bgp-ls-topo-attr-type;
          }
          description
            "The type of link attribute";
        }

        uses bgp-ls-topo-common-link-asla-l2-bundle-member-attr;

        container link-local-remote-identifiers {
          when "derived-from-or-self(../type, " +
               "'bgp-ls-topo-t:" +
               "bgp-ls-topo-attr-link-local-remote-identifiers')" {
            description
              "Only include the link-local-remote-identifiers
               container when the type is
               bgp-ls-topo-attr-link-local-remote-identifiers";
          }
          description
            "This container defines link local and remote
             identifiers.";
          reference
            "RFC 9552: Distribution of Link-State and Traffic
             Engineering Information Using BGP. TLV 258";

          leaf local-identifier {
            type uint32;
            description
              "Link local identifier";
          }

          leaf remote-identifier {
            type uint32;
            description
              "Link remote identifier";
          }
        }

        container link-msd {
          when "derived-from-or-self(../type, " +
               "'bgp-ls-topo-t:bgp-ls-topo-attr-link-msd')" {
            description
              "Only include the link-msd container when the type is
               bgp-ls-topo-attr-link-msd";
          }
          description
            "This container defines link Maximum SID Depth (MSD).";
          reference
            "RFC 8814: Signaling Maximum SID Depth (MSD) Using the
             Border Gateway Protocol - Link State. TLV 267";

          uses bgp-ls-topo-msd-attr;
        }

        container local-ipv4-router-ids {
          when "derived-from-or-self(../type, " +
               "'bgp-ls-topo-t:" +
               "bgp-ls-topo-attr-local-ipv4-routerid')" {
            description
              "Only include the local-ipv4-router-ids container
               when the type is
               bgp-ls-topo-attr-local-ipv4-routerid";
          }
          description
            "This container describes the auxiliary Router-IDs used
             by the IGP.";
          reference
            "RFC 9552: Distribution of Link-State and Traffic
             Engineering Information Using BGP. TLV 1028";
          uses bgp-ls-topo-ipv4-router-id-attr;
        }

        container local-ipv6-router-ids {
          when "derived-from-or-self(../type, " +
               "'bgp-ls-topo-t:" +
               "bgp-ls-topo-attr-local-ipv6-routerid')" {
            description
              "Only include the local-ipv6-router-ids container
               when the type is
               bgp-ls-topo-attr-local-ipv6-routerid";
          }
          description
            "This container describes the auxiliary Router-IDs used
             by the IGP.";
          reference
            "RFC 9552: Distribution of Link-State and Traffic
             Engineering Information Using BGP. TLV 1029";

          uses bgp-ls-topo-ipv6-router-id-attr;
        }

        container remote-ipv4-router-ids {
          when "derived-from-or-self(../type, " +
               "'bgp-ls-topo-t:" +
               "bgp-ls-topo-attr-remote-ipv4-routerid')" {
            description
              "Only include the remote-ipv4-router-ids container
               when the type is
               bgp-ls-topo-attr-remote-ipv4-routerid";
          }
          description
            "This container describes the auxiliary Router-IDs
             used by the IGP.";
          reference
            "RFC 9552: Distribution of Link-State and Traffic
             Engineering Information Using BGP. TLV 1030";

          uses bgp-ls-topo-ipv4-router-id-attr;
        }

        container remote-ipv6-router-ids {
          when "derived-from-or-self(../type, " +
               "'bgp-ls-topo-t:" +
               "bgp-ls-topo-attr-remote-ipv6-routerid')" {
            description
              "Only include the remote-ipv6-router-ids container
               when the type is
               bgp-ls-topo-attr-remote-ipv6-routerid";
          }
          description
            "This container describes the auxiliary Router-IDs
             used by the IGP.";
          reference
            "RFC 9552: Distribution of Link-State and Traffic
             Engineering Information Using BGP. TLV 1031";

          uses bgp-ls-topo-ipv6-router-id-attr;
        }

        container mpls-protocol-mask {
          when "derived-from-or-self(../type, " +
               "'bgp-ls-topo-t:" +
               "bgp-ls-topo-attr-mpls-protocol-mask')" {
            description
              "Only include the mpls-protocol-mask container when
               the type is bgp-ls-topo-attr-mpls-protocol-mask";
          }
          description
            "This container contains the bit mask describing MPLS
             signaling protocols enabled";
          reference
            "RFC 9552: Distribution of Link-State and Traffic
             Engineering Information Using BGP. TLV 1094";

          leaf mask {
            type uint8;
            description
              "Bit mask of MPLS signaling protocols enabled";
          }
        }

        container igp-metric {
          when "derived-from-or-self(../type, " +
               "'bgp-ls-topo-t:bgp-ls-topo-attr-igp-metric')" {
            description
              "Only include the igp-metric container when the type
               is bgp-ls-topo-attr-igp-metric";
          }
          description
            "This container specifies the metric of a link";
          reference
            "RFC 9552: Distribution of Link-State and Traffic
             Engineering Information Using BGP. TLV 1095";

          leaf metric {
            type uint32;
            description
              "IGP metric";
          }
        }

        container srlgs {
          when "derived-from-or-self(../type, " +
               "'bgp-ls-topo-t:bgp-ls-topo-attr-srlg')" {
            description
              "Only include the srlgs container when the type is
               bgp-ls-topo-attr-srlg";
          }
          description
            "This container specifies the Shared Risk Link Groups
             (SRLGs) of a link";
          reference
            "RFC 9552: Distribution of Link-State and Traffic
             Engineering Information Using BGP. TLV 1096";

          uses bgp-ls-topo-srlg-attr;
        }

        container opaque-link-attribute {
          when "derived-from-or-self(../type, " +
               "'bgp-ls-topo-t:bgp-ls-topo-attr-opaque-link')" {
            description
              "Only include the opaque-link-attribute container
               when the type is bgp-ls-topo-attr-opaque-link";
          }
          description
            "This container defines an envelope that transparently
             carries optional Link Attribute TLVs advertised by a
             router";
          reference
            "RFC 9552: Distribution of Link-State and Traffic
             Engineering Information Using BGP. TLV 1097";

          uses bgp-ls-topo-opaque-attribute;
        }

        container link-name {
          when "derived-from-or-self(../type, " +
               "'bgp-ls-topo-t:bgp-ls-topo-attr-link-name')" {
            description
              "Only include the link-name container when the
               type is bgp-ls-topo-attr-link-name";
          }
          description
            "This container identifies the symbolic name of
             the link";
          reference
            "RFC 9552: Distribution of Link-State and Traffic
             Engineering Information Using BGP. TLV 1098";

          leaf name {
            type string {
              length "1..255";
            }
            description
              "Link name";
          }
        }

        container srv6-end-x-sids {
          when "derived-from-or-self(../type, " +
               "'bgp-ls-topo-t:bgp-ls-topo-attr-srv6-end-x-sid')" {
            description
              "Only include the srv6-end-x-sids container when the
               type is bgp-ls-topo-attr-srv6-end-x-sid";
          }
          description
            "This container contains the Segment Routing over IPv6
             (SRv6) Segment Identifiers (SIDs) associated with an
             adjacency.";
          reference
            "RFC 9514: Border Gateway Protocol - Link State (BGP-LS)
             Extensions for Segment Routing over IPv6 (SRv6).
             TLV 1106";

          list srv6-end-x-sid {
            key "sid";

            description
              "List of SRv6 End.X SID";

            uses bgp-ls-topo-srv6-end-x-sid-attr;
          }
        }

        container srv6-lan-end-x-sids {
          when "derived-from-or-self(../type, " +
               "'bgp-ls-topo-t:" +
               "bgp-ls-topo-attr-srv6-isis-lan-end-x-sid')" +
               " or derived-from-or-self(../type, " +
               "'bgp-ls-topo-t:" +
               "bgp-ls-topo-attr-srv6-ospf-lan-end-x-sid')" {
            description
              "Only include the srv6-lan-end-x-sids container when
               the type is bgp-ls-topo-attr-srv6-isis-lan-end-x-sid
               or bgp-ls-topo-attr-srv6-ospf-lan-end-x-sid";
          }
          description
            "This container contains the Segment Routing over IPv6
             (SRv6) Segment Identifiers (SIDs) of an adjacency to
             any node in a LAN other than the pseudonode";
          reference
            "RFC 9514: Border Gateway Protocol - Link State (BGP-LS)
             Extensions for Segment Routing over IPv6 (SRv6).
             TLV 1107 / 1108";

          list srv6-end-x-sid {
            key "sid";

            description
              "List of SRv6 LAN End.X SID";

            uses bgp-ls-topo-srv6-end-x-sid-attr;

            leaf neighbor-id {
              type union {
                type inet:ipv4-address;
                type ietf-isis-t:system-id;
              }
              description
                "Neighbor ID";
            }
          }
        }

        uses bgp-ls-topo-common-link-l2-bundle-member-attr;

        container l2-bundle-members {
          when "derived-from-or-self(../type, " +
               "'bgp-ls-topo-t:" +
               "bgp-ls-topo-attr-l2-bundle-member')" {
            description
              "Only include the l2-bundle-members container when
               the type is bgp-ls-topo-attr-l2-bundle-member";
          }
          description
            "This container identifies an L2 bundle member link
             that is associated with a parent L3 link";
          reference
            "RFC 9085: Border Gateway Protocol - Link State (BGP-LS)
             Extensions for Segment Routing. TLV 1172";

          list l2-bundle-member {
            key "member-descriptor";

            description
              "List of L2 bundle members";

            leaf member-descriptor {
              type uint32;
              description
                "Link local identifier";
            }

            list bundle-member-attribute {
              key "type";

              description
                "List of bundle member attribute types.";

              leaf type {
                type identityref {
                  base bgp-ls-topo-t:bgp-ls-topo-attr-type;
                }
                description
                  "The type of bundle member attribute";
              }

              uses
                bgp-ls-topo-common-link-asla-l2-bundle-member-attr;
              uses bgp-ls-topo-common-link-l2-bundle-member-attr;
            }
          }
        }
      }
    }
  }

  grouping bgp-ls-topo-prefix-attr {
    description
      "Grouping for the BGP-LS topology prefix attributes";

    container prefix-attributes {
      description
        "Enclosing container for prefix attributes list";

      list prefix-attribute {
        key "type";

        description
          "List of prefix attribute types.";

        leaf type {
          type identityref {
            base bgp-ls-topo-t:bgp-ls-topo-attr-type;
          }
          description
            "The type of prefix attribute";
        }

        container flexible-algorithm-prefix-metric {
          when "derived-from-or-self(../type, " +
               "'bgp-ls-topo-t:" +
               "bgp-ls-topo-attr-fa-prefix-metric')" {
            description
              "Only include the flexible-algorithm-prefix-metric
               container when the type is
               bgp-ls-topo-attr-fa-prefix-metric";
          }
          description
            "This container defines the metric associated with the
             prefix for a particular Flexible Algorithm (FA)";
          reference
            "RFC 9351: Border Gateway Protocol - Link State (BGP-LS)
             Extensions for Flexible Algorithm Advertisement.
             TLV 1044";

          list fa-prefix-metric {
            key "algorithm";

            description
              "List of Flexible Algorithm prefix metrics";

            leaf metric {
              type uint32;
              description
                "Flexible Algorithm prefix metric";
            }

            leaf algorithm {
              type uint8 {
                range "128..255";
              }
              description
                "Flexible Algorithm";
            }

            leaf flags {
              type binary {
                length "1";
              }
              description
                "Flags associated with the Flexible Algorithm prefix
                 metric as defined in RFC 9350 for OSPFv2";
            }
          }
        }

        container igp-flags {
          when "derived-from-or-self(../type, " +
               "'bgp-ls-topo-t:bgp-ls-topo-attr-igp-flags')" {
            description
              "Only include the igp-flags container when the type is
               bgp-ls-topo-attr-igp-flags";
          }
          description
            "This container specifies the flags and bits assigned
             to a prefix";
          reference
            "RFC 9552: Distribution of Link-State and Traffic
             Engineering Information Using BGP. TLV 1152";

          leaf flags {
            type bgp-ls-topo-t:igp-flags-bits;
            description
              "IGP flags";
          }
        }

        container igp-route-tags {
          when "derived-from-or-self(../type, " +
               "'bgp-ls-topo-t:bgp-ls-topo-attr-igp-route-tag')" {
            description
              "Only include the igp-route-tags container when the
               type is bgp-ls-topo-attr-igp-route-tag";
          }
          description
            "This container specifies the tags of a prefix";
          reference
            "RFC 9552: Distribution of Link-State and Traffic
             Engineering Information Using BGP. TLV 1153";

          leaf-list tag {
            type uint32;
            description
              "List of IGP route tags";
          }
        }

        container extended-igp-route-tags {
          when "derived-from-or-self(../type, " +
               "'bgp-ls-topo-t:" +
               "bgp-ls-topo-attr-ext-igp-route-tag')" {
            description
              "Only include the extended-igp-route-tags container
               when the type is bgp-ls-topo-attr-ext-igp-route-tag";
          }
          description
            "This container specifies the extended route tags of a
             prefix";
          reference
            "RFC 9552: Distribution of Link-State and Traffic
             Engineering Information Using BGP. TLV 1154";

          leaf-list tag {
            type uint64;
            description
              "List of IGP extended route tags";
          }
        }

        container prefix-metric {
          when "derived-from-or-self(../type, " +
               "'bgp-ls-topo-t:bgp-ls-topo-attr-prefix-metric')" {
            description
              "Only include the prefix-metric container when the
               type is bgp-ls-topo-attr-prefix-metric";
          }
          description
            "This container specifies the metric of a prefix";
          reference
            "RFC 9552: Distribution of Link-State and Traffic
             Engineering Information Using BGP. TLV 1155";

          leaf metric {
            type uint32;
            description
              "Prefix metric";
          }
        }

        container ospf-forwarding-address {
          when "derived-from-or-self(../type, " +
               "'bgp-ls-topo-t:" +
               "bgp-ls-topo-attr-ospf-forwarding-address')" {
            description
              "Only include the ospf-forwarding-address container
               when the type is
               bgp-ls-topo-attr-ospf-forwarding-address";
          }
          description
            "This container specifies the forwarding address of a
             prefix as known in original OSPF advertisement";
          reference
            "RFC 9552: Distribution of Link-State and Traffic
             Engineering Information Using BGP. TLV 1156";

          leaf forw-address {
            type inet:ip-address;
            description
              "Forwarding address";
          }
        }

        container opaque-prefix-attribute {
          when "derived-from-or-self(../type, " +
               "'bgp-ls-topo-t:bgp-ls-topo-attr-opaque-prefix')" {
            description
              "Only include the opaque-prefix-attribute container
               when the type is bgp-ls-topo-attr-opaque-prefix";
          }
          description
            "This container defines an envelope that transparently
             carries optional Prefix Attribute TLVs advertised by a
             router";
          reference
            "RFC 9552: Distribution of Link-State and Traffic
             Engineering Information Using BGP. TLV 1157";

          uses bgp-ls-topo-opaque-attribute;
        }

        container prefix-sids {
          when "derived-from-or-self(../type, " +
               "'bgp-ls-topo-t:bgp-ls-topo-attr-prefix-sid')" {
            description
              "Only include the prefix-sids container when the type
               is bgp-ls-topo-attr-prefix-sid";
          }
          description
            "This container contains the prefix Segment Identifiers
             (SIDs) of a prefix";
          reference
            "RFC 9085: Border Gateway Protocol - Link State (BGP-LS)
             Extensions for Segment Routing. TLV 1158";

          list prefix-sid {
            key "label-index format";

            description
              "List of prefix SID";

            leaf label-index {
              type uint32;
              description
                "Label or index";
            }

            leaf format {
              type bgp-ls-topo-t:sid-format;
              description
                "Format of the SID";
            }

            leaf flags {
              type binary {
                length "1";
              }
              description
                "Flags as defined in Section 2.1.1 of RFC 8667 for
                 ISIS, Section 5 of RFC 8665 for OSPFv2 and
                 Section 6 of RFC 8665 for OSPFv3";
            }

            leaf algorithm {
              type uint8;
              description
                "Algorithm";
            }
          }
        }

        container prefix-range {
          when "derived-from-or-self(../type, " +
               "'bgp-ls-topo-t:bgp-ls-topo-attr-prefix-range')" {
            description
              "Only include the prefix-range container when the
               type is bgp-ls-topo-attr-prefix-range";
          }
          description
            "This container defines a range of
             prefix-to-SID mapping.";
          reference
            "RFC 9085: Border Gateway Protocol - Link State (BGP-LS)
             Extensions for Segment Routing. TLV 1159";

          leaf index {
            type uint32;
            description
              "Starting index of the range";
          }

          leaf range-size {
            type uint16;
            description
              "Number of prefixes covered by the advertisement";
          }

          leaf flags {
            type binary {
              length "1";
            }
            description
              "Flags associated with the range taken from IS-IS
               SID/Label Binding TLV flags as defined in
               Section 2.4.1 of RFC 8667 for ISIS, OSPFv2 OSPF
               Extended Prefix Range TLV flags as defined in
               Section 4 of RFC 8665 for OSPFv2 and OSPFv3
               Extended Prefix Range TLV flags as defined in
               Section 5 of RFC 8666 for OSPFv3";
          }

          leaf algorithm {
            type uint8;
            description
              "Algorithm";
          }

          leaf sid-flags {
            type binary {
              length "1";
            }
            description
              "Flags associated with the SID as defined in Section
               2.1.1 of RFC 8667 for ISIS, Section 5 of RFC 8665 for
               OSPFv2 and Section 6 of RFC 8665 for OSPFv3";
          }
        }

        container srv6-locator {
          when "derived-from-or-self(../type, " +
               "'bgp-ls-topo-t:bgp-ls-topo-attr-srv6-locator')" {
            description
              "Only include the srv6-locator container when the type
               is bgp-ls-topo-attr-srv6-locator";
          }
          description
            "This container contains the Segment Routing over IPv6
             (SRv6) locator information associated with a prefix.";
          reference
            "RFC 9514: Border Gateway Protocol - Link State (BGP-LS)
             Extensions for Segment Routing over IPv6 (SRv6).
             TLV 1162";

          leaf metric {
            type uint32;
            description
              "Flex algo prefix metric";
          }

          leaf flags {
            type binary {
              length "1";
            }
            description
              "Flags associated with the locator, copied from the
               IS-IS SRv6 Locator TLV (Section 7.1 of RFC 9352) for
               ISIS or the OSPFv3 SRv6 Locator TLV (Section 7.1 of
               RFC 9513) for OSPFv3";
          }

          leaf algorithm {
            type uint8;
            description
              "Algorithm associated with the locator";
          }
        }

        container prefix-attribute-flags {
          when "derived-from-or-self(../type, " +
            "'bgp-ls-topo-t:" +
            "bgp-ls-topo-attr-prefix-attribute-flags')" {
            description
              "Only include the prefix-attribute-flags container
            when the type is
            bgp-ls-topo-attr-prefix-attribute-flags";
          }
          description
            "This container defines the prefix attribute flags of a
             prefix";
          reference
            "RFC 9085: Border Gateway Protocol - Link State (BGP-LS)
             Extensions for Segment Routing. TLV 1170";

          leaf flags {
            type binary {
              length "1";
            }
            description
              "Prefix attribute flags as defined in Section 2.1 of
               RFC 7684 for OSPFv2, Appendix A.4.1.1 of RFC 5340 for
               OSPFv3, and Section 2.1 of RFC 7794 for IS-IS";
          }
        }

        container prefix-source-router-id {
          when "derived-from-or-self(../type, " +
            "'bgp-ls-topo-t:" +
            "bgp-ls-topo-attr-prefix-src-router-id')" {
            description
              "Only include the prefix-source-router-id container
               when the type is
               bgp-ls-topo-attr-prefix-src-router-id";
          }
          description
            "This container defines the source router identifier of
             a prefix";
          reference
            "RFC 9085: Border Gateway Protocol - Link State (BGP-LS)
             Extensions for Segment Routing. TLV 1171";

          leaf source-router-id {
            type inet:ip-address;
            description
              "Source router ID";
          }
        }

        container unknowns {
          when "derived-from-or-self(../type, " +
              "'bgp-ls-topo-t:bgp-ls-topo-attr-unknowns')" {
          description
              "Only include the unknowns container when the type is
              bgp-ls-topo-attr-unknowns";
          }
          description
            "This container describes the unknown attributes.";
          reference
            "RFC 9552: Distribution of Link-State and Traffic
             Engineering Information Using BGP.";

          uses bgp-ls-topo-unknown-attr;
        }
      }
    }
  }

  grouping bgp-ls-topo-srv6-sid-attr {
    description
      "Grouping for the BGP-LS topology SRv6 SID attributes";

    container srv6-sid-attributes {
      description
        "Enclosing container for SRv6 SID attributes list";

      list srv6-sid-attribute {
        key "type";

        description
          "List of SRv6 SID attribute types.";

        leaf type {
          type identityref {
            base bgp-ls-topo-t:bgp-ls-topo-attr-type;
          }
          description
            "The type of SRv6 SID attribute";
        }

        container srv6-endpoint-behavior {
          when "derived-from-or-self(../type, " +
               "'bgp-ls-topo-t:" +
               "bgp-ls-topo-attr-srv6-endpoint-behavior')" {
            description
              "Only include the srv6-endpoint-behavior container
               when the type is
               bgp-ls-topo-attr-srv6-endpoint-behavior";
          }
          description
            "This container contains the SRv6 endpoint behavior.";
          reference
            "RFC 9514: Border Gateway Protocol - Link State (BGP-LS)
             Extensions for Segment Routing over IPv6 (SRv6).
             SRv6 endpoint behavior. TLV 1250.";

          uses bgp-ls-topo-srv6-endpoint-behavior-attr;
        }

        container srv6-sid-structure {
          when "derived-from-or-self(../type, " +
               "'bgp-ls-topo-t:" +
               "bgp-ls-topo-attr-srv6-sid-structure')" {
            description
              "Only include the srv6-sid-structure container
               when the type is
               bgp-ls-topo-attr-srv6-sid-structure";
          }
          description
            "This container defines the SRv6 SID structure.";
          reference
            "RFC 9514: Border Gateway Protocol - Link State (BGP-LS)
             Extensions for Segment Routing over IPv6 (SRv6).
             SRv6 SID structure. TLV 1252.";

          uses bgp-ls-topo-srv6-sid-struct-attr;
        }

        container unknowns {
          when "derived-from-or-self(../type, " +
              "'bgp-ls-topo-t:bgp-ls-topo-attr-unknowns')" {
          description
              "Only include the unknowns container when the type is
              bgp-ls-topo-attr-unknowns";
          }
          description
            "This container describes the unknown attributes.";
          reference
            "RFC 9552: Distribution of Link-State and Traffic
             Engineering Information Using BGP.";

          uses bgp-ls-topo-unknown-attr;
        }
      }
    }
  }
}
