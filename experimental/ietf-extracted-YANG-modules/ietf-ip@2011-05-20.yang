module ietf-ip {

  namespace "urn:ietf:params:xml:ns:yang:ietf-ip";
  prefix ip;

  import ietf-interfaces {
    prefix if;
  }
  import ietf-inet-types {
    prefix inet;
  }

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>";

  description
    "This module contains a collection of YANG definitions for
     configuring IP addresses on network interfaces.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";

  // RFC Ed.: replace XXXX with actual RFC number and remove this
  // note.

  // RFC Ed.: update the date below with the date of RFC publication
  // and remove this note.
  revision 2011-05-20 {
    description
      "Initial revision.";
    reference
      "RFC XXXX: A YANG Data Model for IP Configuration";
  }

  augment "/if:interfaces/if:interface" {
    container ipv4 {
      description
        "Parameters for the IPv4 address familiy.";
      list address {
        key "ip";
        description
          "The list of manually configured IPv4 addresses
           on the interface.";

        leaf ip {
          type inet:ipv4-address;
        }
        leaf prefix-length {
          type uint8 {
            range "0..32";
          }
        }
      }
    }
    container ipv6 {
      description
        "Parameters for the IPv6 address familiy.";
      list address {
        key "ip";
        description
          "The list of manually configured IPv6 addresses
           on the interface.";

        leaf ip {
          type inet:ipv6-address;
        }
        leaf prefix-length {
          type uint8 {
            range "0..128";
          }
        }
      }
    }
  }
}
