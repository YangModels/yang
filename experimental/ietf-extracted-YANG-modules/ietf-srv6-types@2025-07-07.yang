module ietf-srv6-types {
  yang-version 1.1;

  namespace "urn:ietf:params:xml:ns:yang:ietf-srv6-types";
  prefix srv6-types;

  import ietf-inet-types {
    prefix inet;
    reference "RFC 6991: Common YANG Data Types";
  }

  organization
    "IETF SPRING Working Group";
  contact
    "WG Web:   <http://tools.ietf.org/wg/spring/>
     WG List:  <mailto:spring@ietf.org>

     Editor:   Kamran Raza
               <mailto:skraza@cisco.com>

     Editor:   Jaganbabu Rajamanickam
               <maito:jrajaman@cisco.com>

     Editor:   Xufeng Liu
               <mailto:xufeng.liu.ietf@gmail.com>

     Editor:   Zhibo Hu
               <mailto:huzhibo@huawei.com>

     Editor:   Iftekhar Hussain
               <mailto:iftekhar_hussain@yahoo.com>

     Editor:   Himanshu Shah
               <mailto:hshah@ciena.com>

     Editor:   Daniel Voyer
               <mailto:daniel.voyer@bell.ca>

     Editor:   Hani Elmalky
               <mailto:helmalky@google.com>

     Editor:   Satoru Matsushima
               <mailto:satoru.matsushima@gmail.com>

     Editor:   Katsuhiro Horiba
               <mailto:katsuhiro.horiba@gmail.com>

     Editor:   Ahmed AbdelSalam
               <mailto:ahabdels@cisco.com>

     Editor:   Pingping Yu
               <mailto:susana.yu@huawei.com>

     ";

  description
    "This YANG module defines the essential types for the
     management of Segment-Routing with IPv6 dataplane (SRv6).

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see the
     RFC itself for full legal notices.";

     // RFC Editor: replace XXXX with actual RFC number and remove
     // this note

  revision 2025-07-07 {
    description
      "Adding compressed SID and few other missing def";
    reference
      "RFC XXXX: YANG Data Model for SRv6";
    // RFC Editor: replace XXXX with actual RFC number and remove
    // this note
  }

  revision 2024-11-21 {
    description
      "Added SID structure definition and ";
    reference
      "RFC XXXX: YANG Data Model for SRv6";
     // RFC Editor: replace XXXX with actual RFC number and remove
     // this note
  }
  revision 2024-03-04 {
    description
      "Renamed some of End identities";
    reference
      "RFC XXXX: YANG Data Model for SRv6";
     // RFC Editor: replace XXXX with actual RFC number and remove
     // this note
  }

  revision 2022-01-14 {
    description
      "Alignment with SRv6 net-pgm rev16";
    reference
      "RFC XXXX: YANG Data Model for SRv6";
     // RFC Editor: replace XXXX with actual RFC number and remove
     // this note
  }

  revision 2019-10-30 {
    description
      "Renaming of some types";
    reference
      "RFC XXXX: YANG Data Model for SRv6";
     // RFC Editor: replace XXXX with actual RFC number and remove
     // this note
  }

  revision 2019-07-08 {
    description
      "Alignment with latest SRv6 network programming";
    reference
      "RFC XXXX: YANG Data Model for SRv6";
     // RFC Editor: replace XXXX with actual RFC number and remove
     // this note
  }

  revision 2018-10-22 {
    description
      "Initial revision.";
    reference
      "RFC XXXX: YANG Data Model for SRv6";
     // RFC Editor: replace XXXX with actual RFC number and remove
     // this note
  }

  identity srv6-endpoint-type {
    description
      "Base identity from which specific SRv6 Endpoint types are
      derived.";
  }

  /* Endpoints defined under draft-ietf-spring-
   * srv6-network-programming */

  identity End {
    base srv6-endpoint-type;
    description
      "End function (variant: no PSP, no USP).";
    reference
      "RFC 8986";
  }

  identity End_PSP {
    base srv6-endpoint-type;
    description
      "End function (variant: PSP only).";
    reference
      "RFC 8986";
  }
  identity End_USP {
    base srv6-endpoint-type;
    description
      "End function (variant: USP only).";
    reference
      "RFC 8986";
  }

  identity End_PSP_USP {
    base srv6-endpoint-type;
    description
      "End function (variant: PSP and USP).";
    reference
      "RFC 8986";
  }

  identity End.X {
    base srv6-endpoint-type;
    description
      "Endpoint with cross-connect to an array
      of layer-3 adjacencies (variant: no PSP, no USP).";
    reference
      "RFC 8986";
  }

  identity End.X_PSP {
    base srv6-endpoint-type;
    description
      "Endpoint with cross-connect to an array
      of layer-3 adjacencies (variant: PSP only).";
    reference
      "RFC 8986";
  }

  identity End.X_USP {
    base srv6-endpoint-type;
    description
      "Endpoint with cross-connect to an array
      of layer-3 adjacencies (variant: USP only).";
    reference
      "RFC 8986";
  }

  identity End.X_PSP_USP {
    base srv6-endpoint-type;
    description
      "Endpoint with cross-connect to an array
      of layer-3 adjacencies (variant: PSP and USP).";
    reference
      "RFC 8986";
  }

  identity End.T {
    base srv6-endpoint-type;
    description
      "Endpoint with specific IPv6 table lookup
      (variant: no PSP, no USP).";
    reference
      "RFC 8986";
  }

  identity End.T_PSP {
    base srv6-endpoint-type;
    description
      "Endpoint with specific IPv6 table lookup
      (variant: PSP only).";
    reference
      "RFC 8986";
  }

  identity End.T_USP {
    base srv6-endpoint-type;
    description
      "Endpoint with specific IPv6 table lookup
      (variant: USP only).";
    reference
      "RFC 8986";
  }

  identity End.T_PSP_USP {
    base srv6-endpoint-type;
    description
      "Endpoint with specific IPv6 table lookup
      (variant: PSP and USP).";
    reference
      "RFC 8986";
  }

  // TODO: End.B6.Insert

  identity End.B6.Encaps {
    base srv6-endpoint-type;
    description
      "Endpoint bound to an SRv6 Policy
      where the SRv6 Policy also includes an
      IPv6 Source Address A.";
    reference
      "RFC 8986";
  }

  identity End.BM {
    base srv6-endpoint-type;
    description
      "Endpoint bound to an SR-MPLS Policy";
    reference
      "RFC 8986";
  }

  identity End.DX6 {
    base srv6-endpoint-type;
    description
      "Endpoint with decapsulation and cross-connect
      to an array of IPv6 adjacencies";
    reference
      "RFC 8986";
  }
  identity End.DX4 {
    base srv6-endpoint-type;
    description
      "Endpoint with decapsulation and cross-connect
      to an array of IPv4 adjacencies";
    reference
      "RFC 8986";
  }

  identity End.DT6 {
    base srv6-endpoint-type;
    description
      "Endpoint with decapsulation and specific
      IPv6 table lookup";
    reference
      "RFC 8986";
  }

  identity End.DT4 {
    base srv6-endpoint-type;
    description
      "Endpoint with decapsulation and specific
      IPv4 table lookup";
    reference
      "RFC 8986";
  }

  identity End.DT46 {
    base srv6-endpoint-type;
    description
      "Endpoint with decapsulation and specific IP
      (IPv4 or IPv6) table lookup";
    reference
      "RFC 8986";
  }

  identity End.DX2 {
    base srv6-endpoint-type;
    description
      "Endpoint with decapsulation and Layer-2
      cross-connect to an L2 interface";
    reference
      "RFC 8986";
  }

  identity End.DX2V {
    base srv6-endpoint-type;
    description
      "Endpoint with decapsulation and specific
      VLAN L2 table lookup";
    reference
      "RFC 8986";
  }

  identity End.DT2U {
    base srv6-endpoint-type;
    description
      "Endpoint with decapsulation and specific
      unicast MAC L2 table lookup";
    reference
      "RFC 8986";
  }

  identity End.DT2M {
    base srv6-endpoint-type;
    description
      "Endpoint with decapsulation and specific L2 table
      flooding";
    reference
      "RFC 8986";
  }

  // TODO: End.B6.Insert.Red

  identity End.B6.Encaps.Red {
    base srv6-endpoint-type;
    description
      "This is a reduced encap variation of the End.B6.Encap
      behavior.";
    reference
      "RFC 8986";
  }

  identity End_USD {
    base srv6-endpoint-type;
    description
      "End function (variant: USD).";
    reference
      "RFC 8986";
  }

  identity End_PSP_USD {
    base srv6-endpoint-type;
    description
      "End function (variant: PSP and USD).";
    reference
      "RFC 8986";
  }
  identity End_USP_USD {
    base srv6-endpoint-type;
    description
      "End function (variant: USP and USD).";
    reference
      "RFC 8986";
  }

  identity End_PSP_USP_USD {
    base srv6-endpoint-type;
    description
      "End function (variant: PSP and USP and USD).";
    reference
      "RFC 8986";
  }

  identity End.X_USD {
    base srv6-endpoint-type;
    description
      "Endpoint with cross-connect to an array
      of layer-3 adjacencies (variant: USD).";
    reference
      "RFC 8986";
  }

  identity End.X_PSP_USD {
    base srv6-endpoint-type;
    description
      "Endpoint with cross-connect to an array
      of layer-3 adjacencies (variant: PSP and USD).";
    reference
      "RFC 8986";
  }

  identity End.X_USP_USD {
    base srv6-endpoint-type;
    description
      "Endpoint with cross-connect to an array
      of layer-3 adjacencies (variant: USP and USD).";
    reference
      "RFC 8986";
  }

  identity End.X_PSP_USP_USD {
    base srv6-endpoint-type;
    description
      "Endpoint with cross-connect to an array
      of layer-3 adjacencies (variant: PSP and USP and USD).";
    reference
      "RFC 8986";
  }

  identity End.T_USD {
    base srv6-endpoint-type;
    description
      "Endpoint with decapsulation and Layer-2
      cross-connect to an L2 interface";
    reference
      "RFC 8986";
  }

  identity End.T_PSP_USD {
    base srv6-endpoint-type;
    description
      "Endpoint with specific IPv6 table lookup
      (variant: PSP and USD).";
    reference
      "RFC 8986";
  }

  identity End.T_USP_USD {
    base srv6-endpoint-type;
    description
      "Endpoint with specific IPv6 table lookup
      (variant: USP and USD).";
    reference
      "RFC 8986";
  }
  identity End.T_PSP_USP_USD {
    base srv6-endpoint-type;
    description
      "Endpoint with specific IPv6 table lookup
      (variant: PSP and USP and USD).";
    reference
      "RFC 8986";
  }

  identity End.MAP {
    base srv6-endpoint-type;
    description
      "DMM End.MAP";
    reference
      "RFC9433";
  }

  identity End.Limit {
    base srv6-endpoint-type;
    description
      "DMM End.Limit";
    reference
      "RFC9433";
  }

  /* Endpoints defined under RFC9800 */

  identity END.NEXT-ONLY-CSID {
    base srv6-endpoint-type;
    description
      "End SID with the NEXT-ONLY-CSID flavor";
    reference
      "RFC 9800";
    // RFC Editor: replace with actual RFC number and remove this
    // note
  }

  identity END.NEXT-CSID {
    base srv6-endpoint-type;
    description
      "End SID with the NEXT-CSID flavor";
    reference
      "RFC 9800";
    // RFC Editor: replace with actual RFC number and remove this
    // note
  }

  identity END.NEXT-CSID_PSP {
    base srv6-endpoint-type;
    description
      "End SID with the NEXT-CSID PSP flavor";
    reference
      "RFC 9800";
    // RFC Editor: replace with actual RFC number and remove this
    // note
  }

  identity END.NEXT-CSID_USP {
    base srv6-endpoint-type;
    description
      "End SID with the NEXT-CSID USP flavor";
    reference
      "RFC 9800";
    // RFC Editor: replace with actual RFC number and remove this
    // note
  }

  identity END.NEXT-CSID_PSP_USP {
    base srv6-endpoint-type;
    description
      "End SID with the NEXT-CSID PSP/USP flavor";
    reference
      "RFC 9800";
    // RFC Editor: replace with actual RFC number and remove this
    // note
  }

  identity END.NEXT-CSID_USD {
    base srv6-endpoint-type;
    description
      "End SID with the NEXT-CSID USD flavor";
    reference
      "RFC 9800";
    // RFC Editor: replace with actual RFC number and remove this
    // note
  }

  identity END.NEXT-CSID_PSP_USD {
    base srv6-endpoint-type;
    description
      "End SID with the NEXT-CSID PSP/USD flavor";
    reference
      "RFC 9800";
    // RFC Editor: replace with actual RFC number and remove this
    // note
  }

  identity END.NEXT-CSID_USP_USD {
    base srv6-endpoint-type;
    description
      "End SID with the NEXT-CSID USP/USD flavor";
    reference
      "RFC 9800";
    // RFC Editor: replace with actual RFC number and remove this
    // note
  }

  identity END.NEXT-CSID_PSP_USP_USD {
    base srv6-endpoint-type;
    description
      "End SID with the NEXT-CSID PSP/USP/USD flavor";
    reference
      "RFC 9800";
    // RFC Editor: replace with actual RFC number and remove this
    // note
  }

  identity END.NEXT-CSID_ONLY {
    base srv6-endpoint-type;
    description
      "End.X SID with the NEXT-ONLY-CSID flavor";
    reference
      "RFC 9800";
    // RFC Editor: replace with actual RFC number and remove this
    // note
  }

  identity END.X.NEXT-CSID {
    base srv6-endpoint-type;
    description
      "End.X SID with the NEXT-CSID flavor";
    reference
      "RFC 9800";
    // RFC Editor: replace with actual RFC number and remove this
    // note
  }

  identity END.X.NEXT-CSID_PSP {
    base srv6-endpoint-type;
    description
      "End.X SID with the NEXT-CSID PSP flavor";
    reference
      "RFC 9800";
    // RFC Editor: replace with actual RFC number and remove this
    // note
  }

  identity END.X.NEXT-CSID_USP {
    base srv6-endpoint-type;
    description
      "End.X SID with the NEXT-CSID USP flavor";
    reference
      "RFC 9800";
    // RFC Editor: replace with actual RFC number and remove this
    // note
  }

  identity END.X.NEXT-CSID_PSP_USP {
    base srv6-endpoint-type;
    description
      "End.X SID with the NEXT-CSID PSP/USP flavor";
    reference
      "RFC 9800";
    // RFC Editor: replace with actual RFC number and remove this
    // note
  }

  identity END.X.NEXT-CSID_USD {
    base srv6-endpoint-type;
    description
      "End.X SID with the NEXT-CSID USD flavor";
    reference
      "RFC 9800";
    // RFC Editor: replace with actual RFC number and remove this
    // note
  }

  identity END.X.NEXT-CSID_PSP_USD {
    base srv6-endpoint-type;
    description
      "End.X SID with the NEXT-CSID PSP/USD flavor";
    reference
      "RFC 9800";
    // RFC Editor: replace with actual RFC number and remove this
    // note
  }

  identity END.X.NEXT-CSID_USP_USD {
    base srv6-endpoint-type;
    description
      "End.X SID with the NEXT-CSID USP/USD flavor";
    reference
      "RFC 9800";
    // RFC Editor: replace with actual RFC number and remove this
    // note
  }

  identity END.X.NEXT-CSID_PSP_USP_USD {
    base srv6-endpoint-type;
    description
      "End.X SID with the NEXT-CSID PSP/USP/USD flavor";
    reference
      "RFC 9800";
    // RFC Editor: replace with actual RFC number and remove this
    // note
  }

  identity End.DX6.NEXT-CSID {
    base srv6-endpoint-type;
    description
      "NEXT-CSID Endpoint with decapsulation and cross-connect
      to an array of IPv6 adjacencies";
    reference
      "RFC 9800";
  }
  identity End.DX4.NEXT-CSID {
    base srv6-endpoint-type;
    description
      "NEXT-CSID Endpoint with decapsulation and cross-connect
      to an array of IPv4 adjacencies";
    reference
      "RFC 9800";
  }

  identity End.DT6.NEXT-CSID {
    base srv6-endpoint-type;
    description
      "NEXT-CSID Endpoint with decapsulation and specific
      IPv6 table lookup";
    reference
      "RFC 9800";
  }

  identity End.DT4.NEXT-CSID {
    base srv6-endpoint-type;
    description
      "NEXT-CSID Endpoint with decapsulation and specific
      IPv4 table lookup";
    reference
      "RFC 9800";
  }

  identity End.DT46.NEXT-CSID {
    base srv6-endpoint-type;
    description
      "NEXT-CSID Endpoint with decapsulation and specific IP
      (IPv4 or IPv6) table lookup";
    reference
      "RFC 9800";
  }

  identity End.DX2.NEXT-CSID {
    base srv6-endpoint-type;
    description
      "NEXT-CSID Endpoint with decapsulation and Layer-2
      cross-connect to an L2 interface";
    reference
      "RFC 9800";
  }

  identity End.DX2V.NEXT-CSID {
    base srv6-endpoint-type;
    description
      "NEXT-CSID Endpoint with decapsulation and specific
      VLAN L2 table lookup";
    reference
      "RFC 9800";
  }

  identity End.DT2U.NEXT-CSID {
    base srv6-endpoint-type;
    description
      "NEXT-CSID Endpoint with decapsulation and specific
      unicast MAC L2 table lookup";
    reference
      "RFC 9800";
  }

  identity End.DT2M.NEXT-CSID {
    base srv6-endpoint-type;
    description
      "NEXT-CSID Endpoint with decapsulation and specific L2 table
      flooding";
    reference
      "RFC 9800";
  }

  /* DMM - RFC9433 */

  identity End.M.GTP6.D {
    base srv6-endpoint-type;
    description
      "DMM End.M.GTP6.D";
    reference
      "RFC 9433";
  }

  identity End.M.GTP6.Di {
    base srv6-endpoint-type;
    description
      "DMM End.M.GTP6.Di";
    reference
      "RFC 9433";
  }

  identity End.M.GTP6.E {
    base srv6-endpoint-type;
    description
      "DMM End.M.GTP6.E";
    reference
      "RFC 9433";
  }

  identity End.M.GTP4.E {
    base srv6-endpoint-type;
    description
      "DMM End.M.GTP4.E";
    reference
      "RFC 9433";
  }
  /* DMM end */

  // TODO: END.DTM
  // TODO: End.M
  // TODO: End.Replicate
  // TODO: End.DTMC4
  // TODO: End.DTMC6
  // TODO: End.DTMC46

  // TODO: End.T NEXT-CSID ...

  identity END.B6.Encaps.NEXT-CSID {
    base srv6-endpoint-type;
    description
      "End.B6.Encaps SID with the NEXT-CSID flavor";
    reference
      "RFC 9800";
    // RFC Editor: replace with actual RFC number and remove this
    // note
  }

  identity END.B6.Encaps.Red.NEXT-CSID {
    base srv6-endpoint-type;
    description
      "End.B6.Encaps.Red SID with the NEXT-CSID flavor";
    reference
      "RFC 9800";
    // RFC Editor: replace with actual RFC number and remove this
    // note
  }

  identity END.BM.NEXT-CSID {
    base srv6-endpoint-type;
    description
      "End.BM SID with the NEXT-CSID flavor";
    reference
      "RFC 9800";
    // RFC Editor: replace with actual RFC number and remove this
    // note
  }

  identity END.REPLACE-SID {
    base srv6-endpoint-type;
    description
      "End SID with the REPLACE-CSID flavor";
    reference
      "RFC 9800";
    // RFC Editor: replace with actual RFC number and remove this
    // note
  }

  identity END.REPLACE-SID_PSP {
    base srv6-endpoint-type;
    description
      "End SID with the REPLACE-CSID PSP flavor";
    reference
      "RFC 9800";
    // RFC Editor: replace with actual RFC number and remove this
    // note
  }

  identity END.REPLACE-SID_USP {
    base srv6-endpoint-type;
    description
      "End SID with the REPLACE-CSID USP flavor";
    reference
      "RFC 9800";
    // RFC Editor: replace with actual RFC number and remove this
    // note
  }

  identity END.REPLACE-SID_PSP_USP {
    base srv6-endpoint-type;
    description
      "End SID with the REPLACE-CSID PSP/USP flavor";
    reference
      "RFC 9800";
    // RFC Editor: replace with actual RFC number and remove this
    // note
  }

  identity END.X.REPLACE-CSID {
    base srv6-endpoint-type;
    description
      "End.X SID with the REPLACE-CSID flavor";
    reference
      "RFC 9800";
    // RFC Editor: replace with actual RFC number and remove this
    // note
  }

  identity END.X.REPLACE-CSID_PSP {
    base srv6-endpoint-type;
    description
      "End.X SID with the REPLACE-CSID PSP flavor";
    reference
      "RFC 9800";
    // RFC Editor: replace with actual RFC number and remove this
    // note
  }

  identity END.X.REPLACE-CSID_USP {
    base srv6-endpoint-type;
    description
      "End.X SID with the REPLACE-CSID USP flavor";
    reference
      "RFC 9800";
    // RFC Editor: replace with actual RFC number and remove this
    // note
  }

  identity END.X.REPLACE-CSID_PSP_USP {
    base srv6-endpoint-type;
    description
      "End SID with the REPLACE-CSID PSP/USP flavor";
    reference
      "RFC 9800";
    // RFC Editor: replace with actual RFC number and remove this
    // note
  }

  // TODO: End.T REPLACE-CSID

  identity END.B6.Encaps.REPLACE-CSID {
    base srv6-endpoint-type;
    description
      "End.B6.Encaps SID with the REPLACE-CSID flavor";
    reference
      "RFC 9800";
    // RFC Editor: replace with actual RFC number and remove this
    // note
  }

  identity END.BM.REPLACE-CSID {
    base srv6-endpoint-type;
    description
      "End.BM.Red SID with the REPLACE-CSID flavor";
    reference
      "RFC 9800";
    // RFC Editor: replace with actual RFC number and remove this
    // note
  }

  identity END.DX6.REPLACE-CSID {
    base srv6-endpoint-type;
    description
      "End.DX6 SID with the REPLACE-CSID flavor";
    reference
      "RFC 9800";
    // RFC Editor: replace with actual RFC number and remove this
    // note
  }

  identity END.DX4.REPLACE-CSID {
    base srv6-endpoint-type;
    description
      "End.DX4 SID with the REPLACE-CSID flavor";
    reference
      "RFC 9800";
    // RFC Editor: replace with actual RFC number and remove this
    // note
  }

  identity END.DT6.REPLACE-CSID {
    base srv6-endpoint-type;
    description
      "End.DT6 SID with the REPLACE-CSID flavor";
    reference
      "RFC 9800";
    // RFC Editor: replace with actual RFC number and remove this
    // note
  }

  identity END.DT4.REPLACE-CSID {
    base srv6-endpoint-type;
    description
      "End.DT4 SID with the REPLACE-CSID flavor";
    reference
      "RFC 9800";
    // RFC Editor: replace with actual RFC number and remove this
    // note
  }

  identity END.DT46.REPLACE-CSID {
    base srv6-endpoint-type;
    description
      "End.DT46 SID with the REPLACE-CSID flavor";
    reference
      "RFC 9800";
    // RFC Editor: replace with actual RFC number and remove this
    // note
  }

  identity END.DX2.REPLACE-CSID {
    base srv6-endpoint-type;
    description
      "End.DX2 SID with the REPLACE-CSID flavor";
    reference
      "RFC 9800";
    // RFC Editor: replace with actual RFC number and remove this
    // note
  }

  identity END.DX2V.REPLACE-CSID {
    base srv6-endpoint-type;
    description
      "End.DX2V SID with the REPLACE-CSID flavor";
    reference
      "RFC 9800";
    // RFC Editor: replace with actual RFC number and remove this
    // note
  }

  identity END.DT2U.REPLACE-CSID {
    base srv6-endpoint-type;
    description
      "End.DT2U SID with the REPLACE-CSID flavor";
    reference
      "RFC 9800";
    // RFC Editor: replace with actual RFC number and remove this
    // note
  }

  identity END.DT2M.REPLACE-CSID {
    base srv6-endpoint-type;
    description
      "End.DT2M SID with the REPLACE-CSID flavor";
    reference
      "RFC 9800";
    // RFC Editor: replace with actual RFC number and remove this
    // note
  }

  identity END.B6.Encaps.Red.REPLACE-CSID {
    base srv6-endpoint-type;
    description
      "End.B6.Encaps.Red SID with the REPLACE-CSID flavor";
    reference
      "RFC 9800";
    // RFC Editor: replace with actual RFC number and remove this
    // note
  }

  identity END.REPLACE-SID_USD {
    base srv6-endpoint-type;
    description
      "End SID with the REPLACE-CSID USD flavor";
    reference
      "RFC 9800";
    // RFC Editor: replace with actual RFC number and remove this
    // note
  }

  identity END.REPLACE-SID_PSP_USD {
    base srv6-endpoint-type;
    description
      "End SID with the REPLACE-CSID PSP/USD flavor";
    reference
      "RFC 9800";
    // RFC Editor: replace with actual RFC number and remove this
    // note
  }

  identity END.REPLACE-SID_USP_USD {
    base srv6-endpoint-type;
    description
      "End SID with the REPLACE-CSID USP/USD flavor";
    reference
      "RFC 9800";
    // RFC Editor: replace with actual RFC number and remove this
    // note
  }

  identity END.REPLACE-SID_PSP_USP_USD {
    base srv6-endpoint-type;
    description
      "End SID with the REPLACE-CSID PSP/USP/USD flavor";
    reference
      "RFC 9800";
    // RFC Editor: replace with actual RFC number and remove this
    // note
  }

  identity END.X.REPLACE-CSID_USD {
    base srv6-endpoint-type;
    description
      "End.X SID with the REPLACE-CSID USD flavor";
    reference
      "RFC 9800";
    // RFC Editor: replace with actual RFC number and remove this
    // note
  }

  identity END.X.REPLACE-CSID_PSP_USD {
    base srv6-endpoint-type;
    description
      "End.X SID with the REPLACE-CSID PSP/USD flavor";
    reference
      "RFC 9800";
    // RFC Editor: replace with actual RFC number and remove this
    // note
  }

  identity END.X.REPLACE-CSID_USP_USD {
    base srv6-endpoint-type;
    description
      "End.X SID with the REPLACE-CSID USP/USD flavor";
    reference
      "RFC 9800";
    // RFC Editor: replace with actual RFC number and remove this
    // note
  }

  identity END.X.REPLACE-CSID_PSP_USP_USD {
    base srv6-endpoint-type;
    description
      "End.X SID with the REPLACE-CSID PSP/USP/USD flavor";
    reference
      "RFC 9800";
    // RFC Editor: replace with actual RFC number and remove this
    // note
  }

  // TODO: End.T w/ REPLACE-CSID *USD
  // TODO: End.DX1*

  /* Endpoints defined under
   * draft-ietf-spring-sr-service-programming */

  identity End.AN {
    base srv6-endpoint-type;
    description
      "Service-Chaining SR Aware function (native)";
    reference
      "draft-ietf-spring-sr-service-programming-05";
    // RFC Editor: replace with actual RFC number and remove this
    // note
  }

  identity End.AS {
    base srv6-endpoint-type;
    description
      "Service-Chaining Static proxy";
    reference
      "draft-ietf-spring-sr-service-programming-05";
    // RFC Editor: replace with actual RFC number and remove this
    // note
  }

  identity End.AD {
    base srv6-endpoint-type;
    description
      "Service-Chaining Dynamic proxy";
    reference
      "draft-ietf-spring-sr-service-programming-05";
    // RFC Editor: replace with actual RFC number and remove this
    // note
  }

  identity End.AM {
    base srv6-endpoint-type;
    description
      "Service-Chaining Masquerading SR proxy";
    reference
      "draft-ietf-spring-sr-service-programming-05";
    // RFC Editor: replace with actual RFC number and remove this
    // note
  }

  identity End.AM_NAT {
    base srv6-endpoint-type;
    description
      "Service-Chaining Masquerading SR proxy with NAT";
    reference
      "draft-ietf-spring-sr-service-programming-05";
    // RFC Editor: replace with actual RFC number and remove this
    // note
  }

  identity End.AM_CACHE {
    base srv6-endpoint-type;
    description
      "Service-Chaining Masquerading SR proxy with Caching";
    reference
      "draft-ietf-spring-sr-service-programming-05";
    // RFC Editor: replace with actual RFC number and remove this
    // note
  }

  identity End.AM_NAT_CACHE {
    base srv6-endpoint-type;
    description
      "Service-Chaining Masquerading SR proxy with NAT and
      Caching";
    reference
      "draft-ietf-spring-sr-service-programming-05";
    // RFC Editor: replace with actual RFC number and remove this
    // note
  }

  identity srv6-headend-type {
    description
      "Base identity from which SRv6 headend rule types are
      derived.";
  }

  identity H.Encaps {
    base srv6-headend-type;
    description
      "Headend rule H.Encaps with encapsulated of an SRv6 policy";
    reference
      "draft-ietf-spring-srv6-network-programming-16";
    // RFC Editor: replace with actual RFC number and remove this
    // note
  }

  identity H.Encaps.Red {
    base srv6-headend-type;
    description
      "Headend rule H.Encaps.Red with reduced encap of an
      SRv6 policy";
    reference
      "draft-ietf-spring-srv6-network-programming-16";
    // RFC Editor: replace with actual RFC number and remove this
    // note
  }

  identity H.Encaps.L2 {
    base srv6-headend-type;
    description
      "Headend rule H.Encaps.l2 on the received L2 frame";
    reference
      "draft-ietf-spring-srv6-network-programming-16";
    // RFC Editor: replace with actual RFC number and remove this
    // note
  }

  identity H.Encaps.L2.Red {
    base srv6-headend-type;
    description
      "Headend rule H.Encaps.L2.Red on the received L2 frame";
    reference
      "draft-ietf-spring-srv6-network-programming-16";
    // RFC Editor: replace with actual RFC number and remove this
    // note
  }

  identity srv6-security-type {
    description
      "Base identity from which SRv6 Security rule types are
      derived.";
  }

  identity EXTIF-ACL-DROP-DA-SIDSPACE {
    base srv6-security-type;
    description
      "Support an ACL on the external interface that
      drops any traffic with DA within the internal SID space.";
    reference
      "RFC 8754 section 5.1";
  }

  identity INTIF-ACL-DROP-DA-SIDSPACE-SA-EXT  {
    base srv6-security-type;
    description
      "Support an ACL that drops any traffic on mySID as DA
      from a source SA that does not belong to internal address
      or SID space.)";
    reference
      "RFC 8754 section 5.1";
  }

  identity srv6-counter-type {
    description
      "Base identity from which SRv6 counter types are derived.";
  }

  identity CNT-MySID-Success {
    base srv6-counter-type;
    description
      "Count packets and bytes traffic that matched mySID and
      was processed successfully";
    reference
      "RFC 8986 section 6";
  }

  typedef srv6-sid {
    type inet:ipv6-prefix;
    description
      "This type defines a SID value in SRv6";
  }

  typedef srv6-sid-compression-type {
    type enumeration {
      enum uncompressed { value 1; description "Uncompressed"; }
      enum csid-next { description "Compressed NEXT-CSID (aka uSID)"; }
      enum csid-replace { description "Compressed REPLACE-CSID"; }
    }
    description
      "SID [compression] type";
  }

  typedef srv6-sid-func-value {
    type uint32;
    description
      "This is a typedef for SID's FUNC value";
  }

  typedef srv6-sid-func-value-reserved-type {
    type enumeration {
      enum invalid {
        value 0;
        description "Invalid function value";
      }
    }

    description "SRv6 SID's FUNC Reserved values";
  }
  typedef srv6-locator-name-type {
    type string {
      length "1..59";
    }
    description "SRv6 locator name";
  }

  typedef srv6-locator-len {
    type uint8 {
      range "16 .. 96";
    }
    description
      "This type defines an SRv6 locator len with range
      constraints";
  }

  typedef srv6-locator-block-len {
    type uint8;
    description
      "This type defines an SRv6 locator block length in bits";
  }

  typedef srv6-locator-node-len {
    type uint8;
    description
      "This type defines an SRv6 locator node length in bits";
  }

  typedef srv6-sid-func-len {
    type uint8;
    description
      "This type defines an SRv6 SID function length in bits";
  }

  typedef srv6-sid-arg-len {
    type uint8;
    description
      "This type defines an SRv6 SID argument length in bits";
  }

  typedef srv6-sid-pfxlen {
    type uint8 {
      range "16 .. 128";
    }
    default 128;
    description
      "This type defines a SID prefixlen with range constraints";
  }
  typedef sid-alloc-type {
    type enumeration {
      enum Dynamic {
        description
          "SID allocated dynamically.";
      }
      enum Explicit {
        description
          "SID allocated with explicit (static) value";
      }
    }
    description
      "Types of sid allocation used.";
  }

  identity srv6-sid-owner-type {
    description
      "Base identity from which SID owner types are derived.";
  }

  identity isis {
    base srv6-sid-owner-type;
    description "ISIS";
  }

  identity ospfv3 {
    base srv6-sid-owner-type;
    description "OSPFv3";
  }

  identity bgp {
    base srv6-sid-owner-type;
    description "BGP";
  }

  identity evpn {
    base srv6-sid-owner-type;
    description "EVPN";
  }

  identity sr-policy {
    base srv6-sid-owner-type;
    description "SR Policy";
  }

  identity service-function {
    base srv6-sid-owner-type;
    description "SF";
  }

  identity static {
    base srv6-sid-owner-type;
    description "Static";
  }

  typedef table-id {
    type uint32;
    description
      "Routing/switching/bridging/VLAN Table Id";
  }

  typedef srv6-status-type {
    type enumeration {
      enum up { value 1; description "State is Up"; }
      enum down { description "State is Down"; }
    }
    description
      "Status type";
  }

  typedef srv6-nexthop-type {
    type enumeration {
      enum ipv4 { value 1; description "IPv4 next-hop"; }
      enum ipv6 { description "IPv6 next-hop"; }
      enum mpls { description "MPLS next-hop"; }
      enum l3_lookup { description "L3 Lookup in a table"; }
      enum l2 { description "L2 next-hop"; }
      enum l2_lookup { description "L2 Lookup in a table"; }
    }
    description
      "Forwarding Next-hop type";
  }

  grouping srv6-sid-structure-grouping {
    description "SRv6 SID structure grouping";

    leaf locator-block-length {
      type srv6-types:srv6-locator-block-len;
      description "SRv6 SID locator block length in bits";
    }
    leaf locator-node-length {
      type srv6-types:srv6-locator-node-len;
      description "SRv6 SID locator node length in bits";
    }
    leaf function-length {
      type srv6-types:srv6-sid-func-len;
      description "SRv6 SID function length in bits";
    }
    leaf argument-length {
      type srv6-types:srv6-sid-arg-len;
      description "SRv6 SID argument length in bits";
    }
  }

  grouping srv6-sid-structure-info-grouping {
    description "SRv6 SID structure info grouping";

   container sid-structure {
    config false;
    description "SID structure container";

    uses srv6-sid-structure-grouping;
   }
 }

  // Base identity for SID formats
  identity srv6-sid-format-type {
    description
      "Base identity from which SID format types are derived.";
  }

  identity srv6-sid-fmt-uc-1 {
    base srv6-sid-format-type;
    description
       "Uncompressed SID format with LBL=40, LNL=24, FL=16, and AL=16 or more.
       The locator length for this format is 64 bits.";
  }

  identity srv6-sid-fmt-uc-128 {
    base srv6-sid-format-type;
    description
       "Uncompressed SID format that allows flexible values for LBL/LNL/FL/AL.";
  }

  identity srv6-sid-fmt-cnext-1616 {
    base srv6-sid-format-type;
    description "Compressed NEXT-CSID format using LBL=16, LNL=16,
              FL=16 (or 32 for wide function), and AL=16 or more.
              The locator length for this format is 32 bits.";
  }

  identity srv6-sid-fmt-cnext-3216 {
    base srv6-sid-format-type;
    description "Compressed NEXT-CSID format using LBL=32, LNL=16,
              FL=16 (or 32 for wide function), and AL=16 or more.
              The locator length for this format is 48 bits.";
  }

  identity srv6-sid-fmt-cnext-4816 {
    base srv6-sid-format-type;
    description "Compressed NEXT-CSID format using LBL=48, LNL=16,
              FL=16 (or 32 for wide function), and AL=16 or more.
              The locator length for this format is 64 bits.";
  }

  identity srv6-sid-fmt-cnext-6416 {
    base srv6-sid-format-type;
    description "Compressed NEXT-CSID format using LBL=64, LNL=16,
              FL=16 (or 32 for wide function), and AL=16 or more.
              The locator length for this format is 80 bits.";
  }

  // TODO: srv6-sid-fmt-crepl-XYZ

} // module
