module ietf-microwave-topology {
 yang-version 1.1;
  namespace "urn:ietf:params:xml:ns:yang:ietf-microwave-topology";

  prefix "mwtopo";

  import ietf-network {
    prefix "nw";
  }

  import ietf-network-topology {
    prefix "nt";
  }

  import ietf-te-topology {
    prefix "tet";
  }

  import ietf-routing-types {
    prefix "rt-types";
  }

  import ietf-yang-schema-mount {
       prefix yangmnt;
       reference "draft-ietf-netmod-schema-mount: YANG Schema Mount";
     }
 organization
  "Internet Engineering Task Force (IETF) CCAMP WG";
 contact
  "
  WG List: <mailto:ccamp@ietf.org>

  ID-draft authors:
   Min Ye (amy.yemin@huawei.com);
   Aihua Guo (aihuaguo@huawei.com);
   Jonas Ahlberg (jonas.ahlberg@ericsson.com);
   Xi Li (Xi.Li@neclab.eu);
   Daniela Spreafico (daniela.spreafico@nokia.com)
  ";

 description
  "This is a module for microwave topology.";

   revision 2018-06-30 {
    description
    "Updated version to add mount point to the interface model.";
    reference "";
  }

   revision 2018-03-05 {
    description
    "Initial version.";
    reference "";
  }

  /*
   * Groupings
   */
  grouping mw-link-attributes {
     description "Microwave link attributes";

         leaf mw-link-frequency {
           type uint32;
           units "kHz";
           description "Frequency of the link";
           }

         leaf mw-link-channel-separation {
           type uint32;
           units "kHz";
           description "The distance
            between adjacent channels in a radio frequency channel
            arrangement used in this link";
           reference "ETSI EN 302 217-1";
           }

          leaf mw-link-nominal-bandwidth {
            type rt-types:bandwidth-ieee-float32;
                units "Mbps";
                config false;
                description "The nominal bandwidth of the link";
          }

          leaf mw-link-current-bandwidth {
           type rt-types:bandwidth-ieee-float32;
           units "Mbps";
           config false;
           description "The current bandwidth of the link";
           }

          leaf mw-unreserved-bandwidth {
           type rt-types:bandwidth-ieee-float32;
           units "Mbps";
           description "the unreserved bandwidth of the link";
           }

          list mw-link-availability{
                key "availability";
                description "List of availability and corresponding
                             link bandwidth";

                leaf availability {
                  type rt-types:percentage;
                  description "availability level of the link";
                }

                leaf mw-link-bandwidth {
                  type rt-types:bandwidth-ieee-float32;
                  units "Mbps";
                  config false;
                  description "The link bandwidth corresponding
                               to the availability level";
                  }
     }

      container "interface-root" {
           description
             "Container for mount point.";
           yangmnt:mount-point "interface-root" {
             description
               "Root for microwave rado interface model.
                            It could contain an interface instance.";
           }
         }

        }

  /*
   * Data nodes
   */
   augment "/nw:networks/nw:network/nw:network-types/"
        + "tet:te-topology" {
    container mw-topology {
      presence "indicates a topology type of microwave.";
      description "microwave topology type";
    }
    description "augment network types to include microwave network";
  }

  augment "/nw:networks/nw:network/nt:link/tet:te/"
        + "tet:te-link-attributes" {
    when "../../../nw:network-types/tet:te-topology/"
       + "mwtopo:mw-topology" {
      description "This augment is only valid for microwave.";
    }
    description "Microwave link augmentation";

    uses mw-link-attributes;
  }

 }
