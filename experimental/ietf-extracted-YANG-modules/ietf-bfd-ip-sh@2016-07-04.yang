module ietf-bfd-ip-sh {
  namespace "urn:ietf:params:xml:ns:yang:ietf-bfd-ip-sh";
  // replace with IANA namespace when assigned
  prefix "bfd-ip-sh";

  import ietf-bfd {
    prefix "bfd";
  }

  import ietf-interfaces {
    prefix "if";
  }

  import ietf-inet-types {
    prefix "inet";
  }

  import ietf-network-instance {
    prefix "ni";
  }

  organization "IETF BFD Working Group";

  contact
    "WG Web:   <http://tools.ietf.org/wg/bfd>
     WG List:  <rtg-bfd@ietf.org>
     WG Chair: Jeff Haas
     WG Chair: Reshad Rahman
     Editor:   Lianshu Zheng and Reshad Rahman";

  description
    "This module contains the YANG definition for BFD IP single-hop
     as per RFC5881.";

  revision 2016-07-04 {
    description "Initial revision.";
    reference "RFC XXXX: A YANG data model for BFD IP single-hop";
  }

  augment "/bfd:bfd" {
    description "BFD augmentation for IP single-hop";
    container ip-sh {
      description "BFD IP single-hop top level container";

      container config {
        description "BFD IP single-hop configuration container";
      }
      container oper {
        config "false";
        description "BFD IP single-hop operational container";
        uses bfd:bfd-session-statistics;
      }
    }
  }

  augment "/ni:network-instances/ni:network-instance/bfd:bfd" {
    description "BFD augmentation for IP single-hop.";

    container ip-sh {
      description "BFD IP single-hop container";
      container config {
        description "BFD configuration";
        container session-cfg {
          description "BFD IP single-hop session configuration";

          list sessions {
            key "interface dest-addr";
            description "List of IP single-hop sessions";
            leaf interface {
              type if:interface-ref;
              description
                "Interface on which the BFD session is running.";
            }
            leaf dest-addr {
              type inet:ip-address;
              description "IP address of the peer";
            }
            leaf source-addr {
              type inet:ip-address;
              description "Local address";
            }

            uses bfd:bfd-grouping-common-cfg-parms;

            uses bfd:bfd-grouping-echo-cfg-parms;
          }
        }
      }

      container oper {
        config "false";
        description "BFD operational container";

        uses bfd:bfd-session-statistics;

        list sessions {
          key "interface dest-addr";
          description "BFD IP single-hop sessions";
          leaf interface {
            type if:interface-ref;
            description
              "Interface on which the BFD session is running.";
          }
          leaf dest-addr {
            type inet:ip-address;
            description "BFD peer address";
          }
          leaf source-addr {
            type inet:ip-address;
            description "BFD source address";
          }

          uses bfd:bfd-all-session;
        }
      }
    }
  }

  notification bfd-singlehop-notification {
    description
      "Notification for BFD single-hop session state change. An " +
      "implementation may rate-limit notifications, e.g. when a" +
      "session is continuously changing state.";

    uses bfd:bfd-notification-parms;

    leaf interface {
      type if:interface-ref;
      description "Interface to which this BFD session belongs to";
    }

    leaf echo-enabled {
      type boolean;
      description "Was echo enabled for BFD";
    }
  }

}
