module ietf-yang-hash {
  namespace "urn:ietf:params:xml:ns:yang:ietf-yang-hash";
  prefix "yh";

  organization
    "IETF CORE (Constrained RESTful Environments) Working Group";

  contact
    "WG Web:   <http://tools.ietf.org/wg/core/>
     WG List:  <mailto:core@ietf.org>
     WG Chair: Carsten Bormann
               <mailto:cabo@tzi.org>

     WG Chair: Andrew McGregor
               <mailto:andrewmcgr@google.com>

     Editor:   Peter van der Stok
               <mailto:consultancy@vanderstok.org>

     Editor:   Andy Bierman
               <mailto:andy@yumaworks.com>

     Editor:   Juergen Schoenwaelder
               <mailto:j.schoenwaelder@jacobs-university.de>

     Editor:   Anuj Sehgal
               <mailto:s.anuj@jacobs-university.de>";

  description
    "This module contains re-hash information for the CoMI protocol.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: remove this note
  // Note: extracted from draft-vanderstok-core-comi-07.txt

  // RFC Ed.: update the date below with the date of RFC publication
  // and remove this note.
  revision 2015-06-06 {
    description
      "Initial revision.";
    reference
      "RFC XXXX: CoMI Protocol.";
  }
  container yang-hash {
    config false;
    description
      "Contains information on the YANG Hash values used by
       the server.";

    list rehash {
      key hash;
      description
        "Each entry describes an re-hash mapping in use by
         the server.";

      leaf hash {
        type uint32;
        description
          "The hash value that has a collision.  This hash value
           cannot be used on the server.  The rehashed
           value for each affected object must be used instead.";
      }

      list object {
        min-elements 2;

        description
          "Each entry identifies one of the objects involved in the
           hash collision and contains the rehash information for
           that object.";

        leaf module {
          type string;
          mandatory true;
          description
            "The module name for this object.";
        }

        leaf newhash {
          type uint32;
          mandatory true;
          description
            "The new hash value for this object.";
        }

        leaf pathlen {
          type uint32;
          description
            "The length of the path expression of the object with
             this hash value.  This object MUST be included
             for any objects in the rehash entry with the
             same 'module' value.";
        }

        leaf path {
          type string;
          description
            "The path expression of the object with
             this hash value. This object MUST be included
             for any objects in the rehash entry with the
             same 'module' and 'pathlen' values.";
        }

      }
    }
  }
}
