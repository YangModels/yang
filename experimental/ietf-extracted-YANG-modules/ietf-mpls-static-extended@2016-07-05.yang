module ietf-mpls-static-extended {

  namespace "urn:ietf:params:xml:ns:yang:ietf-mpls-static-extended";

  prefix "mpls-static-ext";

  import ietf-mpls {
    prefix "mpls";
  }

  import ietf-routing {
    prefix "rt";
  }

  import ietf-mpls-static {
    prefix "mpls-static";
  }

  organization "IETF MPLS Working Group";

  contact
    "WG Web:   <http://tools.ietf.org/wg/mpls/>

     WG List:  <mailto:mpls@ietf.org>

     WG Chair: Loa Andersson
               <mailto:loa@pi.nu>

     WG Chair: Ross Callon
               <mailto:rcallon@juniper.net>
     WG Chair: George Swallow
               <mailto:swallow.ietf@gmail.com>

     Editor:   Tarek Saad
               <mailto:tsaad@cisco.com>

     Editor:   Kamran Raza
               <mailto:skraza@cisco.com>

     Editor:   Rakesh Gandhi
               <mailto:rgandhi@cisco.com>

     Editor:   Xufeng Liu
               <mailto: xufeng.liu.ietf@gmail.com>

     Editor:   Vishnu Pavan Beeram
               <mailto:vbeeram@juniper.net>

     Editor:   Himanshu Shah
               <mailto:hshah@ciena.com>

     Editor:   Igor Bryskin
               <mailto: Igor.Bryskin@huawei.com>

     Editor:   Xia Chen
               <mailto:jescia.chenxia@huawei.com>

     Editor:   Raqib Jones
               <mailto:raqib@Brocade.com>

     Editor:   Bin Wen
               <mailto:Bin_Wen@cable.comcast.com>";

  description
    "This module contains the Extended RSVP YANG data model.";

  revision 2016-07-05 {
    description "Latest revision of RSVP extended yang module.";
    reference "RFC2205";
  }

  /* RSVP features */
  feature bandwidth {
    description
      "Indicates support for static LSP bandwidth allocation";
  }

  grouping static-lsp-extended_config {
    description
      "Configuration parameters for MPLS extended
       parameters";
    leaf bandwidth {
      type uint32;
      description
        "bandwidth in Mbps, e.g., using offline calculation";
    }
    leaf lsp-priority-setup {
      type uint8 {
        range "0..7";
      }
      description "LSP setup priority";
    }
    leaf lsp-priority-hold {
      type uint8 {
        range "0..7";
      }
      description "LSP hold priority";
    }
  }

  grouping bidir-static-lsp_config {
    description "common definitions for static LSPs";
    leaf forward-lsp {
      type mpls-static:static-lsp-ref;
      description
        "Reference to a configured static forward LSP";
                }
    leaf reverse-lsp {
      type mpls-static:static-lsp-ref;
      description
        "Reference to a configured static reverse LSP";
                }
  }

  grouping bidir-static-lsp {
    description "grouping for top level list of static LSPs";
    container config {
      description
        "Holds the intended configuration";
      uses bidir-static-lsp_config;
    }
    container state {
      config false;
      description
        "Holds the state and inuse configuration";
      uses bidir-static-lsp_config;
    }
  }

  augment "/rt:routing/mpls:mpls/mpls-static:static-lsps" {
    description
      "RSVP signaling all interfaces configuration extensions";
    uses static-lsp-extended_config;
  }

  augment "/rt:routing/mpls:mpls" {
    description "Augmentations for MPLS Static LSPs";
    container bidir-static-lsps {
      description
        "Statically configured LSPs, without dynamic signaling";
      list bidir-static-lsp {
        key name;
        description "list of defined static LSPs";

        leaf name {
          type string;
          description "name to identify the LSP";
        }
        uses bidir-static-lsp;
      }
    }
  }
}
