module ietf-service-assurance-device {
yang-version 1.1;
namespace "urn:ietf:params:xml:ns:yang:ietf-service-assurance-device";
prefix service-assurance-device;

import ietf-service-assurance {
  prefix "service-assurance";
}

organization
  "IETF NETCONF (Network Configuration) Working Group";
contact
  "WG Web:   <https://datatracker.ietf.org/wg/netconf/>
   WG List:  <mailto:netconf@ietf.org>
   Author:   Benoit Claise  <mailto:bclaise@cisco.com>
   Author:   Jean Quilbeuf   <mailto:jquilbeu@cisco.com>";
description
 "This module extends the ietf-service-assurance module to add
  support for the subservice DeviceHealthy.

  Network Device is healthy.

  The key words 'MUST', 'MUST NOT', 'REQUIRED', 'SHALL',
  'SHALL NOT', 'SHOULD', 'SHOULD NOT', 'RECOMMENDED',
  'NOT RECOMMENDED', 'MAY', and 'OPTIONAL' in this document
  are to be interpreted as described in BCP 14 (RFC 2119)
  (RFC 8174) when, and only when, they appear in all
  capitals, as shown here.

  Copyright (c) 2019 IETF Trust and the persons identified as
  authors of the code.  All rights reserved.

  Redistribution and use in source and binary forms, with or
  without modification, is permitted pursuant to, and subject
  to the license terms contained in, the Simplified BSD License
  set forth in Section 4.c of the IETF Trust's Legal Provisions
  Relating to IETF Documents
  (https://trustee.ietf.org/license-info).

  This version of this YANG module is part of RFC XXXX; see the
  RFC itself for full legal notices.";

revision 2019-10-04 {
  description
    "Initial revision.";
  reference
      "RFC xxxx: Title to be completed";
}

identity device-idty {
  base service-assurance:subservice-idty;
  description "Network Device is healthy.";
}

augment /service-assurance:subservices/service-assurance:subservice/service-assurance:parameter {
     description
       "Specify the required parameters for a new subservice type";
     container device-idty{
         when "derived-from-or-self(../service-assurance:type, 'device-idty')";
         description
           "Specify the required parameters for the device-idty subservice type";

         leaf device {
             type string;
             description "The device to monitor.";
         }
     }
}
}
