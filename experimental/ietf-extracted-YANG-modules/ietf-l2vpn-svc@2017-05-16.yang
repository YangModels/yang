module ietf-l2vpn-svc {
     namespace "urn:ietf:params:xml:ns:yang:ietf-l2vpn-svc";
     prefix "l2svc";

     import ietf-inet-types {
       prefix inet;
     }
     import ietf-yang-types {
       prefix yang;
     }
     import iana-if-type {
       prefix ianaift;
     }

     organization
       "IETF L2SM Working Group.";
     contact
       "WG List: l2sm@ietf.org
        Editor: Bin_Wen@comcast.com";
     description
       "The YANG module defines a generic service configuration
        model for Layer 2 VPN services common across all of the
        vendor implementations.";
     revision 2017-05-16{
       description
         "Initial revision -05 version";
       reference
         "draft-wen-l2sm-l2vpn-service-model-04.txt
          A YANG Data Model for L2VPN Service Delivery.";
     }

     /* Features */
     feature L2CP-control {
      description
     "L2CP control";
     }

     feature input-bw {
       description
         "Input Bandwidth";
     }
     feature output-bw {
       description
         "Output Bandwidth";
     }
     feature uni-list {
       description
         "Enable support UNI list";
     }
     feature ovc-type {
       description
         "Enable support OVC type";
     }
     feature cloud-access {
       description
         "Allow VPN to connect to a Cloud Service
          provider.";
     }
     feature oam-3ah {
       description
         "Enables support of OAM 802.3ah";
     }
     feature Micro-BFD {
       description
         "Enables support of Micro-BFD";
     }
     feature bfd {
       description
         "Enables support of BFD";
     }
     feature signaling-option {
       description
         "Enable support of signaling option";
     }
     feature site-diversity {
       description
         "Enables support of site diversity constraints";
     }
     feature encryption {
       description
         "Enables support of encryption";
     }
     feature always-on {
       description
         "Enables support for always-on access
          constraint.";
     }
     feature requested-type {
       description
         "Enables support for requested-type access
          constraint.";
     }
     feature bearer-reference {
       description
         "Enables support for bearer-reference access
          constraint.";
     }
     feature qos {
       description
         "Enables support of Class of Services";
     }
     feature qos-custom {
       description
         "Enables support of custom qos profile";
     }
     feature LAG-interface{
      description
    "Enable LAG-interface";
    }
     /* Typedefs */

     typedef svc-id {
       type string;
       description
         "Service ID";
     }
     typedef direction-type {
       type string;
       description
         "Direction";
     }
     typedef evc-id-type {
       type string;
       description
         "EVC ID type";
     }
     typedef ovc-id-type {
       type string;
       description
         "OVC ID type";
     }
     typedef ccm-priority-type {
       type uint8 {
         range "0..7";
       }
       description
         "A 3 bit priority value to be used in the VLAN tag, if present
          in the transmitted frame.";
     }
     typedef control-mode {
       type enumeration {
         enum peer {
           description
             "Peer mode";
         }
         enum tunnel {
           description
             "Tunnel mode";
         }
         enum discard {
           description
             "Discard mode";
         }
      }
      description
        "Defining a type of the control mode";
     }
     typedef neg-mode {
       type enumeration {
         enum full-duplex {
           description
             "Full duplex mode";
         }
         enum auto-neg {
           description
             "Auto negotiation mode";
         }

      }
      description
        "Defining a type of the negotiation mode";
     }

     /* Identities */
    identity site-network-access-type {
     description
      "Base identity for site-network-access type.";
    }

    identity point-to-point {
     base site-network-access-type;
     description
      "Identity for point-to-point connection.";
    }

    identity multipoint {
     base site-network-access-type;
     description
      "Identity for multipoint connection.";
    }

   identity encapsulation-type {
    description
    "Identity of encapsulation type";
   }

  identity eth-type {
    description
    "Identity of ethernet type";
   }

     identity bw-type {
       description
         "Identity of bandwidth";
     }
     identity bw-per-cos {
       base bw-type;
       description
         "Bandwidth is per cos";
     }
     identity bw-per-connection {
       base bw-type;
       description
         "Bandwidth is per connection or site network access";
     }
     identity bw-per-port {
       base bw-type;
       description
         "Bandwidth is per site";
     }

     identity opaque {
       base bw-type;
       description
         "Opaque";
     }
     identity site-type {
       description
         "Identity of site type.";
     }
     identity uni {
       base site-type;
       description
         "Identity of User Network Interface ";
     }
     identity enni {
       base site-type;
       description
         "Identity of External Network to Network Interface";
     }
     identity service-type {
       description
         "Identity of service type.";
     }
     identity vpws {
       base service-type;
       description
         " point-to-point Virtual Private Wire Services(VPWS) type.";
     }
     identity pwe3 {
       base service-type;
       description
         " Pseudo-Wire Emulation Edge to Edge (PWE3) Service type. .";

     }
     identity evpn {
     base service-type;
     description
      "Ethernet VPN Service Type, Ethernet VPNs are specified in RFC 7432";}

    identity vpls-ldp {
    base service-type;
    description
   "LDP based multipoint Virtual Private LAN services (VPLS) Service Type.
   This VPLS uses LDP-signaled Pseudowires";
   }
   identity vpls-bgp {
   base service-type;
   description
   "BGP based multipoint Virtual Private LAN services (VPLS)
   Service Type. This VPLS uses a Border Gateway Protocol
   (BGP) control plane as described in RFC4761 and RFC6624. ";
   }
   identity epl {
   base service-type;
   description
   "Ethernet Private Line (EPL) Service Type. ";
   }
   identity evpl {
   base service-type;
   description
   "Ethernet Virtual Private Line (EVPL) Service Type. ";
   }

   identity ep-lan {
   base service-type;
   description
   " Ethernet Private LAN (EP-LAN)Service Type. ";
   }
   identity evp-lan {
   base service-type;
   description
   " Ethernet Virtual Private LAN (EVP-LAN)Service Type. ";
   }

     identity bundling-type {
       description
         "Bundling type.";
     }
     identity bundling {
       base bundling-type;
       description
         "Identity for bundling";
     }
     identity all2one-Bundling {
       base bundling-type;
       description
         "Identity for all to one bundling";
     }
     identity color-id {
       description
         "Identity of color id";
     }
     identity color-id-evc {
       base color-id;
       description
         "Identity of color id base on EVC";
     }
     identity color-id-evc-cvlan {
       base color-id;
       description
         "Identity of color id base on EVC and CVLAN ";
     }
     identity cos-id {
       description
         "Identity of class of service id";
     }
     identity cos-id-evc {
       base cos-id;
       description
         "Identity of cos id based on EVC";
     }
     identity cos-id-evc-pcp {
       base cos-id;
       description
         "Identity of cos id based on EVC and PCP";
     }
     identity cos-id-evc-dscp {
       base cos-id;
       description
         "Identity of cos id based on EVC and DSCP";
     }

     identity cos-id-ovc-ep {
       base cos-id;
       description
         "Identity of cos id based on OVC EP";
     }
     identity color-type {
       description
         "Identity of color types";
     }
     identity green {
       base color-type;
       description
         "Identity of green type,
          applicable to CIR conforming traffic.
         if color-type is green, Forwardedframes";
     }
     identity yellow {
       base color-type;
       description
         "Identity of yellow type
          applicable to traffic Over CIR, within EIR.
          if color-type is yellow,Discard
          Eligible frames";
     }
     identity red {
       base color-type;
       description
         "Identity of red type
        applicable to traffic Exceeding EIR.
        if color-type is red, Discarded frames";
     }
     identity perf-tier-opt {
       description
         "Identity of performance tier option.";
     }
     identity metro {
       base perf-tier-opt;
       description
         "Identity of metro";
     }
     identity regional {
       base perf-tier-opt;
       description
         "Identity of regional";
     }
     identity continental {
       base perf-tier-opt;
       description
         "Identity of continental";
     }
     identity global {
       base perf-tier-opt;
       description
         "Identity of global";
     }

     identity policing {
       description
         "Identity of policing type";
     }
     identity one-rate-two-color {
       base policing;
       description
         "Identity of one-rate, two-color (1R2C)";
     }
     identity two-rate-three-color {
       base policing;
       description
         "Identity of two-rate, three-color (2R3C)";
     }
     identity BUM-type {
       description
         "Identity of BUM type";
     }
     identity broadcast {
       base BUM-type;
       description
         "Identity of broadcast";
     }
     identity unicast {
       base BUM-type;
       description
         "Identity of unicast";
     }
     identity multicast {
       base BUM-type;
       description
         "Identity of multicast";
     }
     identity loop-prevention-type{
       description
         "Identity of loop prevention";
     }
     identity shut {
       base loop-prevention-type;
       description
         "Identity of shut protection";
     }
     identity trap {
       base loop-prevention-type;
       description
         "Identity of trap protection";
     }
     identity lacp-state {
       description
         "Identity of LACP state";
     }
     identity lacp-on {
       base lacp-state;
       description
         "Identity of LCAP on";
     }
     identity lacp-off {
       base lacp-state;
       description
         "Identity of LACP off";
     }
     identity lacp-mode {
       description
         "Identity of LACP mode";
     }
     identity lacp-passive {
       base lacp-mode;
       description
         "Identity of LACP passive";
     }
     identity lacp-active {
       base lacp-mode;
       description
         "Identity of LACP active";
     }
     identity lacp-speed {
       description
         "Identity of LACP speed";
     }
     identity lacp-fast {
       base lacp-speed;
       description
         "Identity of LACP fast";
     }
     identity lacp-slow {
       base lacp-speed;
       description
         "Identity of LACP slow";
     }
     identity vpn-signaling-type {
        description
          "Identity of VPN signaling types";
     }
     identity vpws-vsi {
       base vpn-signaling-type;
       description
         "Virtual Private Wire Service";
     }
     identity pwe3-vsi {
       base vpn-signaling-type;
       description
         "PWE3 Service";
     }

     identity vpls-vfi {
       base vpn-signaling-type;
       description
         "Virtual Private LAN Service";
     }

     identity evpn-evi {
       base vpn-signaling-type;
       description
         "EVPN Service";
     }

     identity l2vpn-type {
       description
         "Layer 2 VPN types";
     }
     identity kompella {
       base l2vpn-type;
       description
         "Use BGP as signaling protocol.";
     }
     identity martini {
       base l2vpn-type;
       description
         "Use LDP as signaling protocol";
     }
     identity evpn-type {
       description
         "Ethernet VPN types";
     }
     identity pbb {
       base evpn-type;
       description
         " Provider Backbone Bridging-EVPN";
     }

     identity management {
       description
         "Base identity for site management scheme.";
     }
     identity co-managed {
       base management;
       description
         "Base identity for co-managed site.";
     }
     identity customer-managed {
       base management;
       description
         "Base identity for customer managed site.";
     }
     identity provider-managed {
       base management;
       description
         "Base identity for provider managed site.";
     }
     identity address-family {
       description
         "Base identity for an address family.";
     }
     identity ipv4 {
       base address-family;
       description
         "Identity for IPv4 address family.";
     }
     identity ipv6 {
       base address-family;
       description
         "Identity for IPv6 address family.";
     }
     identity vpn-topology {
       description
         "Base identity for VPN topology.";
     }
     identity any-to-any {
       base vpn-topology;
       description
         "Identity for any to any VPN topology.";
     }
     identity hub-spoke {
       base vpn-topology;
       description
         "Identity for Hub'n'Spoke VPN topology.";
     }
     identity hub-spoke-disjoint {
       base vpn-topology;
       description
         "Identity for Hub'n'Spoke VPN topology
          where Hubs cannot talk between each other.";
     }
     identity site-role {
       description
         "Base identity for site type.";
     }
     identity any-to-any-role {
       base site-role;
       description
         "Site in an any to any IPVPN.";
     }
     identity spoke-role {
       base site-role;
       description

         "Spoke Site in a Hub &amp; Spoke IPVPN.";
     }
     identity hub-role {
       base site-role;
       description
         "Hub Site in a Hub &amp Spoke IPVPN.";
     }
     identity pm-type {
       description
         "Performance monitor type";
     }
     identity loss {
       base pm-type;
       description
         "Loss measurement";
     }
     identity delay {
       base pm-type;
       description
         "Delay measurement";
     }
     identity fault-alarm-defect-type {
       description
         "Indicating the alarm priority defect";
     }
     identity remote-rdi {
       base fault-alarm-defect-type;
       description
         "Indicates the aggregate health of the remote MEPs.";
     }
     identity remote-mac-error {
       base fault-alarm-defect-type;
       description
         "Indicates that one or more of the remote MEPs is
          reporting a failure in its Port Status TLV or
          Interface Status TLV.";
     }
     identity remote-invalid-ccm {
       base fault-alarm-defect-type;
       description
         "Indicates that at least one of the Remote MEP
          state machines is not receiving valid CCMs
          from its remote MEP.";
      }
      identity invalid-ccm {
        base fault-alarm-defect-type;
        description
          "Indicates that one or more invalid CCMs has been
           received and that 3.5 times that CCMs transmission
           interval has not yet expired.";
      }
      identity cross-connect-ccm {
        base fault-alarm-defect-type;
        description
          "Indicates that one or more cross connect CCMs has been
           received and that 3.5 times of at least one of those
           CCMs transmission interval has not yet expired.";
      }
      identity data-svc-frame-delivery {
        description
          "Delivery types";
      }
      identity discard {
        base data-svc-frame-delivery;
        description
          "Service Frames are discarded.";
      }
      identity unconditional {
        base data-svc-frame-delivery;
        description
          "Service Frames are unconditionally";
      }
      identity conditional {
        base data-svc-frame-delivery;
        description
          "Service Frame are conditionally
           delivered to the destination UNI.";
      }
      identity evc-type {
        description
          "Service topology Type";
      }
      identity point-to-point-type {
        base evc-type;
        description
          "Point to Point.";
      }
      identity multipoint-to-multipoint {
        base evc-type;
        description
          "Multipoint to Multipoint.";
      }
      identity rooted-multipoint {
        base evc-type;
        description
          "Rooted Multipoint.";
      }

       identity placement-diversity {
         description
           "Base identity for site placement
            constraints";
       }
       identity bearer-diverse {
         base placement-diversity;
         description
           "Identity for bearer diversity.
            The bearers should not use common elements.";
       }
       identity pe-diverse {
         base placement-diversity;
         description
           "Identity for PE diversity";
       }
       identity pop-diverse {
         base placement-diversity;
         description
           "Identity for POP diversity";
       }
       identity linecard-diverse {
         base placement-diversity;
         description
           "Identity for linecard diversity";
       }
       identity same-pe {
         base placement-diversity;
         description
           "Identity for having sites connected
            on the same PE";
       }
       identity same-bearer {
         base placement-diversity;
         description
           "Identity for having sites connected
            using the same bearer";
       }
       identity l2-access-type {
         description
           "This identify the access type
            of the vpn acccess interface";
       }
       identity untag {
         base l2-access-type;
         description
           "Untag";
       }
       identity port {
         base l2-access-type;
         description
           "Port";
       }
       identity dot1q {
         base l2-access-type;
         description
           "Qot1q";
       }
       identity qinq {
         base l2-access-type;
         description
           "QinQ";
       }
       identity sub-interface {
         base l2-access-type;
         description
          "Create a default sub-interface and keep vlan";
       }
       identity vxlan {
         base l2-access-type;
         description
           "Vxlan access into the vpn";
       }
       identity mac-learning-mode {
         description
           "MAC learning mode";
       }
       identity data-plane {
         base mac-learning-mode;
         description
           "User MAC addresses are learned through ARP broadcast.";
       }
       identity control-plane {
         base mac-learning-mode;
         description
           "User MAC addresses are advertised through EVPN-BGP";
       }

     /* Groupings */
     grouping vpn-service-cloud-access {
       container cloud-accesses {
         if-feature cloud-access;
         list cloud-access {
           key cloud-identifier;
           leaf cloud-identifier {
             type string;
             description
               "Identification of cloud service. Local
                admin meaning.";
           }
           choice list-flavor {
             case permit-any {
               leaf permit-any {
                 type empty;
                 description
                   "Allow all sites.";
               }
             }
             case deny-any-except {
               leaf-list permit-site {
                 type leafref {
                   path "/l2vpn-svc/sites/site/site-id";
                 }
                 description
                   "Site ID to be authorized.";
               }
             }
             case permit-any-except {
               leaf-list deny-site {
                 type leafref {
                   path "/l2vpn-svc/sites/site/site-id";
                 }
                 description
                   "Site ID to be denied.";
               }
             }
             description
               "Choice for cloud access policy.";
           }
           container authorized-sites {
             list authorized-site {
               key site-id;
               leaf site-id {
                 type leafref {
                   path "/l2vpn-svc/sites/site/site-id";
                 }
                 description
                   "Site ID.";
               }
               description
                 "List of authorized sites.";
             }
             description
               "Configuration of authorized sites";
           }
           container denied-sites {
             list denied-site {

               key site-id;
               leaf site-id {
                 type leafref {
                   path "/l2vpn-svc/sites/site/site-id";
                 }
                 description
                   "Site ID.";
               }
               description
                 "List of denied sites.";
             }
             description
               "Configuration of denied sites";
           }
           description
             "Cloud access configuration.";
         }
         description
           "Container for cloud access configurations";
       }
       description
        "Grouping for vpn cloud definition";
     }

     grouping site-device {
       container device {
         list devices {
           key "device-id";
           leaf device-id {
             type string;
             description
               "Device ID";
           }
           leaf site-name {
             type string;
             description
               "Site name";
           }
           container management {
             leaf address {
               type inet:ip-address;
               description
                 "Address";
             }
             leaf management-transport {
               type identityref {
                 base address-family;
               }
               description
                 "Transport protocol used for management.";
             }
             description
               "Container for management";
           }
           description
             "List of devices";
         }
         description
           "Devices configuration";
       }
       description
         "Device parameters for the site.";
     }

     grouping site-management {
       container management {
         leaf type {
           type identityref {
             base management;
           }
           description
             "Management type of the connection.";
         }
         description
           "Container for management";
       }
      description
        "Grouping for management";
     }

     grouping site-vpn-policy {
       container vpn-policies {
         list vpn-policy {
           key vpn-policy-id;
           leaf vpn-policy-id {
             type string;
             description
               "Unique identifier for the VPN policy.";
           }
           list entries {
             key id;
             leaf id {
               type string;
               description
                 "Unique identifier for the policy entry.";
             }

             container filter {
               choice lan {
                 case lan-tag {
                   leaf-list lan-tag {
                     type string;
                     description
                       "List of lan-tags to be matched.";
                   }
                 }
                 description
                   "Choice for LAN matching type";
               }
               description
                 "If used, it permit to split site LANs
                  among multiple VPNs.
                  If no filter used, all the LANs will be
                  part of the same VPNs with the same
                  role.";
             }
             container vpn {
               leaf vpn-id {
                 type leafref {
                   path "/l2vpn-svc/vpn-services/"+
                        "vpn-svc/vpn-id";
                 }
                 mandatory true;
                 description
                   "Reference to an IPVPN.";
               }
               leaf site-role {
                 type identityref {
                   base site-role;
                 }
                 default any-to-any-role;
                 description
                   "Role of the site in the IPVPN.";
               }
               description
                 "List of VPNs the LAN is associated to.";
             }
             description
               "List of entries for export policy.";
           }
           description
             "List of VPN policies.";
         }
         description
           "VPN policy.";
       }
       description
         "VPN policy parameters for the site.";
     }

     grouping umb-frame-delivery {
       leaf unicast-frame-delivery {
         type identityref {
           base data-svc-frame-delivery;
         }
         description
           "Unicast Data Service Frame Delivery Mode
            (unconditional[default], conditional, or discard).";
       }
       leaf multicast-frame-delivery {
         type identityref {
           base data-svc-frame-delivery;
         }
         description
           "Multicast Data Service Frame Delivery Mode
            (unconditional[default], conditional, or discard).";
       }
       leaf broadcast-frame-delivery {
         type identityref {
           base data-svc-frame-delivery;
         }
         description
           "Broadcast Data Service Frame Delivery Mode
            (unconditional[default], conditional, or discard).";
       }
       description
         "Grouping for unicast, mulitcast, broadcast frame delivery";
     }

     grouping customer-location-info {
       container location {
         leaf address {
           type string;
           description
             "Address (number and street) of the site.";
         }
         leaf zip-code {
           type string;
           description
             "ZIP code of the site.";
         }
         leaf state {
           type string;
           description
             "State of the site. This leaf can also be used to
              describe a region for country who does not have
              states.";
         }
         leaf city {
           type string;
           description
             "City of the site.";
         }
         leaf country-code {
           type string;
           description
             "Country of the site.";
         }
         description
           "Location of the site.";
       }
       description
         "This grouping defines customer location parameters";
      }

      grouping site-diversity {
        container site-diversity {
          if-feature site-diversity;
          container groups {
            list group {
              key group-id;
              leaf group-id {
                type string;
                description
                  "Group-id the site is belonging to";
              }
              description
                "List of group-id";
            }
            description
              "Groups the site is belonging to.
               All site network accesses will inherit those group
               values.";
          }
          description
            "Diversity constraint type.";
        }
        description
          "This grouping defines site diversity parameters";
      }

      grouping site-service {

        list cvlan-id-to-evc-map {
          key "evc-id type";
          leaf evc-id {
            type leafref {
              path "/l2vpn-svc/vpn-services/vpn-svc/vpn-id";
            }
            description
              "EVC ID";
          }
          leaf type {
            type identityref {
              base bundling-type;
            }
            description
              "Bundling type";
          }
          list cvlan-id {
            key vid;
            leaf vid {
              type identityref {
                base ianaift:iana-interface-type;
              }
              description
                "CVLAN ID";
            }
            description
              "List of CVLAN-ID to EVC Map configurations";
          }
          description
            "List for cvlan-id to evc map configurations";
        }
        leaf service-level-mac-limit {
          type string;
          description
            "Service-level MAC-limit (E-LAN only)";
        }
        description
          "This grouping defines site service parameters";
      }

      grouping service-protection {
        container service-protection {
          container protection-model {
            description
              "Container of protection model configurations";
          }
          container peer-evc-ovc-id {
            description
              "Container of peer EVC ID configurations";
          }
          description
            "Container of End-to-end Service Protection
             configurations";
        }
        description
          "Grouping for service protection";
      }

      grouping signaling-option-grouping {
        list signaling-option {
          key "type";
          leaf type {
            type identityref {
              base vpn-signaling-type;
            }
            description
              "VPN signaling types";
          }
          container bgp-ldp-l2vpn {
            leaf vpn-id {
              type svc-id;
              description
                "Identifies the target VPN";
            }
            leaf type {
              type identityref {
                base l2vpn-type;
              }
              description
                "L2VPN types";
            }
            description
              "Container for MP BGP L2VPN";
          }
          container mp-bgp-evpn {
            leaf vpn-id {
              type svc-id;
              description
                "Identifies the target VPN";
            }
            leaf type {
              type identityref {
                base evpn-type;
              }
              description
                "L2VPN types";
            }
            leaf mac-learning-mode {
              type identityref {
                base mac-learning-mode;
              }
              description
                "Indicates through which plane MAC addresses are
                 advertised.";
            }
            leaf arp-suppress {
              type boolean;
              default false;
              description
                "Indicates whether to suppress ARP broadcast.";
            }
            description
              "Container for MP BGP L2VPN";
          }
          container t-ldp-pwe {
          leaf type {
          type identityref {
          base l2vpn-type;
          }
        description
        "T-LDP PWE type";
         }
            list pe-eg-list {
              key "service-ip-lo-addr vc-id";
              leaf service-ip-lo-addr {
                type inet:ip-address;
                description
                  "Service ip lo address";
              }
              leaf vc-id {
                type string;
                description
                "VC id";
              }
              description
                "List of PE/EG";
            }
            container pwe-encapsulation-type {
             leaf ethernet {
              type boolean;
              description
                "Ethernet";
             }
             leaf vlan {
              type boolean;
              description
                "VLAN";
             }
             description
              "Container of PWE Encapsulation Type configurations";
             }
            container pwe-mtu {
             leaf allow-mtu-mismatch {
              type boolean;
              description
                "Allow MTU mismatch";
             }
             description
              "Container of PWE MTU configurations";
             }
             container control-word {
              description
               "Container of control word configurations";
            }
            description
              "Container of T-LDP PWE configurations";
          }

          description
            "List of VPN Signaling Option.";
        }
        description
          "Grouping for signaling option";
      }

      grouping load-balance-grouping {
        leaf fat-pw {
          type boolean;
          description
            "Fat label is applied to Pseudowires across MPLS
             network";
        }
        leaf entropy-label {
          type boolean;
          description
            "Entropy label is applied to IP forwarding,
             L2VPN or L3VPN across MPLS network";
        }
        leaf vxlan-source-port {
          type string;
          description
            "Vxlan source port";
        }
       description
         "Grouping for load balance ";
     }

     grouping operational-requirements-ops {
       leaf actual-site-start {
         type yang:date-and-time;
         config false;
         description
           "Optional leaf indicating actual date
            and time when the service at a particular
            site actually started";
       }
       leaf actual-site-stop {
         type yang:date-and-time;
         config false;
         description
           "Optional leaf indicating actual date
            and time when the service at a particular
            site actually stopped";
       }
       description
         "This grouping defines some operational parameters
          parameters";
     }

     grouping intra-mkt-grouping {
       list intra-mkt {
         key "metro-mkt-id mkt-name";
         leaf metro-mkt-id {
           type uint32;
           description
             "Metro MKT ID";
         }
         leaf mkt-name {
           type string;
           description
             "MKT Name";
         }
         leaf site-id {
          type leafref{
         path "/l2vpn-svc/sites/site/site-id";
        }
          description
          "OVC identifier";
         }
         description
           "List of intra-MKT";
       }
       description
         "Grouping for intra-MKT";
     }

     grouping inter-mkt-service {
       leaf inter-mkt-service{
         type boolean;
         description
           "Indicate whether service is inter market service.";
       }
       description
         "Grouping for inter-MKT service";
     }

     grouping svc-type-grouping {
       container evc {
         leaf enabled {
         type boolean;
         description
        "Enabled EVC";
     }
      leaf evc-type {
       type identityref {
       base evc-type;
    }
     description
      "EVC type";
   }
       leaf number-of-pe {
           type uint32;
           config false;
           description
             "Number of PE";
         }
       leaf number-of-site {
           type uint32;
           config false;
           description
             "Number of Sites";
       }
       container uni-list {
           if-feature uni-list;
           list uni-list {
             key "uni-site-id";
             leaf uni-site-id {
               type string;
               description
                 "UNI site Identifier";
             }
       leaf off-net {
        type boolean;
        description
        "Off net enable";
       }
             description
               "List for UNIs";
           }
           description
             "Container for UNI List";
         }
         container ce-vlan-preservation {
          description
          "CE vlan preservation";
         }
   leaf ce-vlan-cos-perservation {
    type boolean;
    description
    "CE vlan COS preservation";
   }
   uses site-service;
         description
           "Container for Ethernet virtual connection.";
       }
       container ovc {
         if-feature ovc-type;
         list ovc-list {
           key ovc-id;
           leaf ovc-id {
             type svc-id;
             description
               "OVC ID type";
           }

           leaf off-net {
             type boolean;
             description
               "Off net";
           }
     leaf svlan-cos-preservation {
      type boolean;
      description
     "SVLAN CoS preservation";
     }
     leaf svlan-id-preservation {
      type boolean;
     description
    "SVLAN ID preservation";
     }
       leaf svlan-id-ethernet-tag {
            type string;
             description
             "SVLAN-ID/Ethernet Tag configurations";
           }
        leaf ovc-endpoint {
           type string;
           description
         "OVC Endpoint";
        }
           description
             "List for OVC";
         }
         description
           "Container for OVC";
       }
       description
         "Grouping of service types.";
     }

     grouping cfm-802-grouping {
       leaf MAID {
         type string;
         description
           "MA ID";
       }
       leaf mep-id {
         type uint32;
         description
           "Local MEP ID";
       }
       leaf mep-level {
         type uint32;
         description
           "MEP level";
       }
       leaf mep-up-down {
         type enumeration {
           enum up {
             description
               "MEP up";
           }
           enum down {
             description
               "MEP down";
           }
         }
         description
           "MEP up/down";
       }
       leaf remote-mep-id {
         type uint32;
         description
           "Remote MEP ID";
       }
       leaf cos-for-cfm-pdus {
         type uint32;
         description
           "COS for CFM PDUs";
       }
       leaf ccm-interval {
         type uint32;
         description
           "CCM interval";
       }
       leaf ccm-holdtime {
         type uint32;
         description
           "CCM hold time";
       }
       leaf alarm-priority-defect {
         type identityref {
           base fault-alarm-defect-type;
         }
         description
          "The lowest priority defect that is
           allowed to generate a Fault Alarm.
           The non-existence of this leaf means
           that no defects are to be reported";
       }
       leaf ccm-p-bits-pri {
         type ccm-priority-type;
         description
           "The priority parameter for CCMs transmitted by the MEP";
       }
       description
         "Grouping for 802.1ag CFM attribute";
     }

     grouping y-1731 {
       list y-1731 {
         key MAID;
         leaf MAID {
           type string;
           description
             "MA ID ";
         }
         leaf mep-id {
           type uint32;
           description
             "Local MEP ID";
         }
         leaf type {
           type identityref {
             base pm-type;
           }
           description
             "Performance monitor types";
         }
         leaf remote-mep-id {
           type uint32;
           description
             "Remote MEP ID";
         }
         leaf message-period {
           type uint32;
           description
             "Defines the interval between OAM messages. The message
              period is expressed in milliseconds";
         }
         leaf measurement-interval {
           type uint32;
           description
             "Specifies the measurement interval for statistics. The
              measurement interval is expressed in seconds";
         }
         leaf cos {
           type uint32;
           description
             "Class of service";
         }
         leaf loss-measurement {
           type boolean;
           description
             "Whether enable loss measurement";
         }
         leaf synthethic-loss-measurement {
           type boolean;
           description
             "Indicate whether enable synthetic loss measurement";
         }
         container delay-measurement {
           leaf enable-dm {
             type boolean;
             description
               "Whether to enable delay measurement";
           }
           leaf two-way {
             type boolean;
             description
               "Whether delay measurement is two-way (true) of one-
               way (false)";
           }
           description
             "Container for delay measurement";
         }
         leaf frame-size {
           type uint32;
           description
             "Frame size";
         }
         leaf session-type {
           type enumeration {
             enum proactive {
               description
                 "Proactive mode";
             }
             enum on-demand {
               description
                 "On demand mode";
             }
           }
           description
             "Session type";
         }
         description
           "List for y-1731.";
       }
       description
         "Grouping for y.1731";
     }

     grouping enni-site-info-grouping {
       container site-info {
         leaf site-name {
           type string;
           description
             "Site name";
         }
         leaf address {
           type inet:ip-address;
           description
             "Address";
         }
         leaf Edge-Gateway-Device-Info {
           type string;
           description
             "Edge Gateway Device Info ";
         }
         description
           "Container of site info configurations";
       }
       description
         "Grouping for site information";
     }

     grouping site-security {
       container security-filtering {
         uses mac-loop-prevention-grouping;
         container access-control-list {
           list mac {
             key "mac-address";
             leaf mac-address {
               type yang:mac-address;
               description
                 "MAC address";
             }
             description
               "List for MAC";
           }
           description
             "Container for access control";
         }
         uses mac-addr-limit-grouping;
         uses B-U-M-storm-control-grouping;
         description
           "Security parameters";
       }
       description
         "This grouping defines security parameters for a site";
     }

     grouping lacp-grouping {
       container LACP {
         leaf LACP-state {
           type boolean;
           description
             "LACP on/off";
         }
         leaf LACP-mode {
           type boolean;
           description
             "LACP mode";
         }
         leaf LACP-speed {
           type boolean;
           description
             "LACP speed";
         }
         leaf mini-link {
           type uint32;
           description
             "Mini link";
         }
         leaf system-priority {
           type uint16;
           description
             "Indicates the LACP priority for the system.
              The range is from 0 to 65535.
              The default is 32768.";
         }
         container Micro-BFD {
           if-feature Micro-BFD;
           leaf Micro-BFD-on-off {
             type enumeration {
               enum on {
                 description
                   "Micro-bfd on";
               }
               enum off {
                 description
                   "Micro-bfd off";
               }
             }
             description
               "Micro BFD ON/OFF";
           }
           leaf bfd-interval {
             type uint32;
             description
               "BFD interval";
           }
           leaf bfd-hold-timer {
             type uint32;
             description
               "BFD hold timer";
           }
           description
             "Container of Micro-BFD configurations";
         }
         container bfd {
           if-feature bfd;
           leaf bfd-enabled {
             type boolean;
             description
               "BFD activation";
           }
           choice holdtime {
             case profile {
               leaf profile-name {
                 type string;
                 description
                   "Service provider well known profile.";
               }
               description
                 "Service provider well known profile.";
             }
             case fixed {
               leaf fixed-value {
                 type uint32;
                 units msec;
                 description
                   "Expected hold time expressed in msec.";
               }
             }
             description
               "Choice for hold time flavor.";
           }
           description
             "Container for BFD.";
         }
         container Member-link-list {
           list member-link {
             key "name";
             leaf name {
               type string;
               description
                 "Member link name";
             }
             leaf port-speed {
               type uint32;
               description
                 "Port speed";
             }
             leaf mode {
               type neg-mode;
               description
                 "Negotiation mode";
             }
             leaf mtu {
               type uint32;
               description
                 "MTU";
             }
             container oam-802.3AH-link {
               if-feature oam-3ah;
               leaf enable {
                 type boolean;
                 description
                   "Indicate whether support oam 802.3 ah link";
               }
               description
                 "Container for oam 802.3 ah link.";
             }
             description
               "Member link";
           }
           description
             "Container of Member link list";
         }
         leaf flow-control {
           type string;
           description
             "Flow control";
         }

         leaf encapsulation-type {
           type enumeration {
             enum dot1q {
               description
                 "DOT1Q";
             }
             enum priority-tagged {
               description
                 "Priority-Tagged";
             }
            enum  untagged{
              description
                "untagged";
             }
           }
           description
             "Encapsulation type";
         }
         leaf ethertype {
           type enumeration{
              enum ipv4{
               description
               "ipv4";
              }
              enum ipv6{
               description
               "ipv6";
              }
              enum pppoe-all{
               description
               "pppoe-all";
              }
               enum pppoe-discovery{
               description
               "pppoe-discovery";
              }
              enum pppoe-session{
               description
               "pppoe-session";
              }

           }
           description
             "Ether type";
         }
         leaf lldp {
           type boolean;
            description
              "LLDP";
         }
         description
           "LACP";
       }
       description
         "Grouping for lacp";
     }

     grouping phy-interface-grouping {
       container phy-interface {
         leaf port-number {
           type uint32;
           description
             "Port number";
         }
         leaf port-speed {
           type uint32;
           description
             "Port speed";
         }
         leaf mode {
           type neg-mode;
           description
             "Negotiation mode";
         }

         leaf phy-mtu {
           type uint32;
           description
             "PHY MTU";
         }
         leaf flow-control {
           type string;
           description
             "Flow control";
         }
         leaf encapsulation-type {
           type enumeration {
             enum VLAN {
               description
                 "VLAN";
             }
             enum Ethernet {
               description
                 "Ethernet";
             }
           }
           description
             "Encapsulation-type";
         }
         leaf ethertype {
           type string;
           description
             "Ethertype";
         }
         leaf lldp {
           type boolean;
           description
             "LLDP";
         }
         container oam-802.3ah-link {
          if-feature oam-3ah;
          leaf enable {
            type boolean;
            description
              "Indicate whether support oam 802.3 ah link.
              IEEE 802.3ah Link EFM - Ethernet in the First Mile.
              802.3ah Link EFM support:
              1.Link performance monitoring
               Attributes and status information for Ethernet links
               Errored Symbol Period (errored symbols/second)
               Errored Frame (errored frames/second exceeds the threshold)
               Errored Frame Period (errored frames/N frames exceeds the threshold)
               Errored Frame Seconds Summary (errored seconds/M seconds exceeds
              the threshold)
              2.Remote fault detection and fault signaling
              Identifies how downed or compromised links and frame error events
             (CRC, Runt, IP Checksum...etc.) are detected and handled by conveying
              failure conditions to its peer
              3.Remote loopback testing
               Loopback control to test segments and links
              by sending test frames through";
          }
          description
            "Container for oam 802.3 ah link.";
         }
         leaf uni-loop-prevention {
           type boolean;
           description
             "If this leaf set to truth that the port automatically
              goes down when a physical loopback is detect.";
         }
         description
           "Container of PHY Interface Attributes configurations";
       }
       description
         "Grouping for phy interface.";
     }

     grouping lag-interface-grouping {
       container LAG-interface {
       if-feature LAG-interface;
         list LAG-interface {
           key "LAG-interface-number";
           leaf LAG-interface-number {
             type uint32;
             description
               "LAG interface number";
           }
           uses lacp-grouping;
           description
             "List of LAG interfaces";
         }
         description
           "Container of LAG interface attributes configuration";
       }
       description
         "Grouping for LAG interface";
     }
     grouping l2-access-grouping {
       container dot1q {
         when "'../l2-access-type'='dot1q'";
         leaf physical-inf {
           type string;
           description
             "Physical Interface";
         }
         leaf vlan-id {
           type uint32;
           description
             "VLAN identifier";
         }
         description
           "dot1q";
       }
       container qinq {
         when "'../l2-access-type'='qinq'";
         leaf s-vlan-id {
           type uint32;
           description
             "S-VLAN Identifier";
         }
         leaf c-vlan-id {
           type uint32;
           description
             "C-VLAN Identifier";
         }
         description
           "QinQ";
       }
       leaf sub-if-id {
         when "'../l2-access-type'='sub-interface'";
         type uint32;
         description
           "Sub interface ID";
       }
       container vxlan {
         when "'../l2-access-type'='vxlan'";
         leaf vni-id {
            type uint32;
            description
              "VNI Identifier";
         }
         list peer-list {
           key peer-ip;
           leaf peer-ip {
             type inet:ip-address;
             description
               "Peer IP";
           }
           description
             "List for peer IP";
         }
         description
           "QinQ";
       }
       description
         "Grouping for Layer2 access";
     }

     grouping ethernet-connection-grouping {
       container connection {
      container encapsulation-type {
      leaf encap-type {
       type identityref {
       base encapsulation-type;
     }
      description
      "Encapsulation Type";
     }
     leaf eth-type {
      type identityref {
      base eth-type;
     }
      description
     "Ethernet Type";
    }
      description
     "Container for encapsulation type";
    }

         leaf ESI {
          type string;
           description
           "Ethernet segment id";
         }
         leaf interface-description {
           type string;
           description
            "Interface description";
         }
         container vlan {
           leaf vlan-id {
             type uint32;
             description
               "VLAN-ID/Ethernet Tag configurations";
           }
           description
             "Abstract container for VLAN";
         }
         uses l2-access-grouping;
         uses phy-interface-grouping;
         uses lag-interface-grouping;
         description
           "Container for bearer";
       }
       description
         "Grouping for bearer.";
     }

     grouping svc-mtu-grouping {
       leaf svc-mtu {
         type uint32;
         description
           "EVC MTU";
       }
       description
         "Grouping for evc mtu";
     }

     grouping mac-addr-limit-grouping {
       container mac-addr-limit {
         leaf exceeding-option {
           type uint32;
           description
             "Exceeding option";
         }
         description
           "Container of MAC-Addr limit configurations";
       }
       description
         "Grouping for mac address limit";
     }
     grouping availability-grouping {
       container availability {
           choice redundancy-mode {
             case single-active {
               leaf single-active {
                 type boolean;
                 description
                   "Single active";
               }
               description
                 "Single active case";
             }
             case all-active {
               leaf all-active {
                 type boolean;
                 description
                   "All active";
               }
               description
                 "All active case";
             }
             description
               "Redundancy mode choice";
           }
         description
           "Container of availability optional configurations";
       }
       description
         "Grouping for availability";
     }

     grouping l2cp-grouping {
       container l2cp-control {
       if-feature L2CP-control;
         leaf stp-rstp-mstp {
           type control-mode;
           description
             "STP/RSTP/MSTP protocol type applicable to all UNIs";
         }
         leaf pause {
           type control-mode;
           description
             "Pause protocol type applicable to all UNIs";
         }
         leaf lacp-lamp {
           type control-mode;
           description
             "LACP/LAMP  ";
         }

         leaf link-oam {
           type control-mode;
           description
             "Link OAM";
         }
         leaf esmc {
           type control-mode;
           description
             "ESMC";
         }
         leaf l2cp-802.1x {
           type control-mode;
           description
             "802.x";
         }
         leaf e-lmi {
           type control-mode;
           description
             "E-LMI";
         }
         leaf lldp {
           type boolean;
           description
             "LLDP protocol type applicable to all UNIs";
         }
         leaf ptp-peer-delay {
           type control-mode;
           description
             "PTP peer delay";
         }
         leaf garp-mrp {
           type control-mode;
           description
             "GARP/MRP";
         }
         leaf provider-bridge-group {
           type control-mode;
           description
             "Provider bridge group reserved MAC address
              01-80-C2-00-00-08";
         }
         leaf provider-bridge-mvrp {
           type control-mode;
           description
             "Provider bridge MVRP reserved MAC address
              01-80-C2-00-00-0D";
         }
         description
           "Container of L2CP control configurations";
        }
        description
          "Grouping for l2cp control";
     }

     grouping B-U-M-storm-control-grouping {
       container b-u-m-storm-control {
          leaf bum-overall-rate {
            type uint32;
            description
              "overall rate for BUM";
           }
           list BUM-rate-per-type {
             key "type";
             leaf type {
               type identityref {
                 base BUM-type;
               }
               description
                 "BUM type";
             }
             leaf rate {
               type uint32;
               description
                 "rate for BUM";
           }
           description
             "List of rate per type";
         }
         description
           "Container of B-U-M-strom-control configurations";
       }
       description
         "Grouping for B-U-M-strom-control";
     }

     grouping mac-loop-prevention-grouping {
       container mac-loop-prevention {
         leaf frequency {
           type uint32;
           description
             "Frequency";
         }
         leaf protection-type {
           type identityref {
             base loop-prevention-type;
           }
           description
             "Protection type";
         }
         leaf number-retries {
           type uint32;
           description
             "Number of retries";
         }
         description
           "Container of MAC loop prevention.";
       }
       description
         "Grouping for MAC loop prevention";
     }

     grouping ethernet-svc-oam-grouping {
       container Ethernet-Service-OAM {
         leaf MD-name {
           type string;
           description
             "Maintenance domain name";
         }
         leaf MD-level {
           type uint8;
           description
             "Maintenance domain level";
         }

         container cfm-802.1-ag {
           list n2-uni-c {
             key "MAID";
             uses cfm-802-grouping;
             description
               "List of UNI-N to UNI-C";
           }
           list n2-uni-n {
             key "MAID";
             uses cfm-802-grouping;
             description
              "List of UNI-N to UNI-N";
           }
           description
             "Container of 802.1ag CFM configurations.";
         }
         uses y-1731;
         description
           "Container for Ethernet service OAM.";
       }
       description
         "Grouping for Ethernet service OAM.";
     }

     grouping fate-sharing-group {
       container groups {
         leaf fate-sharing-group-size {
           type uint16;
           description
             "Fate sharing group size.";
         }
         list group {
           key group-id;
           leaf group-id {
             type string;
             description
               "Group-id the site network access
                is belonging to";
           }
           description
             "List of group-id";
         }
         description
           "Groups the fate sharing group member
            is belonging to";
       }
       description
         "Grouping for Fate sharing group.";
     }
     grouping site-group {
       container groups {
         list group {
           key group-id;
           leaf group-id {
             type string;
             description
               "Group-id the site is belonging to";
           }
           description
             "List of group-id";
         }
         description
           "Groups the site or site-network-access
            is belonging to.";
       }
       description
         "Grouping definition to assign
          group-ids to site or site-network-access";
     }

     grouping access-diversity {
       container access-diversity {
         if-feature site-diversity;
         uses fate-sharing-group;
         container constraints {
           list constraint {
             key constraint-type;
             leaf constraint-type {
               type identityref {
                 base placement-diversity;
               }
               description
                 "Diversity constraint type.";
             }
             container target {
               choice target-flavor {
                 case id {
                   list group {
                     key group-id;
                     leaf group-id {
                       type string;
                       description
                         "The constraint will apply
                          against this particular
                          group-id";
                     }
                     description
                       "List of groups";
                   }
                 }
                 case all-accesses {
                   leaf all-other-accesses {
                     type empty;
                     description
                       "The constraint will apply
                        against all other site network
                        access of this site";
                   }
                 }
                 case all-groups {
                   leaf all-other-groups {
                     type empty;
                     description
                       "The constraint will apply
                        against all other groups the
                        customer is managing";
                   }
                 }
                 description
                   "Choice for the group definition";
               }
               description
                 "The constraint will apply against
                  this list of groups";
             }
             description
               "List of constraints";
           }
           description
             "Constraints for placing this site
               network access";
         }
         description
           "Diversity parameters.";
       }
       description
         "This grouping defines access diversity
          parameters";
     }

     grouping request-type-profile-grouping {
       container request-type-profile {
         choice request-type-choice {
           case dot1q-case {
             container dot1q {
               leaf physical-if {
                 type string;
                 description
                   "Physical interface";
               }
               leaf vlan-id {
                 type uint16;
                 description
                   "VLAN ID";
               }
               description
                 "Container for dot1q.";
             }
             description
               "Case for dot1q";
           }
           case physical-case {
             leaf physical-if {
                type string;
                description
                  "Physical interface";
             }
             leaf circuit-id {
               type string;
               description
                 "Circuit ID";
             }
             description
               "Physical case";
           }
           description
             "Choice for request type";
         }
         description
           "Container for request type profile.";
       }
       description
         "Grouping for request type profile";
     }

     grouping site-attachment-bearer {
       container bearer {
         container requested-type {
           if-feature requested-type;
           leaf requested-type {
             type string;
             description
               "Type of requested bearer Ethernet, DSL,
                Wireless ... Operator specific.";
           }
           leaf strict {
             type boolean;
             default false;
             description
               "Define if the requested-type is a preference
                or a strict requirement.";
           }
           uses request-type-profile-grouping;
           description
             "Container for requested type.";
         }
         leaf always-on {
           if-feature always-on;
           type boolean;
           default true;
           description
             "Request for an always on access type.
              This means no Dial access type for
              example.";
         }
         leaf bearer-reference {
           if-feature bearer-reference;
           type string;
           description
             "This is an internal reference for the
              service provider.";
         }
         description
           "Bearer specific parameters.
            To be augmented.";
       }
       description
         "Grouping to define physical properties of
          a site attachment.";
     }

     grouping vpn-attachment-grouping {
       container vpn-attachment {
         leaf device-id {
           type string;
           description
             "Device ID";
         }
         container management {
           leaf address-family {
             type identityref {
               base address-family;
             }
             description
               "Address family used for management.";
           }
           leaf address {
             type inet:ip-address;
             description
               "Management address";
           }
           description
             "Management configuration..";
         }
         choice attachment-flavor {
           case vpn-id {
             leaf vpn-id {
               type leafref {
                 path "/l2vpn-svc/vpn-services"+
                      "/vpn-svc/vpn-id";
               }
               description
                 "Reference to a VPN.";
             }
             leaf site-role {
               type identityref {
                 base site-role;
               }
               default any-to-any-role;
               description
                 "Role of the site in the IPVPN.";
             }
           }
         case vpn-policy-id {
         leaf vpn-policy-id {
          type leafref {
         path "/l2vpn-svc/sites/site/vpn-policies/vpn-policy/vpn-policy-id";
        }
       description
      "Reference to a vpn policy";
       }
     }
           mandatory true;
           description
             "Choice for VPN attachment flavor.";
         }
         description
           "Defines VPN attachment of a site.";
       }
       description
         "Grouping for access attachment";
     }

     grouping site-service-basic {
       container svc-input-bandwidth {
         if-feature input-bw;
         list input-bandwidth {
           key "type";
           leaf type {
             type identityref {
               base bw-type;
             }
             description
               "Bandwidth Type";
           }
         leaf cos-id {
           type uint8;
           description
          "CoS id";
          }
           leaf evc-id {
             type svc-id;
             description
               "EVC ID";
           }
           leaf CIR {
             type uint64;
             description
               "Committed Information Rate in bits/second.";
           }
           leaf CBS {
             type uint64;
             description
               "Size of burst window for allowed CIR (CBS) in Bytes.";
           }
           leaf EIR {
             type uint64;
             description
               "Excess Information Rate in bits/second.";
           }
           leaf EBS {
             type uint64;
             description
               "Size of burst window for allowed EIR (EBS) in Bytes.";
           }
           leaf CM {
             type uint8;
             description
               "Color Mode";
           }
           description
             "List for input bandwidth";
         }
         description
           "From the PE perspective, the service input
            bandwidth of the connection.";
       }
       container svc-output-bandwidth {
         if-feature output-bw;
         list output-bandwidth {
           key "type";
           leaf type {
             type identityref {
               base bw-type;
             }
             description
               "Bandwidth Type";
           }
            leaf cos-id {
            type uint8;
            description
            "CoS id";
           }
           leaf evc-id {
             type svc-id;
             description
               "EVC ID";
           }
           leaf CIR {
             type uint64;
             description
               "Committed Information Rate in bits/second";
           }
           leaf CBS {
             type uint64;
             description
               "Size of burst window for allowed CIR (CBS) in Bytes";
           }
           leaf EIR {
             type uint64;
             description
               "Excess Information Rate in bits/second";
           }
           leaf EBS {
             type uint64;
             description
               "Size of burst window for allowed EIR (EBS) in Byte";
           }
           leaf CM {
             type uint8;
             description
               "Color Mode";
           }
           description
             "List for output bandwidth";

         }
         description
           "From the PE perspective, the service output
            bandwidth of the connection.";
       }
       description
         "Grouping for site service";
     }

     grouping flow-definition {
       container match-flow {
         leaf dscp {
           type inet:dscp;
           description
             "DSCP value.";
         }
         leaf dot1p {
           type uint8 {
             range "0 .. 7";
           }
           description
             "802.1p matching.";
         }
         leaf pcp {
           type uint8;
           description
             "PCP value";
         }
         leaf src-mac {
          type yang:mac-address;
          description
            "Source MAC";
         }
         leaf dst-mac {
          type yang:mac-address;
          description
            "Destination MAC";
         }
         container cos-color-id {
           leaf device-id {
             type string;
             description
               "Device ID";
           }
           leaf cos-label {
             type identityref {
               base cos-id;
             }
             description
               "COS label";
           }
           leaf pcp {
             type uint8;
             description
               "PCP value";
           }
           leaf dscp {
             type inet:dscp;
             description
               "DSCP value.";
           }
           description
             "Container for cos color id";
         }
         leaf color-type {
           type identityref {
             base color-type;
           }
           description
             "Color Types";
         }
         leaf-list target-sites {
           type svc-id;
           description
             "Identify a site as traffic destination.";
         }
         description
           "Describe flow matching criterions.";
        }
        description
          "Flow definition based on criteria.";
       }

       grouping site-service-qos-profile {
         container qos {
           if-feature qos;
           container qos-classification-policy {
             list rule {
               key id;
               ordered-by user;
               leaf id {
                 type uint16;
                 description
                   "ID of the rule.";
               }
               choice match-type {
                 case match-flow {
                   uses flow-definition;
                 }
                 case match-phy-port {
                   leaf match-phy-port {
                     type uint16;
                     description
                       "Defines the physical port
                        to match.";
                   }
                 }
                 description
                   "Choice for classification";
               }
               leaf target-class-id {
                 type string;
                 description
                   "Identification of the class of service.
                    This identifier is internal to the
                    administration.";
             }
             description
               "List of marking rules.";
           }
           description
             "Need to express marking rules ...";
         }
         container qos-profile {
           choice qos-profile {
             description
               "Choice for QoS profile.
                Can be standard profile or custom.";
             case standard {
               leaf ingress-profile {
                 type string;
                 description
                   "Ingress QoS Profile to be used";
               }
               leaf egress-profile {
                 type string;
                 description
                   "Egress QoS Profile to be used";
               }
             }
             case custom {
               container classes {
                 if-feature qos-custom;
                   list class {
                     key class-id;
                     leaf class-id {
                       type string;
                       description
                         "Identification of the class of
                         service. This identifier is internal
                         to the administration.";
                     }
                     leaf direction {
                       type direction-type;
                       description
                         "Direction type";
                     }
                     leaf policing {
                       type identityref {
                         base policing;
                       }
                       description
                         "The policing can be either one-rate,
                          two-color (1R2C) or two-rate, three-color
                          (2R3C)";
                     }
                     leaf byte-offset {
                       type uint16;
                       description
                         "For not including extra VLAN tags in the QoS
                          calculation";
                     }

                     leaf rate-limit {
                       type uint8;
                       units percent;
                       description
                         "To be used if class must be rate limited.
                          Expressed as percentage of the svc-bw.";
                     }
                     leaf discard-percentage {
                       type uint8;

                       default 100;
                       description
                         "The value of the discard-percentage,
                          Expressed as pecentage of the svc-bw ";
                     }
                     container frame-delay {
                       choice flavor {
                         case lowest {
                           leaf use-low-del {
                             type empty;
                             description
                               "The traffic class should use
                                the lowest delay path";
                           }
                         }
                         case boundary {
                           leaf delay-bound {
                             type uint16;
                             units msec;
                             description
                               "The traffic class should use
                                a path with a defined maximum
                                delay. The maximum delay is
                               maximum time taken for service
                              frames across the network.
                              It is Measured from the arrival
                             of the first bit at the ingress
                             of the network to output of last
                             bit at the egress of the network.";
                           }
                         }
                         description
                           "Delay constraint on the traffic
                            class";
                       }
                       description
                         "Delay constraint on the traffic
                          class";
                     }
                     container frame-jitter {
                       choice flavor {
                         case lowest {
                           leaf use-low-jit {
                             type empty;
                             description
                               "The traffic class should use
                                the lowest jitter path";
                           }
                         }
                         case boundary {
                           leaf delay-bound {
                             type uint32;
                             units usec;
                             description
                               "The traffic class should use
                                a path with a defined maximum
                                jitter. The frame jitter is
                               the variation in Frame Delay
                               for a number of frames";
                           }
                         }
                         description
                           "Jitter constraint on the traffic
                            class";
                       }
                       description
                         "Jitter constraint on the traffic
                          class";
                     }
                     container frame-loss {
                       leaf fr-loss-rate {
                         type decimal64 {
                           fraction-digits 2;
                         }
                         description
                           "Loss constraint on the traffic class.
                            Measured from the number of lost service
                           frames and the number of sent service frame.
                           Frame Loss Ratio = frames lost number/ number of frames sent";
                       }
                       description
                         "Container for frame loss";
                     }

                     container bandwidth {
                      leaf guaranteed-bw-percent {
                       type uint8;
                        units percent;
                      description
                      "To be used to define the guaranteed bandwidth
                      as a percentage of the available service bandwidth.";
                      }
                      leaf end-to-end {
                       type empty;
                       description
                       "Used if the bandwidth reservation
                        must be done on the MPLS network too.";
                      }
                      description
                     "Bandwidth constraint on the traffic class.";
                   }

                     description
                       "List of class of services.";
                   }
                   description
                     "Container for list of class of services.";
                 }
               }
             }
             description
               "Qos profile configuration.";
           }
           description
             "QoS configuration.";
         }
         description
           "This grouping defines QoS parameters
            for a site";
       }

          grouping services-grouping {
           container service {
            uses site-service-qos-profile;
            description
           "Container for service";
          }
            description
         "Grouping for Services";
         }

       grouping service-grouping { //biaoshi
         container service {
           uses site-service-basic;
           leaf svlan-id-ethernet-tag {
            type string;
             description
             "SVLAN-ID/Ethernet Tag configurations";
           }
           uses site-service;
           leaf service-multiplexing {
             type boolean;
             description
               "Service multiplexing";
           }
           uses site-service-qos-profile;
           description
             "Container for service";
         }
         description
           "Grouping for service.";
       }

     /* MAIN L2VPN SERVICE */

     container l2vpn-svc {

        container vpn-services {
          list vpn-svc {
            key "vpn-id";
            leaf vpn-id {
              type svc-id;
              description
                "Defining a service id.";
            }
            leaf vpn-type {
              type identityref {
                base service-type;
              }
              description
                "Service type";
            }
            leaf customer-account-number {
             type uint32;
             description
              "Customer account number";
             }
            leaf customer-name {
             type string;
             description
              "Customer name";
             }
            uses svc-type-grouping;
            leaf svc-topo {
              type identityref {
                base vpn-topology;
              }
              description
                "Defining service topology, such as
                 any-to-any,hub-spoke, etc.";
            }
            uses vpn-service-cloud-access; // need fixed??

            container metro-network-id {
              uses inter-mkt-service;
              uses intra-mkt-grouping;
              description
                "Container of Metro-Network ID configurations";
            }
            container global-l2cp-control {
              if-feature L2CP-control;
               leaf stp-rstp-mstp {
                type control-mode;
                description
                  "STP/RSTP/MSTP protocol type applicable to all UNIs";
              }
              leaf pause {
                type control-mode;
                description
                  "Pause protocol type applicable to all UNIs ";
              }
              leaf lldp {
                type boolean;
                description
                  "LLDP protocol type applicable to all UNIs ";
              }
              description
                "Container of L2CP control global configurations";
            }
            container load-balance-options {
              uses load-balance-grouping;
              description
                "Container for load balance options";
            }
            leaf service-level-mac-limit {
              type string;
              description
              "Service-level MAC-limit (E-LAN only)";
            }
            uses service-protection;

            description
              "List of vpn-svc";
          }
          description
            "Container for VPN services.";
        }

       /* SITE */

        container sites {
          list site {
            key "site-id site-type";
            leaf site-id {
              type string;
              description
                "Site id";
            }
            leaf site-type {
              type identityref {
                base site-type;
              }
              description
                "Site type";
            }
            uses site-device;
            uses site-management;
            uses customer-location-info;
            uses site-diversity;
            uses site-vpn-policy ;
            container signaling-option {
              if-feature signaling-option;
              uses signaling-option-grouping;
              description
                "Container for signaling option";
            }
            container load-balance-options {
              uses load-balance-grouping;
              description
                "Container for load balance options";
            }
            uses services-grouping;
            uses site-security;
            uses operational-requirements-ops;
            container site-network-accesses {
              list site-network-access {
                key "network-access-id";
                leaf network-access-id {
                  type string;
                  description
                    "Identifier of network access";
                }
               leaf site-network-access-type {
                type identityref {
                base site-network-access-type;
                }
                default "point-to-point";
                description
               "Describes the type of connection, e.g.,
               point-to-point or multipoint.";
                }

                leaf remote-carrier-name {
                  when "'../site-type' = 'enni'" {
                    description
                      "Site type = enni";
                  }
                  type string;
                  description
                    "Remote carrier name";
                }
                uses access-diversity;
                uses site-attachment-bearer;
                uses ethernet-connection-grouping;
                uses l2cp-grouping;
                uses svc-mtu-grouping;
                uses availability-grouping;
                uses vpn-attachment-grouping;
                uses service-grouping;
                uses ethernet-svc-oam-grouping;
                uses site-security;
                description
                  "List of ports";
              }
              description
                "Container of port configurations";
            }
            description
              "List of sites";
          }
          description
            "Container of site configurations";
        }

        description
          "Container for L2VPN service";
     }
   }
