module ietf-ipfix-psamp {
  namespace "urn:ietf:params:xml:ns:yang:ietf-ipfix-psamp";
  prefix ipfix;

  import ietf-yang-types { prefix yang; }
  import ietf-inet-types { prefix inet; }

  organization
    "IETF IPFIX Working Group";

  contact
    "WG Web:   <http://tools.ietf.org/wg/ipfix/>
    WG List:  <mailto:ipfix@ietf.org>

    WG Chair: Nevil Brownlee
              <n.brownlee@auckland.ac.nz>

    WG Chair: Juergen Quittek
              <quittek@neclab.eu>

    Editor:   Gerhard Muenz
              <mailto:muenz@net.in.tum.de>";
  description
    "IPFIX/PSAMP Configuration Data Model

    Copyright (c) 2010 IETF Trust and the persons identified as
    the document authors.  All rights reserved.
    Redistribution and use in source and binary forms, with or
    without modification, is permitted pursuant to, and subject
    to the license terms contained in, the Simplified BSD License
    set forth in Section 4.c of the IETF Trust's Legal Provisions
    Relating to IETF Documents
    (http://trustee.ietf.org/license-info).";

  revision 2010-08-02 {
    description "Version of draft-ietf-ipfix-configuration-model-07
      Changes in draft-ietf-ipfix-configuration-model-07:
      - UdpCollector parameter templateLifetime replaced by
        templateLifeTime, optionsTemplateLifeTime,
        templateLifePacket, optionsTemplateLifePacket
      - Transport Session state parameters templateRefreshTimeout,
        optionsTemplateRefreshTimeout, templateRefreshPacket, and
        optionsRefreshPacket remove as they appear as configuration
        parameters
      - Transport Session state parameter 'packets' removed as it
        does not make sense.
      Changes in draft-ietf-ipfix-configuration-model-06:
      - new features cacheModeImmediate, cacheModeTimeout,
        cacheModeNatural, cacheModePermanent
      - parameter exportingProcess/destination/exportMemberType
        replaced by new parameter exportingProcess/exportMode
      - new destination subclasses sctpExporter, tcpExporter,
        udpExporter, and fileWriter
      - Template's bitvector state parameter flags replaced by
        isFlowKey and isScope parameters
      - interface and linecard containers removed from
        observationPoint
      - Cache parameter maxRecords renamed maxFlows
      - fileWriter and fileReader have separate statistics
        (do not use Transport Session statistics)
      - new Transport Session state parameter
        transportSessionStartTime
      - parameter inactiveFlows renamed unusedCacheEntries
        (as in IPFIX MIB)
      - a Selection Process may receive packets from multiple
        Observation Points but may only refer to a single Cache
      - selectorId state parameter removed
      - selectionSequenceId reported together with
        observationDomainId
      - nameType type definition for name parameters (keys)
      - renaming: *IpAddress => *IPAddress
      - renaming: *Receiver => *Collector
      - parameters numberOfStreams and maxAllowedStreams
        removed
      Changes in draft-ietf-ipfix-configuration-model-05:
      - new Cache Mode 'natural'
      - new parameter exportInterval for permanent Cache
      - new optionType 'extendedTypeInformation'
      - ieId value range restricted to 1..32767
      - parameter isFlowKey not available for Reverse Information
        Elements and Cache Mode 'immediate'
      - sourceIpAddress parameter used for all transport protocols,
        replaces localIpAddress parameter for SCTP
      - destinationIpAddress parameter may appear multiple times
        in the case of SCTP
      - new parameters ifIndex or ifName for export destinations
      - description of timedReliability parameter updated
      - new parameter maxPacketSize for UDP export
      - must statement of selectionProcess updated
      - must statement of Cache removed
      Changes in draft-ietf-ipfix-configuration-model-04:
      - descriptions and references added in various places,
        especially for state parameters
      - enum types cacheMode, exportMemberType, optionsType replaced
        by identities in order to facilitate the addition of new
        values using YANG deviations
      - Selector parameters revised:
        - parameter names now correspond to Information Element
          names
        - single matching value instead of range in filterMatch
          (which is consistent with Selector Report Interpretation)
        - filterHash parameters adapted to PSAMP RFCs
        - sampNonUniProb, sampFlowState, filterRState removed
          (a Selector Report Interpretation does not exist, yet)
      - some must statements replaced by choices, which is easier
        to read
      - orderedDelivery parameter removed, better add a parameter
        for activating per-sctp stream later
      - YANG data type timeticks replaced by uint32 and unit
        milliseconds
      - configuration of fields included in an Options Template
        removed because there is no real use-case
      - observationPointId, selectionSequenceId, and selectorId are
        now state parameters (i.e., not configurable any more)
        because there is no real use-case to configure them
      - meaning of configuration parameters activeTimeout and
        inactiveTimeout clarified
      - several additional must statements enforcing certain
        configuration restrictions
      Changes in draft-ietf-ipfix-configuration-model-03:
      - list of used or received templates now inside transport
        session container because templates are defined per transport
        session
      - transport session: removed 'index', added missing 'protocol'
      - exportingProcessId removed
      - Transport Session state data can be used for File Readers
        and File Writers
      - module name changed
      - Renaming: cacheType => cacheMode,
        Options' type => optionsType,
        Destination's/FileWriter's type => exportMemberType,
        uri => file, optionTemplate => optionsTemplate,
        optionField => optionsField
      - transport layer security parameters added to Destination
        class and Receiver class
      - must statements ensure that Selection Processes and Caches
        process packets of a single Observation Domain (as long as
        Selection Processes are not cascaded)
      - replaced default value of port by description because the
        value differs in the case of DTLS/TLS
      Changes in draft-ietf-ipfix-configuration-model-02:
      - conformance to draft-ietf-netmod-yang-03 and
        draft-ietf-netmod-yang-types-01
      - canonical form
      - observationDomainId is now mandatory parameter
      - usage of YANG features
      - renamed parameter 'idleTimeout' in 'inactiveTimeout'
      - state data: Selector statistics, Cache statistics, Templates,
        Transport Sessions
      - Exporting Process: new structure of destination, fileWriter
      - Collecting Process: new structure of receiver, fileReader
      - more groupings and typedefs
      - options configured per Exporting Process, not per
        destination
      - verified optional parameters, added default values or
        description clause if necessary
      Changes in draft-ietf-ipfix-configuration-model-01:
      - separation of Selectors and Selection Processes as in PSAMP
        documents
      - parameter modifications in filterMatch
      - new rateLimit parameter in destinations of Exporting Process
      - Cache Type 'normal' now called 'timeout'
      Changes in draft-ietf-ipfix-configuration-model-00:
      - Metering Process container replaced by direct reference to
        Selection Process
      - meteringProcessId parameter disappears together with the
        Metering Process container
      - concatenation of Selection Processes realize Selection
        Sequence
      - removal of premature support of
        IPFIX Mediators/Concentrators.
      - more SCTP parameters in SctpReceiver and SctpExport classes
      - sendBufferSize parameter for all *Export classes
      - templateId no longer configuration parameter
      Changes in draft-muenz-ipfix-configuration-04:
      - first version in yang
      - Collecting Process can be configured for file import
      - Collecting Process can be configured to export received
        records without modifications (e.g., to file or other
        collectors)
      - SCTP export parameter timedReliability
      - parameter for eligible local IP addresses for SCTP endpoint
      - all tags names uncapitalized, types names etc. capitalized
      - CacheParameters renamed as Cache
      - description attribute removed
      Changes in -03:
      - Linecard and Interface classes now have direction element
      - sec => s (SI unit)
      - optional description attribute for annotations
      - simplifications in ExportingProcess class
      - new parameters: observationPointId, meteringProcessId,
        selectorId, exportingProcessId (note that devices do not
        have to support the configuration of these parameters)
      - new FileExport class for exporting into a file
      - Reporting class renamed Options Class
      Changes in -02:
      - new structure without next pointers
      - packet reporting and flow metering replaced by record cache
      - added reporting with options";

    reference "RFC XXXX: IPFIX/PSAMP Configuration Data Model";
  }

  /*****************************************************************
  * Features
  *****************************************************************/

  feature exporter {
    description "If supported, the Monitoring Device can be used as
      an Exporter. Exporting Processes can be configured.";
  }

  feature collector {
    description "If supported, the Monitoring Device can be used as
      a Collector. Collecting Processes can be configured.";
  }

  feature meter {
    description "If supported, Observation Points, Selection
      Processes, and Caches can be configured.";
  }

  feature psampSampCountBased {
    description "If supported, the Monitoring Device supports
      count-based Sampling. The Selector method sampCountBased can
      be configured.";
  }

  feature psampSampTimeBased {
    description "If supported, the Monitoring Device supports
      time-based Sampling. The Selector method sampTimeBased can
      be configured.";
  }

  feature psampSampRandOutOfN {
    description "If supported, the Monitoring Device supports
      random n-out-of-N Sampling. The Selector method
      sampRandOutOfN can be configured.";
  }

  feature psampSampUniProb {
    description "If supported, the Monitoring Device supports
      uniform probabilistic Sampling. The Selector method
      sampUniProb can be configured.";
  }

  feature psampFilterMatch {
    description "If supported, the Monitoring Device supports
      property match Filtering. The Selector method filterMatch
      can be configured.";
  }

  feature psampFilterHash {
    description "If supported, the Monitoring Device supports
      hash-based Filtering. The Selector method filterHash can be
      configured.";
  }

  feature cacheModeImmediate {
    description "If supported, the Monitoring Device supports
      Cache Mode 'immediate'.";
  }
  feature cacheModeTimeout {
    description "If supported, the Monitoring Device supports
      Cache Mode 'timeout'.";
  }

  feature cacheModeNatural {
    description "If supported, the Monitoring Device supports
      Cache Mode 'natural'.";
  }

  feature cacheModePermanent {
    description "If supported, the Monitoring Device supports
      Cache Mode 'permanent'.";
  }

  feature udpTransport {
    description "If supported, the Monitoring Device supports UDP
      as transport protocol.";
  }

  feature tcpTransport {
    description "If supported, the Monitoring Device supports TCP
      as transport protocol.";
  }

  feature fileReader {
    description "If supported, the Monitoring Device supports the
      configuration of Collecting Processes as File Readers.";
  }

  feature fileWriter {
    description "If supported, the Monitoring Device supports the
      configuration of Exporting Processes as File Writers.";
  }

  /*****************************************************************
  * Identities
  *****************************************************************/

  /*** Hash function identities ***/
  identity hashFunction {
    description "Base identity for all hash functions used for
      hash-based packet filtering. Identities derived from
      this base are used by the leaf
      /ipfix/selectionProcess/selector/filterHash/hashFunction.";
  }
  identity BOB {
    base "hashFunction";
    description "BOB hash function";
    reference "RFC5475, Section 6.2.4.1.";
  }
  identity IPSX {
    base "hashFunction";
    description "IPSX hash function";
    reference "RFC5475, Section 6.2.4.1.";
  }
  identity CRC {
    base "hashFunction";
    description "CRC hash function";
    reference "RFC5475, Section 6.2.4.1.";
  }

  /*** Cache mode identities ***/
  identity cacheMode {
    description "Base identity for all Cache Modes specifying
      Flow expiration policies of a Cache. Identities derived from
      this base are used by the leaf /ipfix/cache/cacheMode.";
  }
  identity immediate {
    base "cacheMode";
    description "Flow expiration after the first packet;
      generation of Packet Records.
      This identity MUST NOT be referred to unless the feature
      cacheModeImmediate is supported by the Monitoring Device.";
  }
  identity timeout {
    base "cacheMode";
    description "Flow expiration after active and inactive timeout;
      generation of Flow Records.
      This identity MUST NOT be referred to unless the feature
      cacheModeTimeout is supported by the Monitoring Device.";
  }
  identity natural {
    base "cacheMode";
    description "Flow expiration after active and inactive timeout,
      or on natural termination (e.g. TCP FIN, or TCP RST) of the
      Flow; generation of Flow Records.
      This identity MUST NOT be referred to unless the feature
      cacheModeNatural is supported by the Monitoring Device.";
  }
  identity permanent {
    base "cacheMode";
    description "No flow expiration, periodical export with
      time interval exportInterval; generation of Flow Records.
      This identity MUST NOT be referred to unless the feature
      cacheModePermanent is supported by the Monitoring Device.";
  }

  /*** Export mode identities ***/
  identity exportMode {
    description "Base identity for different usages of export
      destinations configured for an Exporting Process.
      Identities derived from this base are used by the leaf
      /ipfix/exportingProcess/exportMode.";
  }
  identity parallel {
    base "exportMode";
    description "Parallel export of Data Records to all
      destinations configured for the Exporting Process.";
  }
  identity loadBalancing {
    base "exportMode";
    description "Load-balancing between the different destinations
      configured for the Exporting Process.";
  }
  identity fallback {
    base "exportMode";
    description "Export to the primary destination (i.e., the first
      SCTP, UDP, TCP, or file destination configured for the
      Exporting Process). If the export to the primary destination
      fails, the Exporting Process tries to export to the secondary
      destination. If the secondary destination fails as well, it
      continues with the tertiary, etc.";
  }

  /*** Options type identities ***/
  identity optionsType {
    description "Base identity for report types exported with
      options. Identities derived from this base are used by the leaf
      /ipfix/exportingProcess/options/optionsType.";
  }
  identity meteringStatistics {
    base "optionsType";
    description "Metering Process Statistics.";
    reference "RFC 5101, Section 4.1.";
  }
  identity meteringReliability {
    base "optionsType";
    description "Metering Process Reliability Statistics.";
    reference "RFC 5101, Section 4.2.";
  }
  identity exportingReliability {
    base "optionsType";
    description "Exporting Process Reliability
      Statistics.";
    reference "RFC 5101, Section 4.3.";
  }
  identity flowKeys {
    base "optionsType";
    description "Flow Keys.";
    reference "RFC 5101, Section 4.4.";
  }
  identity selectionSequence {
    base "optionsType";
    description "Selection Sequence and Selector Reports.";
    reference "RFC5476, Sections 6.5.1 and 6.5.2.";
  }
  identity selectionStatistics {
    base "optionsType";
    description "Selection Sequence Statistics Report.";
    reference "RFC5476, Sections 6.5.3.";
  }
  identity accuracy {
    base "optionsType";
    description "Accuracy Report.";
    reference "RFC5476, Section 6.5.4.";
  }
  identity reducingRedundancy {
    base "optionsType";
    description "Enables the utilization of Options Templates to
      reduce redundancy in the exported Data Records.";
    reference "RFC5473.";
  }
  identity extendedTypeInformation {
    base "optionsType";
    description "Export of extended type information for
      enterprise-specific Information Elements used in the
      exported Templates.";
    reference "RFC5610.";
  }

  /*****************************************************************
  * Type definitions
  *****************************************************************/

  typedef nameType {
    type string {
      length "1..max";
      pattern "\S(.*\S)?";
    }
    description "Type for 'name' leafs which are used to identify
      specific instances within lists etc.
      Leading and trailing whitespaces are not allowed.";
  }

  typedef direction {
    type enumeration {
      enum ingress {
        description "This value is used for monitoring incoming
          packets.";
      }
      enum egress {
        description "This value is used for monitoring outgoing
          packets.";
      }
      enum both {
        description "This value is used for monitoring incoming and
          outgoing packets.";
      }
    }
    description "Direction of packets going through an interface or
      linecard.";
  }

  typedef transportSessionStatus {
    type enumeration {
      enum inactive {
        description "This value MUST be used for Transport Sessions
          that are specified in the system but currently not active.
          The value can be used for Transport Sessions that are
          backup (secondary) sessions.";
      }
      enum active {
        description "This value MUST be used for Transport Sessions
          that are currently active and transmitting or receiving
          data.";
      }
      enum unknown {
        description "This value MUST be used if the status of the
          Transport Sessions cannot be detected by the device. This
          value should be avoided as far as possible.";
      }
    }
    description "Status of a Transport Session.";
    reference "RFC5815, Section 8 (ipfixTransportSessionStatus).";
  }

  /*****************************************************************
  * Groupings
  *****************************************************************/
  grouping observationPointParameters {
    description "Interface as input to Observation Point.";
    leaf observationPointId {
      type uint32;
      config false;
      description "Observation Point ID (i.e., the value of the
        Information Element observationPointId) assigned by the
        Monitoring Device.";
      reference "RFC5102, Section 5.1.10.";
    }
    leaf observationDomainId {
      type uint32;
      mandatory true;
      description "The Observation Domain ID associates the
        Observation Point to an Observation Domain. Observation
        Points with identical Observation Domain ID belong to the
        same Observation Domain.";
      reference "RFC5101.";
    }
    choice OPLocation {
      mandatory true;
      description "Location of the Observation Point.";
      leaf ifIndex {
        type uint32;
        description "Index of an interface as stored in the ifTable
          of IF-MIB.";
        reference "RFC 1229.";
      }
      leaf ifName {
        type string;
        description "Name of an interface as stored in the ifTable
          of IF-MIB.";
        reference "RFC 1229.";
      }
      leaf entPhysicalIndex {
        type uint32;
        description "Index of a linecard as stored in the
          entPhysicalTable of ENTITY-MIB.";
        reference "RFC 4133.";
      }
      leaf entPhysicalName {
        type string;
        description "Name of a linecard as stored in the
          entPhysicalTable of ENTITY-MIB.";
        reference "RFC 4133.";
      }
    }
    leaf direction {
      type direction;
      default both;
      description "Direction of packets. If not applicable (e.g., in
        the case of a sniffing interface in promiscuous mode), this
        parameter is ignored.";
    }
  }

  grouping selectorParameters {
    description "Configuration and state parameters of a Selector.";
    choice Method {
      mandatory true;
      description "Packet selection method applied by the Selector.";
      leaf selectAll {
        type empty;
        description "Method which selects all packets.";
      }
      container sampCountBased {
        if-feature psampSampCountBased;
        description "This container contains the configuration
          parameters of a Selector applying systematic count-based
          packet sampling to the packet stream.";
        reference "RFC5475, Section 5.1;
          RFC5476, Section 6.5.2.1.";
        leaf packetInterval {
          type uint32;
          units packets;
          mandatory true;
          description "The number of packets that are consecutively
            sampled between gaps of length packetSpace.
            This parameter corresponds to the Information Element
            samplingPacketInterval.";
          reference "RFC5477, Section 8.2.2.";
        }
        leaf packetSpace {
          type uint32;
          units packets;
          mandatory true;
          description "The number of unsampled packets between two
            sampling intervals.
            This parameter corresponds to the Information Element
            samplingPacketSpace.";
          reference "RFC5477, Section 8.2.3.";
        }
      }
      container sampTimeBased {
        if-feature psampSampTimeBased;
        description "This container contains the configuration
          parameters of a Selector applying systematic time-based
          packet sampling to the packet stream.";
        reference "RFC5475, Section 5.1;
          RFC5476, Section 6.5.2.2.";
        leaf timeInterval {
          type uint32;
          units microseconds;
          mandatory true;
          description "The time interval in microseconds during
            which all arriving packets are sampled between gaps
            of length timeSpace.
            This parameter corresponds to the Information Element
            samplingTimeInterval.";
          reference "RFC5477, Section 8.2.4.";
        }
        leaf timeSpace {
          type uint32;
          units microseconds;
          mandatory true;
          description "The time interval in microseconds during
            which no packets are sampled between two sampling
            intervals specified by timeInterval.
            This parameter corresponds to the Information Element
            samplingTimeInterval.";
          reference "RFC5477, Section 8.2.5.";
        }
      }
      container sampRandOutOfN {
        if-feature psampSampRandOutOfN;
        description "This container contains the configuration
          parameters of a Selector applying n-out-of-N packet
          sampling to the packet stream.";
        reference "RFC5475, Section 5.2.1;
          RFC5476, Section 6.5.2.3.";
        leaf size {
          type uint32;
          units packets;
          mandatory true;
          description "The number of elements taken from the parent
            population.
            This parameter corresponds to the Information Element
            samplingSize.";
          reference "RFC5477, Section 8.2.6.";
        }
        leaf population {
          type uint32;
          units packets;
          mandatory true;
          description "The number of elements in the parent
            population.
            This parameter corresponds to the Information Element
            samplingPopulation.";
          reference "RFC5477, Section 8.2.7.";
        }
      }
      container sampUniProb {
        if-feature psampSampUniProb;
        description "This container contains the configuration
          parameters of a Selector applying uniform probabilistic
          packet sampling (with equal probability per packet) to the
          packet stream.";
        reference "RFC5475, Section 5.2.2.1;
          RFC5476, Section 6.5.2.4.";
        leaf probability {
          type decimal64 {
            fraction-digits 18;
            range "0..1";
          }
          mandatory true;
          description "Probability that a packet is sampled,
            expressed as a value between 0 and 1. The probability
            is equal for every packet.
            This parameter corresponds to the Information Element
            samplingProbability.";
          reference "RFC5477, Section 8.2.8.";
        }
      }
      container filterMatch {
        if-feature psampFilterMatch;
        description "This container contains the configuration
          parameters of a Selector applying property match filtering
          to the packet stream.";
        reference "RFC5475, Section 6.1;
          RFC5476, Section 6.5.2.5.";
        choice nameOrId {
          mandatory true;
          description "The field to be matched is specified by
            either the name or the ID of the Information
            Element.";
          leaf ieName {
            type string;
            description "Name of the Information Element.";
          }
          leaf ieId {
            type uint16 {
              range "1..32767" {
                description "Valid range of Information Element
                    identifiers.";
                reference "RFC5102, Section 4.";
              }
            }
            description "ID of the Information Element.";
          }
        }
        leaf ieEnterpriseNumber {
          type uint32;
          description "If present, the Information Element is
            enterprise-specific. The field value configures the
            enterprise number. If omitted or zero, the Information
            Element is registered in the IANA registry of IPFIX
            Information Elements.";
        }
        leaf value {
          type string;
          mandatory true;
          description "Matching value of the Information Element.";
        }
      }
      container filterHash {
        if-feature psampFilterHash;
        description "This container contains the configuration
          parameters of a Selector applying hash-based filtering
          to the packet stream.";
        reference "RFC5475, Section 6.2;
          RFC5476, Section 6.5.2.6.";
        leaf hashFunction {
          type identityref {
            base "hashFunction";
          }
          default BOB;
          description "Hash function to be applied. According to
            RFC5475, Section 6.2.4.1, 'BOB' must be used in order to
            be compliant with PSAMP.";
        }
        leaf ipPayloadOffset {
          type uint64;
          units octets;
          default 0;
          description "IP payload offset indicating the position of
            the first payload byte considered as input to the hash
            function.
            Default value 0 corresponds to the minimum offset that
            must be configurable according to RFC5476, Section
            6.2.5.6.
            This parameter corresponds to the Information Element
            hashIPPayloadOffset.";
          reference "RFC5477, Section 8.3.2.";
        }
        leaf ipPayloadSize {
          type uint64;
          units octets;
          default 8;
          description "Number of IP payload bytes used as input to
            the hash function, counted from the payload offset.
            If the IP payload is shorter than the payload range,
            all available payload octets are used as input.
            Default value 8 corresponds to the minimum IP payload
            size that must be configurable according to RFC5476,
            Section 6.2.5.6.
            This parameter corresponds to the Information Element
            hashIPPayloadSize.";
          reference "RFC5477, Section 8.3.3.";
        }
        leaf digestOutput {
          type boolean;
          default false;
          description "If true, the output from this Selector is
            included in the Packet Report as a packet digest.
            Therefore, the configured Cache Layout needs to contain
            a digestHashValue field.
            This parameter corresponds to the Information Element
            hashDigestOutput.";
          reference "RFC5477, Section 8.3.8.";
        }
        leaf initializerValue {
          type uint64;
          description "Initializer value to the hash function.
            If not configured by the user, the Monitoring Device
            arbitrarily chooses an initializer value.";
          reference "RFC5477, Section 8.3.9.";
        }
        list selectedRange {
          key name;
          min-elements 1;
          description "List of hash function return ranges for
            which packets are selected.";
          leaf name {
            type nameType;
            description "Key of this list.";
          }
          leaf min {
            type uint64;
            description "Beginning of the hash function's selected
              range.
              This parameter corresponds to the Information Element
              hashSelectedRangeMin.";
            reference "RFC5477, Section 8.3.6.";
          }
          leaf max {
            type uint64;
            description "End of the hash function's selected range.
              This parameter corresponds to the Information Element
              hashSelectedRangeMax.";
            reference "RFC5477, Section 8.3.7.";
          }
        }
      }
    }
    leaf packetsObserved {
      type yang:counter64;
      config false;
      description "The number of packets observed at the input of
        the Selector.
        If this is the first Selector in the Selection Process,
        this counter corresponds to the total number of packets in
        all Observed Packet Streams at the input of the Selection
        Process. Otherwise, the counter corresponds to the total
        number of packets at the output of the preceding Selector.
        Discontinuities in the value of this counter can occur at
        re-initialization of the management system, and at other
        times as indicated by the value of
        selectorDiscontinuityTime.";
      reference "RFC5815, Section 8
        (ipfixSelectorStatsPacketsObserved).";
    }
    leaf packetsDropped {
      type yang:counter64;
      config false;
      description "The total number of packets discarded by the
        Selector.
        Discontinuities in the value of this counter can occur at
        re-initialization of the management system, and at other
        times as indicated by the value of
        selectorDiscontinuityTime.";
      reference "RFC5815, Section 8
        (ipfixSelectorStatsPacketsDropped).";
    }
    leaf selectorDiscontinuityTime {
      type yang:date-and-time;
      config false;
      description "Timestamp of the most recent occasion at which
        one or more of the Selector counters suffered a
        discontinuity.
        In contrast to ipfixSelectionProcessStatsDiscontinuityTime
        in the IPFIX MIB module, the time is absolute and not
        relative to sysUpTime.";
      reference "RFC5815, Section 8
        (ipfixSelectionProcessStatsDiscontinuityTime).";
    }
  }

  grouping cacheParameters {
    description "Configuration and state parameters of a Cache.";
    leaf cacheMode {
      type identityref {
        base "cacheMode";
      }
      mandatory true;
      description "Cache Mode of this Cache.";
    }
    leaf maxFlows {
      when "../cacheMode != 'immediate'" {
        description "This parameter is not available for Cache Mode
          'immediate'.";
      }
      type uint32;
      units flows;
      description "This parameter configures the maximum number of
        Flows in the Cache, which is the maximum number of Flows
        that can be measured simultaneously.
        The Monitoring Device MUST ensure that sufficient resources
        are available to store the configured maximum number of
        Flows.
        If the maximum number of Flows is measured, no additional
        Flows can be measured before any of the existing entries is
        removed. However, traffic which pertains to existing Flows
        can continue to be measured.";
    }
    leaf activeTimeout {
      when "(../cacheMode = 'timeout') or
        (../cacheMode = 'natural')" {
        description "This parameter is only available for Cache Modes
          'timeout' and 'natural'.";
      }
      type uint32;
      units milliseconds;
      description "This parameter configures the time in
        milliseconds after which a Flow is expired even though
        packets matching this Flow are still received by the Cache.
        The parameter value zero indicates infinity, meaning that
        there is no active timeout.
        If not configured by the user, the Monitoring Device sets
        this parameter.";
    }
    leaf inactiveTimeout {
      when "(../cacheMode = 'timeout') or
        (../cacheMode = 'natural')" {
        description "This parameter is only available for Cache Modes
          'timeout' and 'natural'.";
      }
      type uint32;
      units milliseconds;
      description "This parameter configures the time in
        milliseconds after which a Flow is expired if no packets
        matching this Flow are received by the Cache.
        The parameter value zero indicates infinity, meaning that
        there is no inactive timeout.
        If not configured by the user, the Monitoring Device sets
        this parameter.";
    }
    leaf exportInterval {
      when "../cacheMode = 'permanent'" {
        description "This parameter is only available for Cache Mode
          'permanent'.";
      }
      type uint32;
      units milliseconds;
      description "This parameter configures the interval for
        periodical export of Flow Records in milliseconds.
        If not configured by the user, the Monitoring Device sets
        this parameter.";
    }
    container cacheLayout {
      description "Cache Layout.";
      list cacheField {
        key name;
        min-elements 1;
        description "List of fields in the Cache Layout.";
        leaf name {
          type nameType;
          description "Key of this list.";
        }
        choice nameOrId {
          mandatory true;
          description "Name or ID of the Information Element.";
          reference "RFC5102.";
          leaf ieName {
            type string;
            description "Name of the Information Element.";
          }
          leaf ieId {
            type uint16 {
              range "1..32767" {
                description "Valid range of Information Element
                    identifiers.";
                reference "RFC5102, Section 4.";
              }
            }
            description "ID of the Information Element.";
          }
        }
        leaf ieLength {
          type uint16;
          units octets;
          description "Length of the field in which the Information
            Element is encoded. A value of 65535 specifies a
            variable-length Information Element. For Information
            Elements of integer and float type, the field length MAY
            be set to a smaller value than the standard length of the
            abstract data type if the rules of reduced size encoding
            are fulfilled.
            If not configured by the user, this parameter is set by
            the Monitoring Device.";
          reference "RFC5101, Section 6.2; RFC5102.";
        }
        leaf ieEnterpriseNumber {
          type uint32;
          description "If present, the Information Element is
            enterprise-specific. The field value configures the
            enterprise number. If omitted or zero, the Information
            Element is registered in the IANA registry of IPFIX
            Information Elements.
            If the enterprise number is set to 29305, this field
            contains a Reverse Information Element. In this case,
            the Cache MUST generate Data Records in accordance to
            RFC5103.";
          reference "RFC5101; RFC5102.";
        }
        leaf isFlowKey {
          when "(../../../cacheMode != 'immediate')
            and
            ((count(../ieEnterpriseNumber) = 0)
            or
            (../ieEnterpriseNumber != 29305))" {
            description "This parameter is not available for
              Reverse Information Elements (which have enterprise
              number 29305) or if the Cache Mode is 'immediate'.";
          }
          type empty;
          description "If present, this is a flow key.";
        }
      }
    }
    leaf activeFlows {
      when "../cacheMode != 'immediate'" {
        description "This parameter is not available for Cache Mode
          'immediate'.";
      }
      type yang:gauge32;
      units flows;
      config false;
      description "The number of Flows currently active in this
        Cache.";
      reference "ietf-draft-ipfix-mib-10, Section 8
        (ipfixMeteringProcessCacheActiveFlows).";
    }
    leaf unusedCacheEntries {
      when "../cacheMode != 'immediate'" {
        description "This parameter is not available for Cache Mode
          'immediate'.";
      }
      type yang:gauge32;
      units flows;
      config false;
      description "The number of unused Cache entries in this
        Cache.";
      reference "ietf-draft-ipfix-mib-10, Section 8
        (ipfixMeteringProcessCacheUnusedCacheEntries).";
    }
    leaf dataRecords {
      type yang:counter64;
      units "Data Records";
      config false;
      description "The number of Data Records generated by this
        Cache.
        Discontinuities in the value of this counter can occur at
        re-initialization of the management system, and at other
        times as indicated by the value of
        cacheDiscontinuityTime.";
      reference "ietf-draft-ipfix-mib-10, Section 8
        (ipfixMeteringProcessDataRecords).";
    }
    leaf cacheDiscontinuityTime {
      type yang:date-and-time;
      config false;
      description "Timestamp of the most recent occasion at which
        the counter dataRecords suffered a discontinuity.
        In contrast to ipfixMeteringProcessDiscontinuityTime
        in the IPFIX MIB module, the time is absolute and not
        relative to sysUpTime.";
      reference "ietf-draft-ipfix-mib-10, Section 8
        (ipfixMeteringProcessDiscontinuityTime).";
    }
  }

  grouping exportingProcessParameters {
    description "Parameters of an Exporting Process.";
    leaf exportMode {
      type identityref {
        base "exportMode";
      }
      default parallel;
      description "This parameter determines to which configured
        destination(s) the incoming Data Records are exported.";
    }
    list destination {
      key name;
      min-elements 1;
      description "List of export destinations.";
      leaf name {
        type nameType;
        description "Key of this list.";
      }
      choice DestinationParameters {
        mandatory true;
        description "Configuration parameters depend on whether
          SCTP, UDP, or TCP are used as transport protocol, and
          whether the destination is a file.";
        container sctpExporter {
          description "SCTP parameters.";
          uses sctpExporterParameters;
        }
        container udpExporter {
          if-feature udpTransport;
          description "UDP parameters.";
          uses udpExporterParameters;
        }
        container tcpExporter {
          if-feature tcpTransport;
          description "TCP parameters.";
          uses tcpExporterParameters;
        }
        container fileWriter {
          if-feature fileWriter;
          description "File Writer parameters.";
          uses fileWriterParameters;
        }
      }
    }
    list options {
      key name;
      description "List of options reported by the Exporting
        Process.";
      leaf name {
        type nameType;
        description "Key of this list.";
      }
      uses optionsParameters;
    }
  }

  grouping commonExporterParameters {
    description "Parameters of en export destination which are
      common to all transport protocols.";
    leaf ipfixVersion {
      type uint16;
      default 10;
      description "IPFIX version number.";
    }
    leaf destinationPort {
      type inet:port-number;
      description "If not configured by the user, the Monitoring
        Device uses the default port number for IPFIX, which is
        4739 without transport layer security and 4740 if transport
        layer security is activated.";
    }
    choice indexOrName {
      description "Index or name of the interface as stored in the
        ifTable of IF-MIB.
        If configured, the Exporting Process MUST use the given
        interface to export IPFIX Messages to the export
        destination.
        If omitted, the Exporting Process selects the outgoing
        interface based on local routing decision and accepts
        return traffic, such as transport layer acknowledgments,
        on all available interfaces.";
      reference "RFC 1229.";
      leaf ifIndex {
        type uint32;
        description "Index of an interface as stored in the ifTable
          of IF-MIB.";
        reference "RFC 1229.";
      }
      leaf ifName {
        type string;
        description "Name of an interface as stored in the ifTable
          of IF-MIB.";
        reference "RFC 1229.";
      }
    }
    leaf sendBufferSize {
      type uint32;
      units bytes;
      description "Size of the socket send buffer.
        If not configured by the user, this parameter is set by
        the Monitoring Device.";
    }
    leaf rateLimit {
      type uint32;
      units "bytes per second";
      description "Maximum number of bytes per second the Exporting
        Process may export to the given destination. The number of
        bytes is calculated from the lengths of the IPFIX Messages
        exported. If not configured, no rate limiting is performed.";
      reference "RFC5476, Section 6.3.";
    }
    container transportLayerSecurity {
      presence "If transportLayerSecurity is present, DTLS is
        enabled if the transport protocol is SCTP or UDP, and TLS
        is enabled if the transport protocol is TCP.";
      description "Transport layer security configuration.";
      uses transportLayerSecurityParameters;
    }
    container transportSession {
      config false;
      description "State parameters of the Transport Session
        directed to the given destination.";
      uses transportSessionParameters;
    }
  }

  grouping sctpExporterParameters {
    description "SCTP specific export destination parameters.";
    uses commonExporterParameters;
    leaf-list sourceIPAddress {
      type inet:ip-address;
      description "List of source IP addresses used by the
        Exporting Process.
        If configured, the specified addresses are eligible local
        IP addresses of the multi-homed SCTP endpoint.
        If not configured, all locally assigned IP addresses are
        eligible local IP addresses.";
      reference "RFC 4960 (multi-homed SCTP endpoint).";
    }
    leaf-list destinationIPAddress {
      type inet:ip-address;
      min-elements 1;
      description "One or multiple IP addresses of the Collecting
        Process to which IPFIX Messages are sent.
        The user MUST ensure that all configured IP addresses
        belong to the same Collecting Process.
        The Exporting Process tries to establish an SCTP
        association to any of the configured destination IP
        addresses.";
      reference "RFC 4960 (multi-homed SCTP endpoint).";
    }
    leaf timedReliability {
      type uint32;
      units milliseconds;
      default 0;
      description "Lifetime in milliseconds until an IPFIX
        Message containing Data Sets only is 'abandoned' due to
        the timed reliability mechanism of PR-SCTP.
        If this parameter is set to zero, reliable SCTP
        transport is used for all Data Records.
        Regardless of the value of this parameter, the Exporting
        Process MAY use reliable SCTP transport for Data Sets
        associated with Options Templates.";
      reference "RFC 3758; RFC 4960.";
    }
  }

  grouping udpExporterParameters {
    description "Parameters of a UDP export destination.";
    uses commonExporterParameters;
    leaf sourceIPAddress {
      type inet:ip-address;
      description "Source IP address used by the Exporting Process.
      If not configured, the IP address assigned to the outgoing
      interface is used as source IP address.";
    }
    leaf destinationIPAddress {
      type inet:ip-address;
      mandatory true;
      description "IP address of the Collection Process to which
        IPFIX Messages are sent.";
    }
    leaf maxPacketSize {
      type uint16;
      units octets;
      description "This parameter specifies the maximum size of
        IP packets sent to the Collector. If set to zero, the
        Exporting Device MUST derive the maximum packet size
        from path MTU discovery mechanisms.
        If not configured by the user, this parameter is set by
        the Monitoring Device.";
    }
    leaf templateRefreshTimeout {
      type uint32;
      units seconds;
      default 600;
      description "Sets time after which Templates are resent in the
        UDP Transport Session.
        Note that the configured lifetime MUST be adapted to the
        templateLifeTime parameter value at the receiving Collecting
        Process.
        Note that this parameter corresponds to
        ipfixTransportSessionTemplateRefreshTimeout in the IPFIX
        MIB module.";
      reference "RFC5101, Section 10.3.6; RFC5815, Section 8
        (ipfixTransportSessionTemplateRefreshTimeout).";
    }
    leaf optionsTemplateRefreshTimeout {
      type uint32;
      units seconds;
      default 600;
      description "Sets time after which Options Templates are
        resent in the UDP Transport Session.
        Note that the configured lifetime MUST be adapted to the
        optionsTemplateLifeTime parameter value at the receiving
        Collecting Process.
        Note that this parameter corresponds to
        ipfixTransportSessionOptionsTemplateRefreshTimeout in the
        IPFIX MIB module.";
      reference "RFC5101, Section 10.3.6; RFC5815, Section 8
        (ipfixTransportSessionOptionsTemplateRefreshTimeout).";
    }
    leaf templateRefreshPacket {
      type uint32;
      units "IPFIX Messages";
      description "Sets number of IPFIX Messages after which
        Templates are resent in the UDP Transport Session.
        Note that this parameter corresponds to
        ipfixTransportSessionTemplateRefreshPacket in the IPFIX
        MIB module.
        If omitted, Templates are only resent after timeout.";
      reference "RFC5101, Section 10.3.6; RFC5815, Section 8
        (ipfixTransportSessionTemplateRefreshPacket).";
    }
    leaf optionsTemplateRefreshPacket {
      type uint32;
      units "IPFIX Messages";
      description "Sets number of IPFIX Messages after which
        Options Templates are resent in the UDP Transport Session
        protocol.
        Note that this parameter corresponds to
        ipfixTransportSessionOptionsTemplateRefreshPacket in the
        IPFIX MIB module.
        If omitted, Templates are only resent after timeout.";
      reference "RFC5101, Section 10.3.6; RFC5815, Section 8
        (ipfixTransportSessionOptionsTemplateRefreshPacket).";
    }
  }

  grouping tcpExporterParameters {
    description "Parameters of a TCP export destination.";
    uses commonExporterParameters;
    leaf sourceIPAddress {
      type inet:ip-address;
      description "Source IP address used by the Exporting Process.
        If not configured by the user, this parameter is set by
        the Monitoring Device to an IP address assigned to the
        outgoing interface.";
    }
    leaf destinationIPAddress {
      type inet:ip-address;
      mandatory true;
      description "IP address of the Collection Process to which
        IPFIX Messages are sent.";
    }
  }

  grouping fileWriterParameters {
    description "File Writer parameters.";
    leaf ipfixVersion {
      type uint16;
      default 10;
      description "IPFIX version number.";
    }
    leaf file {
      type inet:uri;
      mandatory true;
      description "URI specifying the location of the file.";
    }
    leaf bytes {
      type yang:counter64;
      units octets;
      config false;
      description "The number of bytes written by the File Writer.
        Discontinuities in the value of this counter can occur at
        re-initialization of the management system, and at other
        times as indicated by the value of
        fileWriterDiscontinuityTime.";
    }
    leaf messages {
      type yang:counter64;
      units "IPFIX Messages";
      config false;
      description "The number of IPFIX Messages written by the File
        Writer.
        Discontinuities in the value of this counter can occur at
        re-initialization of the management system, and at other
        times as indicated by the value of
        fileWriterDiscontinuityTime.";
    }
    leaf discardedMessages {
      type yang:counter64;
      units "IPFIX Messages";
      config false;
      description "The number of IPFIX Messages that could not be
        written by the File Writer due to internal buffer
        overflows, limited storage capacity etc.
        Discontinuities in the value of this counter can occur at
        re-initialization of the management system, and at other
        times as indicated by the value of
        fileWriterDiscontinuityTime.";
    }
    leaf records {
      type yang:counter64;
      units "Data Records";
      config false;
      description "The number of Data Records written by the File
        Writer.
        Discontinuities in the value of this counter can occur at
        re-initialization of the management system, and at other
        times as indicated by the value of
        fileWriterDiscontinuityTime.";
    }
    leaf templates {
      type yang:counter32;
      units "Templates";
      config false;
      description "The number of Template Records (excluding
        Options Template Records) written by the File Writer.
        Discontinuities in the value of this counter can occur at
        re-initialization of the management system, and at other
        times as indicated by the value of
        fileWriterDiscontinuityTime.";
    }
    leaf optionsTemplates {
      type yang:counter32;
      units "Options Templates";
      config false;
      description "The number of Options Template Records written
        by the File Writer.
        Discontinuities in the value of this counter can occur at
        re-initialization of the management system, and at other
        times as indicated by the value of
        fileWriterDiscontinuityTime.";
    }
    leaf fileWriterDiscontinuityTime {
      type yang:date-and-time;
      config false;
      description "Timestamp of the most recent occasion at which
        one or more File Writer counters suffered a discontinuity.
        In contrast to discontinuity times in the IPFIX MIB module,
        the time is absolute and not relative to sysUpTime.";
    }
    list template {
      config false;
      description "This list contains the Templates and Options
        Templates that have been written by the File Reader.
        Withdrawn or invalidated (Options) Template MUST be removed
        from this list.";
      uses templateParameters;
    }
  }

  grouping optionsParameters {
    description "Parameters specifying the data export using an
      Options Template.";
    leaf optionsType {
      type identityref {
        base "optionsType";
      }
      mandatory true;
      description "Type of the exported options data.";
    }
    leaf optionsTimeout {
      type uint32;
      units milliseconds;
      description "Time interval for periodic export of the options
        data. If set to zero, the export is triggered when the
        options data has changed.
        If not configured by the user, this parameter is set by the
        Monitoring Device.";
    }
  }

  grouping collectingProcessParameters {
    description "Parameters of a Collecting Process.";
    list sctpCollector {
      key name;
      description "List of SCTP receivers (sockets) on which the
        Collecting Process receives IPFIX Messages.";
      leaf name {
        type nameType;
        description "Key of this list.";
      }
      uses sctpCollectorParameters;
    }
    list udpCollector {
      if-feature udpTransport;
      key name;
      description "List of UDP receivers (sockets) on which the
        Collecting Process receives IPFIX Messages.";
      leaf name {
        type nameType;
        description "Key of this list.";
      }
      uses udpCollectorParameters;
    }
    list tcpCollector {
      if-feature tcpTransport;
      key name;
      description "List of TCP receivers (sockets) on which the
        Collecting Process receives IPFIX Messages.";
      leaf name {
        type nameType;
        description "Key of this list.";
      }
      uses tcpCollectorParameters;
    }
    list fileReader {
      if-feature fileReader;
      key name;
      description "List of File Readers from which the Collecting
        Process reads IPFIX Messages.";
      leaf name {
        type nameType;
        description "Key of this list.";
      }
      uses fileReaderParameters;
    }
  }

  grouping commonCollectorParameters {
    description "Parameters of a Collecting Process which are
      common to all transport protocols.";
    leaf localPort {
      type inet:port-number;
      description "If not configured, the Monitoring Device uses the
        default port number for IPFIX, which is 4739 without
        transport layer security and 4740 if transport layer
        security is activated.";
    }
    container transportLayerSecurity {
      presence "If transportLayerSecurity is present, DTLS is enabled
        if the transport protocol is SCTP or UDP, and TLS is enabled
        if the transport protocol is TCP.";
      description "Transport layer security configuration.";
      uses transportLayerSecurityParameters;
    }
    list transportSession {
      config false;
      description "This list contains the currently established
        Transport Sessions terminating at the given socket.";
      uses transportSessionParameters;
    }
  }

  grouping sctpCollectorParameters {
    description "Parameters of a listening SCTP socket at a
      Collecting Process.";
    uses commonCollectorParameters;
    leaf-list localIPAddress {
      type inet:ip-address;
      description "List of local IP addresses on which the
        Collecting Process listens for IPFIX Messages. The IP
        addresses are used as eligible local IP addresses of the
        multi-homed SCTP endpoint.";
      reference "RFC 4960 (multi-homed SCTP endpoint).";
    }
  }

  grouping udpCollectorParameters {
    description "Parameters of a listening UDP socket at a
      Collecting Process.";
    uses commonCollectorParameters;
    leaf-list localIPAddress {
      type inet:ip-address;
      description "List of local IP addresses on which the Collecting
        Process listens for IPFIX Messages.";
    }
    leaf templateLifeTime {
      type uint32;
      units seconds;
      default 1800;
      description "Sets the lifetime of Templates for all UDP
        Transport Sessions terminating at this UDP socket.
        Templates which are not received again within the configured
        lifetime become invalid at the Collecting Process.
        As specified in RFC5101, the Template lifetime MUST be at
        least three times higher than the templateRefreshTimeout
        parameter value configured on the corresponding Exporting
        Processes.
        Note that this parameter corresponds to
        ipfixTransportSessionTemplateRefreshTimeout in the IPFIX
        MIB module.";
      reference "RFC5101, Section 10.3.7; RFC5815, Section 8
        (ipfixTransportSessionTemplateRefreshTimeout).";
    }
    leaf optionsTemplateLifeTime {
      type uint32;
      units seconds;
      default 1800;
      description "Sets the lifetime of Options Templates for all
        UDP Transport Sessions terminating at this UDP socket.
        Options Templates which are not received again within the
        configured lifetime become invalid at the Collecting
        Process.
        As specified in RFC5101, the Options Template lifetime MUST
        be at least three times higher than the
        optionsTemplateRefreshTimeout parameter value configured on
        the corresponding Exporting Processes.
        Note that this parameter corresponds to
        ipfixTransportSessionOptionsTemplateRefreshTimeout in the
        IPFIX MIB module.";
      reference "RFC5101, Section 10.3.7; RFC5815, Section 8
        (ipfixTransportSessionOptionsTemplateRefreshTimeout).";
    }
    leaf templateLifePacket {
      type uint32;
      units "IPFIX Messages";
      description "If this parameter is configured, Templates
        defined in a UDP Transport Session become invalid if they
        are neither included in a sequence of more than this number
        of IPFIX Messages nor received again within the period of
        time specified by templateLifeTime.
        Note that this parameter corresponds to
        ipfixTransportSessionTemplateRefreshPacket in the IPFIX
        MIB module.";
      reference "RFC5101, Section 10.3.7; RFC5815, Section 8
        (ipfixTransportSessionTemplateRefreshPacket).";
    }
    leaf optionsTemplateLifePacket {
      type uint32;
      units "IPFIX Messages";
      description "If this parameter is configured, Options
        Templates defined in a UDP Transport Session become
        invalid if they are neither included in a sequence of more
        than this number of IPFIX Messages nor received again
        within the period of time specified by
        optionsTemplateLifeTime.
        Note that this parameter corresponds to
        ipfixTransportSessionOptionsTemplateRefreshPacket in the
        IPFIX MIB module.";
      reference "RFC5101, Section 10.3.7; RFC5815, Section 8
        (ipfixTransportSessionOptionsTemplateRefreshPacket).";
    }
  }

  grouping tcpCollectorParameters {
    description "Parameters of a listening TCP socket at a
      Collecting Process.";
    uses commonCollectorParameters;
    leaf-list localIPAddress {
      type inet:ip-address;
      description "List of local IP addresses on which the Collecting
        Process listens for IPFIX Messages.";
    }
  }

  grouping fileReaderParameters {
    description "File Reader parameters.";
    leaf file {
      type inet:uri;
      mandatory true;
      description "URI specifying the location of the file.";
    }
    leaf bytes {
      type yang:counter64;
      units octets;
      config false;
      description "The number of bytes read by the File Reader.
        Discontinuities in the value of this counter can occur at
        re-initialization of the management system, and at other
        times as indicated by the value of
        fileReaderDiscontinuityTime.";
    }
    leaf messages {
      type yang:counter64;
      units "IPFIX Messages";
      config false;
      description "The number of IPFIX Messages read by the File
        Reader.
        Discontinuities in the value of this counter can occur at
        re-initialization of the management system, and at other
        times as indicated by the value of
        fileReaderDiscontinuityTime.";
    }
    leaf records {
      type yang:counter64;
      units "Data Records";
      config false;
      description "The number of Data Records read by the File
        Reader.
        Discontinuities in the value of this counter can occur at
        re-initialization of the management system, and at other
        times as indicated by the value of
        fileReaderDiscontinuityTime.";
    }
    leaf templates {
      type yang:counter32;
      units "Templates";
      config false;
      description "The number of Template Records (excluding
        Options Template Records) read by the File Reader.
        Discontinuities in the value of this counter can occur at
        re-initialization of the management system, and at other
        times as indicated by the value of
        fileReaderDiscontinuityTime.";
    }
    leaf optionsTemplates {
      type yang:counter32;
      units "Options Templates";
      config false;
      description "The number of Options Template Records read by
        the File Reader.
        Discontinuities in the value of this counter can occur at
        re-initialization of the management system, and at other
        times as indicated by the value of
        fileReaderDiscontinuityTime.";
    }
    leaf fileReaderDiscontinuityTime {
      type yang:date-and-time;
      config false;
      description "Timestamp of the most recent occasion at which
        one or more File Reader counters suffered a discontinuity.
        In contrast to discontinuity times in the IPFIX MIB module,
        the time is absolute and not relative to sysUpTime.";
    }
    list template {
      config false;
      description "This list contains the Templates and Options
        Templates that have been read by the File Reader.
        Withdrawn or invalidated (Options) Template MUST be removed
        from this list.";
      uses templateParameters;
    }
  }

  grouping transportLayerSecurityParameters {
    description "Transport layer security parameters.";
    leaf-list localCertificationAuthorityDN {
      type string;
      description "Distinguished names of certification authorities
        whose certificates may be used to identify the local
        endpoint.";
    }
    leaf-list localSubjectDN {
      type string;
      description "Distinguished names which may be used in the
        certificates to identify the local endpoint.";
    }
    leaf-list localSubjectFQDN {
      type inet:domain-name;
      description "Fully qualified domain names which may be used to
        in the certificates to identify the local endpoint.";
    }
    leaf-list remoteCertificationAuthorityDN {
      type string;
      description "Distinguished names of certification authorities
        whose certificates are accepted to authorize remote
        endpoints.";
    }
    leaf-list remoteSubjectDN {
      type string;
      description "Distinguished names which are accepted in
        certificates to authorize remote endpoints.";
    }
    leaf-list remoteSubjectFQDN {
      type inet:domain-name;
      description "Fully qualified domain name which are accepted in
        certificates to authorize remote endpoints.";
    }
  }

  grouping templateParameters {
    description "State parameters of a Template used by an Exporting
      Process or received by a Collecting Process in a specific
      Transport Session. Parameter names and semantics correspond to
      the managed objects in IPFIX-MIB";
    reference "RFC5101; RFC5815, Section 8 (ipfixTemplateEntry,
      ipfixTemplateDefinitionEntry, ipfixTemplateStatsEntry)";
    leaf observationDomainId {
      type uint32;
      description "The ID of the Observation Domain for which this
        Template is defined.";
      reference "RFC5815, Section 8
        (ipfixTemplateObservationDomainId).";
    }
    leaf templateId {
      type uint16 {
        range "256..65535" {
          description "Valid range of Template IDs.";
          reference "RFC5101";
        }
      }
      description "This number indicates the Template Id in the IPFIX
        message.";
      reference "RFC5815, Section 8 (ipfixTemplateId).";
    }
    leaf setId {
      type uint16;
      description "This number indicates the Set ID of the Template.
        Currently, there are two values defined. The value 2 is used
        for Sets containing Template definitions. The value 3 is
        used for Sets containing Options Template definitions.";
      reference "RFC5815, Section 8 (ipfixTemplateSetId).";
    }
    leaf accessTime {
      type yang:date-and-time;
      description "Used for Exporting Processes, this parameter
        contains the time when this (Options) Template was last
        sent to the Collector(s) or written to the file.
        Used for Collecting Processes, this parameter contains the
        time when this (Options) Template was last received from the
        Exporter or read from the file.";
      reference "RFC5815, Section 8 (ipfixTemplateAccessTime).";
    }
    leaf templateDataRecords {
      type yang:counter64;
      description "The number of transmitted or received Data
        Records defined by this (Options) Template.
        Discontinuities in the value of this counter can occur at
        re-initialization of the management system, and at other
        times as indicated by the value of
        templateDiscontinuityTime.";
      reference "RFC5815, Section 8 (ipfixTemplateDataRecords).";
    }
    leaf templateDiscontinuityTime {
      type yang:date-and-time;
      description "Timestamp of the most recent occasion at which
        the counter templateDataRecords suffered a discontinuity.
        In contrast to ipfixTemplateDiscontinuityTime in the IPFIX
        MIB module, the time is absolute and not relative to
        sysUpTime.";
      reference "RFC5815, Section 8
        (ipfixTemplateDiscontinuityTime).";
    }
    list field {
      description "This list contains the (Options) Template
        fields of which the (Options) Template is defined.
        The order of the list corresponds to the order of the fields
        in the (Option) Template Record.";
      leaf ieId {
        type uint16 {
          range "1..32767" {
            description "Valid range of Information Element
                identifiers.";
            reference "RFC5102, Section 4.";
          }
        }
        description "This parameter indicates the Information
          Element Id of the field.";
        reference "RFC5815, Section 8 (ipfixTemplateDefinitionIeId);
          RFC5102.";
      }
      leaf ieLength {
        type uint16;
        units octets;
        description "This parameter indicates the length of the
          Information Element of the field.";
        reference "RFC5815, Section 8
          (ipfixTemplateDefinitionIeLength); RFC5102.";
      }
      leaf ieEnterpriseNumber {
        type uint32;
        description "This parameter indicates the IANA enterprise
          number of the authority defining the Information Element
          Id.
          If the Information Element is not enterprise-specific,
          this state parameter is omitted.";
        reference "RFC5815, Section 8
          (ipfixTemplateDefinitionIeEnterpriseNumber).";
      }
      leaf isFlowKey {
        when "../../setId = 2" {
          description "This parameter is available for non-Options
            Templates (Set ID is 2).";
        }
        type empty;
        description "If present, this is a Flow Key field.";
        reference "RFC5815, Section 8
          (ipfixTemplateDefinitionFlags).";
      }
      leaf isScope {
        when "../../setId = 3" {
          description "This parameter is available for Options
            Templates (Set ID is 3).";
        }
        type empty;
        description "If present, this is a scope field.";
        reference "RFC5815, Section 8
          (ipfixTemplateDefinitionFlags).";
      }
    }
  }

  grouping transportSessionParameters {
    description "State parameters of a Transport Session originating
      from an Exporting or terminating at a Collecting Process.
      Parameter names and semantics correspond to the managed
      objects in IPFIX-MIB.";
    reference "RFC5101, RFC5815, Section 8
      (ipfixTransportSessionEntry,
       ipfixTransportSessionStatsEntry)";
    leaf ipfixVersion {
      type uint16;
      description "Used for Exporting Processes, this parameter
        contains the version number of the IPFIX protocol that the
        Exporter uses to export its data in this Transport Session.
        Hence, it is identical to the value of the configuration
        parameter ipfixVersion of the outer SctpExporter,
        UdpExporter, or TcpExporter node.
        Used for Collecting Processes, this parameter contains the
        version number of the IPFIX protocol it receives for
        this Transport Session. If IPFIX Messages of different
        IPFIX protocol versions are received, this parameter
        contains the maximum version number.";
      reference "RFC5815, Section 8
        (ipfixTransportSessionIpfixVersion).";
    }
    leaf sourceAddress {
      type inet:ip-address;
      description "The source address of the Exporter of the
        IPFIX Transport Session.
        This parameter is omitted if the transport protocol is
        SCTP since SCTP has no notion of addresses.
        In the case of UDP, the parameter value equals the value
        of the configuration parameter sourceIPAddress of the outer
        UdpExporter node.";
      reference "RFC5815, Section 8
        (ipfixTransportSessionSourceAddressType,
        ipfixTransportSessionSourceAddress).";
    }
    leaf destinationAddress {
      type inet:ip-address;
      description "The destination address of the Collector of
        the IPFIX Transport Session.
        This parameter is omitted if the transport protocol is
        SCTP since SCTP has no notion of addresses.
        Used for Exporting Processes, the parameter value equals
        the value of the configuration parameter
        destinationIPAddress of the outer UdpExporter or
        TcpExporter node.
        Used for Collecting Processes, the parameter value equals
        the value of the configuration parameter localIPAddress
        of the outer UdpCollector or TcpCollector node.";
      reference "RFC5815, Section 8
        (ipfixTransportSessionDestinationAddressType,
        ipfixTransportSessionDestinationAddress).";
    }
    leaf sourcePort {
      type inet:port-number;
      description "The transport protocol port number of the
        Exporter of the IPFIX Transport Session.";
      reference "RFC5815, Section 8
        (ipfixTransportSessionSourcePort).";
    }
    leaf destinationPort {
      type inet:port-number;
      description "The transport protocol port number of the
        Collector of the IPFIX Transport Session.
        Used for Exporting Processes, the parameter value equals
        the value of the configuration parameter destinationPort
        of the outer SctpExporter, UdpExporter, or TcpExporter
        node.
        Used for Collecting Processes, the parameter value equals
        the value of the configuration parameter localPort of the
        outer SctpCollector, UdpCollector, or TcpCollector node.";
      reference "RFC5815, Section 8
        (ipfixTransportSessionDestinationPort).";
    }
    leaf sctpAssocId {
      type uint32;
      description "The association id used for the SCTP session
        between the Exporter and the Collector of the IPFIX
        Transport Session. It is equal to the sctpAssocId entry
        in the sctpAssocTable defined in the SCTP-MIB.
        This parameter is only available if the transport protocol
        is SCTP.";
      reference "RFC5815, Section 8
        (ipfixTransportSessionSctpAssocId),
        RFC3871";
    }
    leaf status {
      type transportSessionStatus;
      description "Status of the Transport Session.";
      reference "RFC5815, Section 8 (ipfixTransportSessionStatus).";
    }
    leaf rate {
      type yang:gauge32;
      units "bytes per second";
      description "The number of bytes per second transmitted by the
        Exporting Process or received by the Collecting Process.
        This parameter is updated every second.";
      reference "RFC5815, Section 8 (ipfixTransportSessionRate).";
    }
    leaf bytes {
      type yang:counter64;
      units bytes;
      description "The number of bytes transmitted by the
        Exporting Process or received by the Collecting Process.
        Discontinuities in the value of this counter can occur at
        re-initialization of the management system, and at other
        times as indicated by the value of
        transportSessionDiscontinuityTime.";
      reference "RFC5815, Section 8 (ipfixTransportSessionBytes).";
    }
    leaf messages {
      type yang:counter64;
      units "IPFIX Messages";
      description "The number of messages transmitted by the
        Exporting Process or received by the Collecting Process.
        Discontinuities in the value of this counter can occur at
        re-initialization of the management system, and at other
        times as indicated by the value of
        transportSessionDiscontinuityTime.";
      reference "RFC5815, Section 8
        (ipfixTransportSessionMessages).";
    }
    leaf discardedMessages {
      type yang:counter64;
      units "IPFIX Messages";
      description "Used for Exporting Processes, this parameter
        indicates the number of messages that could not be sent due
        to internal buffer overflows, network congestion, routing
        issues, etc. Used for Collecting Process, this parameter
        indicates the number of received IPFIX Message that are
        malformed, cannot be decoded, are received in the wrong
        order or are missing according to the sequence number.
        Discontinuities in the value of this counter can occur at
        re-initialization of the management system, and at other
        times as indicated by the value of
        transportSessionDiscontinuityTime.";
      reference "RFC5815, Section 8
        (ipfixTransportSessionDiscardedMessages).";
    }
    leaf records {
      type yang:counter64;
      units "Data Records";
      description "The number of Data Records transmitted by the
        Exporting Process or received by the Collecting Process.
        Discontinuities in the value of this counter can occur at
        re-initialization of the management system, and at other
        times as indicated by the value of
        transportSessionDiscontinuityTime.";
      reference "RFC5815, Section 8
        (ipfixTransportSessionRecords).";
    }
    leaf templates {
      type yang:counter32;
      units "Templates";
      description "The number of Templates transmitted by the
        Exporting Process or received by the Collecting Process.
        Discontinuities in the value of this counter can occur at
        re-initialization of the management system, and at other
        times as indicated by the value of
        transportSessionDiscontinuityTime.";
      reference "RFC5815, Section 8
        (ipfixTransportSessionTemplates).";
    }
    leaf optionsTemplates {
      type yang:counter32;
      units "Options Templates";
      description "The number of Option Templates transmitted by the
        Exporting Process or received by the Collecting Process.
        Discontinuities in the value of this counter can occur at
        re-initialization of the management system, and at other
        times as indicated by the value of
        transportSessionDiscontinuityTime.";
      reference "RFC5815, Section 8
        (ipfixTransportSessionOptionsTemplates).";
    }
    leaf transportSessionStartTime {
      type yang:date-and-time;
      description "Timestamp of the start of the given Transport
        Session.
        This state parameter does not correspond to any object in
        the IPFIX MIB module.";
    }
    leaf transportSessionDiscontinuityTime {
      type yang:date-and-time;
      description "Timestamp of the most recent occasion at which
        one or more of the Transport Session counters suffered a
        discontinuity.
        In contrast to ipfixTransportSessionDiscontinuityTime
        in the IPFIX MIB module, the time is absolute and not
        relative to sysUpTime.";
      reference "RFC5815, Section 8
        (ipfixTransportSessionDiscontinuityTime).";
    }
    list template {
      description "This list contains the Templates and Options
        Templates that are transmitted by the Exporting Process
        or received by the Collecting Process.
        Withdrawn or invalidated (Options) Template MUST be removed
        from this list.";
      uses templateParameters;
    }
  }

  /*****************************************************************
  * Main container
  *****************************************************************/

  container ipfix {
    description "Top-level node of the IPFIX/PSAMP configuration
      data model.";
    list collectingProcess {
      if-feature collector;
      key name;
      description "Collecting Process of the Monitoring Device.";
      leaf name {
        type nameType;
        description "Key of this list.";
      }
      uses collectingProcessParameters;
      leaf-list exportingProcess {
        type leafref { path "/ipfix/exportingProcess/name"; }
        description "Export of received records without any
          modifications. Records are processed by all Exporting
          Processes in the list.";
      }
    }

    list observationPoint {
      if-feature meter;
      key name;
      description "Observation Point of the Monitoring Device.";
      leaf name {
        type nameType;
        description "Key of this list.";
      }
      uses observationPointParameters;
      leaf-list selectionProcess {
        type leafref { path "/ipfix/selectionProcess/name"; }
        description "Selection Processes in this list process packets
          in parallel.";
      }
    }

    list selectionProcess {
      if-feature meter;
      key name;
      description "Selection Process of the Monitoring Device.";
      leaf name {
        type nameType;
        description "Key of this list.";
      }
      list selector {
        key name;
        min-elements 1;
        ordered-by user;
        description "List of Selectors that define the action of the
          Selection Process on a single packet. The Selectors are
          serially invoked in the same order as they appear in this
          list.";
        leaf name {
          type nameType;
          description "Key of this list.";
        }
        uses selectorParameters;
      }
      list selectionSequence {
        config false;
        description "This list contains the Selection Sequence IDs
          which are assigned by the Monitoring Device to distinguish
          different Selection Sequences passing through the
          Selection Process.
          As Selection Sequence IDs are unique per Observation
          Domain, the corresponding Observation Domain IDs are
          included as well.
          With this information, it is possible to associate
          Selection Sequence (Statistics) Report Interpretations
          exported according to the PSAMP protocol with a Selection
          Process in the configuration data.";
        reference "RFC5476.";
        leaf observationDomainId {
          type uint32;
          description "Observation Domain ID for which the
            Selection Sequence ID is assigned.";
        }
        leaf selectionSequenceId {
          type uint64;
          description "Selection Sequence ID used in the Selection
            Sequence (Statistics) Report Interpretation.";
        }
      }
      leaf cache {
        type leafref { path "/ipfix/cache/name"; }
        description "Cache which receives the output of the
          Selection Process.";
      }
    }

    list cache {
      if-feature meter;
      key name;
      description "Cache of the Monitoring Device.";
      leaf name {
        type nameType;
        description "Key of this list.";
      }
      uses cacheParameters;
      leaf-list exportingProcess {
        type leafref { path "/ipfix/exportingProcess/name"; }
        description "Records are exported by all Exporting Processes
          in the list.";
      }
    }

    list exportingProcess {
      if-feature exporter;
      key name;
      description "Exporting Process of the Monitoring Device.";
      leaf name {
        type nameType;
        description "Key of this list.";
      }
      uses exportingProcessParameters;
    }
  }
}
