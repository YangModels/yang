module example-iana-if-type {
  yang-version "1.1";
  namespace "urn:ietf:params:xml:ns:yang:example-iana-if-type";
  prefix ianaift;

  import ietf-interfaces {
    prefix if;
  }

  import iana-if-property-type {
    prefix ianaifp;
  }

  // Full description, etc elided for clarity.
  organization "IANA";
  contact "";
  description
    "This example module illustrates how iana-if-type.yang could
     be extended to use interface properties.";
  reference
    "IANA 'ifType definitions' registry.
     <http://www.iana.org/assignments/smi-numbers>";

  revision 2017-06-27 {
    description
      "Initial example of how IANA if type could be extended";
    reference
      "Taken from draft-rwilton-netmod-interface-properties-00";
  }

  // Previous revision statements elided for clarity.

  identity iana-interface-type {
    base if:interface-type;
    description
      "This identity is used as a base for all interface types
       defined in the 'ifType definitions' registry.";
  }

  // Most identies elided for clarity, some are retained to
  // illustrate how the interface properties are defined.
  identity other {
    base iana-interface-type;
    description
      "None of the following";
  }

  identity ethernetCsmacd {
    base iana-interface-type;
    base ianaifp:physical;
    base ianaifp:multicast;
    base ianaifp:ethernet-like;
    description
      "For all Ethernet-like interfaces, regardless of speed,
       as per RFC 3635.";
    reference
      "RFC 3635 - Definitions of Managed Objects for the
                  Ethernet-like Interface Types";
  }

  identity ieee8023adLag {
    base iana-interface-type;
    base ianaifp:virtual;
    base ianaifp:multicast;
    base ianaifp:ethernet-like;
    description
      "IEEE 802.3ad Link Aggregate.";
  }

  identity atm {
    base iana-interface-type;
    base ianaifp:physical;
    base ianaifp:multicast;
    description
      "ATM cells.";
  }

  identity atmSubInterface {
    base iana-interface-type;
    base ianaifp:virtual;
    base ianaifp:sub-interface;
    base ianaifp:multicast;
    description
      "ATM Sub Interface.";
  }

  identity l2vlan {
    base iana-interface-type;
    base ianaifp:virtual;
    base ianaifp:sub-interface;
    base ianaifp:multicast;
    description
      "Layer 2 Virtual LAN using 802.1Q.";
  }

  identity pos {
    base iana-interface-type;
    base ianaifp:point-to-point;
    description
      "Packet over SONET/SDH Interface.";
  }

  identity irb {
    base iana-interface-type;
    base ianaifp:virtual;
    base ianaifp:multicast;
    base ianaifp:ethernet-like;

    description
      "Integrated Routing and Bridging interface, also known as an
       SVI or BVI interface.

       Note, not currently defined in if-type.yang";
  }
}
