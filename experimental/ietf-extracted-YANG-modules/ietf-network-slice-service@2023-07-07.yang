module ietf-network-slice-service {
  yang-version 1.1;
  namespace
    "urn:ietf:params:xml:ns:yang:ietf-network-slice-service";
  prefix ietf-nss;

  import ietf-inet-types {
    prefix inet;
    reference
      "RFC 6991: Common YANG Types";
  }
  import ietf-vpn-common {
    prefix vpn-common;
    reference
      "RFC 9181: A Common YANG Data Model for Layer 2 and Layer 3
                 VPNs";
  }
  import ietf-network {
    prefix nw;
    reference
      "RFC 8345: A YANG Data Model for Network Topologies";
  }
  import ietf-network-topology {
    prefix nt;
    reference
      "RFC 8345: A YANG Data Model for Network
                 Topologies, Section 6.2";
  }

  /* Import TE Types */

  import ietf-te-types {
    prefix te-types;
    reference
      "RFC 8776: Common YANG Data Types for Traffic Engineering";
  }
  import ietf-te-packet-types {
    prefix te-packet-types;
    reference
      "RFC 8776: Common YANG Data Types for Traffic Engineering";
  }

  organization
    "IETF Traffic Engineering Architecture and Signaling (TEAS)
     Working Group";
  contact
    "WG Web:  <https://tools.ietf.org/wg/teas/>
     WG List:  <mailto:teas@ietf.org>

     Editor: Bo Wu
          <lana.wubo@huawei.com>
     Editor: Dhruv Dhody
          <dhruv.ietf@gmail.com>
     Editor: Reza Rokui
          <reza.rokui@nokia.com>
     Editor: Tarek Saad
          <tsaad@cisco.com>
     Author: Liuyan Han
          <hanliuyan@chinamobile.com>
     Editor: John Mullooly
          <jmullool@cisco.com>";
  description
    "This module defines a model for the IETF Network Slice Service.

        Copyright (c) 2023 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

     This version of this YANG module is part of RFC XXXX; see the
     RFC itself for full legal notices.";

  revision 2023-07-07 {
    description
      "Initial revision.";
    reference
      "RFC XXXX: A YANG Data Model for the IETF Network Slice Service";
  }

  /* Features */
  /* Identities */

  identity service-tag-type {
    description
      "Base identity for IETF Network Slice Service tag type.";
  }

  identity service-tag-customer {
    base service-tag-type;
    description
      "The IETF Network Slice Service customer ID tag type.";
  }

  identity service-tag-service {
    base service-tag-type;
    description
      "The IETF Network Slice Service tag type,e.g. L2 or L3
       service.";
  }

  identity service-tag-opaque {
    base service-tag-type;
    description
      "The IETF Network Slice Service opaque tag type.";
  }

  identity attachment-circuit-tag-type {
    description
      "Base identity for the attachment circuit tag type.";
  }

  identity attachment-circuit-tag-vlan-id {
    base attachment-circuit-tag-type;
    description
      "The attachment circuit VLAN ID tag type. e.g. dot1Q or QinQ
       VLAN IDs.";
  }

  identity attachment-circuit-tag-ip-mask {
    base attachment-circuit-tag-type;
    description
      "The attachment circuit tag IP mask.";
  }

  identity service-isolation-type {
    description
      "Base identity for IETF Network Slice Service isolation type.";
  }

  identity service-traffic-isolation {
    base service-isolation-type;
    description
      "Specify the requirement for separating the traffic of the
       customer's IETF Network Slice Service from other services,
       which may be provided by the service provider using VPN
       technologies, such as L3VPN, L2VPN, EVPN, etc.";
  }

  identity service-security-type {
    description
      "Base identity for IETF Network Slice Service security type.";
  }

  identity service-security-authenticate {
    base service-security-type;
    description
      "Indicates the slice service requires authentication.";
  }

  identity service-security-integrity {
    base service-security-type;
    description
      "Indicates the slice service requires data integrity.";
  }

  identity service-security-encryption {
    base service-security-type;
    description
      "Indicates the slice service requires data encryption.";
  }

  identity point-to-point {
    base vpn-common:vpn-topology;
    description
      "Identity for point-to-point IETF Network Slice
       Service connectivity.";
  }

  identity point-to-multipoint {
    base vpn-common:vpn-topology;
    description
      "Identity for point-to-multipoint IETF Network Slice
       Service connectivity.";
  }

  identity multipoint-to-multipoint {
    base vpn-common:vpn-topology;
    description
      "Identity for multipoint-to-multipoint IETF Network Slice
       Service connectivity.";
  }
  identity multipoint-to-point {
    base vpn-common:vpn-topology;
    description
      "Identity for multipoint-to-point IETF Network Slice
       Service connectivity.";
  }

  identity sender-role {
    base vpn-common:role;
    description
      "An SDP is acting as a sender.";
  }

  identity receiver-role {
    base vpn-common:role;
    description
      "An SDP is acting as a receiver.";
  }

  identity service-slo-metric-type {
    description
      "Base identity for IETF Network Slice Service SLO metric type.";
  }

  identity service-slo-one-way-bandwidth {
    base service-slo-metric-type;
    description
      "SLO bandwidth metric. Minimum guaranteed bandwidth between
       two SDPs at any time and is measured unidirectionally.";
  }

  identity service-slo-two-way-bandwidth {
    base service-slo-metric-type;
    description
      "SLO bandwidth metric. Minimum guaranteed bandwidth between
       two SDPs at any time.";
  }

  identity service-slo-shared-bandwidth {
    base service-slo-metric-type;
    description
      "The shared SLO bandwidth bound. It is the limit on the
       bandwidth that can be shared amongst a group of
       connectivity constructs of a slice service.";
  }

  identity service-slo-one-way-delay-maximum {
    base service-slo-metric-type;
    description
      "The SLO objective of this metric is the upper bound of network
       delay when transmitting between two SDPs.
       The metric is defined in RFC7679.";
  }

  identity service-slo-one-way-delay-percentile {
    base service-slo-metric-type;
    description
      "The SLO objective of this metric is percentile objective of
       network delay when transmitting between two SDPs.
       The metric is defined in RFC7679.";
  }

  identity service-slo-two-way-delay-maximum {
    base service-slo-metric-type;
    description
      "SLO two-way delay is the upper bound of network delay when
       transmitting between two SDPs.
       The metric is defined in RFC2681.";
  }

  identity service-slo-two-way-delay-percentile {
    base service-slo-metric-type;
    description
      "The SLO objective of this metric is the percentile
       objective of network delay when the traffic transmitting
       between two SDPs.
       The metric is defined in RFC2681.";
  }

  identity service-slo-one-way-delay-variation-maximum {
    base service-slo-metric-type;
    description
      "The SLO objective of this metric is maximum bound of the
       difference in the one-way delay between sequential packets
       between two SDPs.
       The metric of one-way delay variation is defined in RFC3393.";
  }

  identity service-slo-one-way-delay-variation-percentile {
    base service-slo-metric-type;
    description
      "The SLO objective of this metric is the percentile objective
       in the one-way delay between sequential packets between two
       SDPs.
       One-way delay variation percentile is defined by RFC3393.";
  }
  identity service-slo-two-way-delay-variation-maximum {
    base service-slo-metric-type;
    description
      "SLO two-way delay variation defined by RFC5481, is the
       difference in the round-trip delay between sequential packets
       between two SDPs.";
  }

  identity service-slo-two-way-delay-variation-percentile {
    base service-slo-metric-type;
    description
      "The delay variation percentile is defined by RFC5481.
       The SLO objective of this metric is the percentile objective
       in the round-trip delay between sequential packets between
       two SDPs.";
  }

  identity service-slo-one-way-packet-loss {
    base service-slo-metric-type;
    description
      "SLO loss metric. The ratio of packets dropped to packets
       transmitted between two SDPs in one-way
       over a period of time as specified in RFC7680.";
  }

  identity service-slo-two-way-packet-loss {
    base service-slo-metric-type;
    description
      "SLO loss metric. The ratio of packets dropped to packets
       transmitted between two SDPs in two-way
       over a period of time as specified in RFC7680.";
  }

  identity service-match-type {
    description
      "Base identity for IETF Network Slice Service traffic
       match type.";
  }

  /*
   * Identity for availability-type
   */

  identity availability-type {
    description
      "Base identity from which specific availability types are
       derived.";
  }
  identity level-1 {
    base availability-type;
    description
      "level 1: 99.9999%";
  }

  identity level-2 {
    base availability-type;
    description
      "level 2: 99.999%";
  }

  identity level-3 {
    base availability-type;
    description
      "level 3: 99.99%";
  }

  identity level-4 {
    base availability-type;
    description
      "level 4: 99.9%";
  }

  identity level-5 {
    base availability-type;
    description
      "level 5: 99%";
  }

  identity service-phy-interface-match {
    base service-match-type;
    description
      "Use the physical interface as match criteria for
       slice service traffic.";
  }

  identity service-vlan-match {
    base service-match-type;
    description
      "Use the VLAN ID as match criteria for the slice service
       traffic.";
  }

  identity service-label-match {
    base service-match-type;
    description
      "Use the MPLS label as match criteria for the slice service
       traffic.";
  }

  identity service-source-ip-prefix-match {
    base service-match-type;
    description
      "Use source ip prefix as match criteria for the slice service
       traffic. Examples of 'value' of this match type is
       '192.0.2.0/24' and '2001:db8::1/64'.";
  }

  identity service-destination-ip-prefix-match {
    base service-match-type;
    description
      "Use destination ip prefix as match criteria for the slice
       service traffic. Examples of 'value' of this match type is
       '203.0.113.1/32', '2001:db8::2/128'.";
  }

  identity service-dscp-match {
    base service-match-type;
    description
      "Use DSCP in the IP packet header as match criteria
       for the slice service traffic.";
  }

  identity service-acl-match {
    base service-match-type;
    description
      "Use Access Control List (ACL) as match criteria
       for the slice service traffic.";
    reference
      "RFC 8519: YANG Data Model for
       Network Access Control Lists (ACLs)";
  }

  identity service-any-match {
    base service-match-type;
    description
      "Match all slice service traffic.";
  }

  identity slo-sle-policy-override {
    description
      "Base identity for SLO/SLE policy override options.";
  }

  identity slo-sle-policy-full-override {
    base slo-sle-policy-override;
    description
      "The policy of SLO/SLE(s) that is defined at a
       child level override a parent SLO/SLE policy,
       which means that no SLO/SLE(s) are inherited from parent
       if a child SLO/SLE policy exists.";
  }

  identity slo-sle-policy-partial-override {
    base slo-sle-policy-override;
    description
      "The policy of SLO/SLE(s) that is defined at a
       child level updates the parent SLO/SLE policy.
       For example, if a specific SLO is defined
       at the child level, that specific SLO overrides the
       one inherited from a parent SLO/SLE policy, while all other
       SLOs in the parent SLO-SLE policy still apply.";
  }

  /* typedef */

  typedef percentile {
    type decimal64 {
      fraction-digits 3;
      range "0..100";
    }
    description
      "The percentile is a value between 0 and 100
       to 3 decimal places, e.g. 10.000, 99.900 ,99.990, etc.
       For example, for a given one-way delay measurement,
       if the percentile is set to 95.000 and the 95th percentile
       one-way delay is 2 milliseconds, then the 95 percent of
       the sample value is less than or equal to 2 milliseconds.";
  }

  /* grouping */

  grouping service-slos {
    description
      "Directly Measurable Objectives of a slice service.";
    container slo-policy {
      description
        "Contains the SLO policy.";
      list metric-bound {
        key "metric-type";
        description
          "List of slice service metric bounds.";
        leaf metric-type {
          type identityref {
            base service-slo-metric-type;
          }
          description
            "Identifies an entry in the list of metric type
             bounds for the slice service.";
        }
        leaf metric-unit {
          type string;
          mandatory true;
          description
            "The metric unit of the parameter. For example,
             s, ms, ns, and so on.";
        }
        leaf value-description {
          type string;
          description
            "The description of previous value.";
        }
        leaf percentile-value {
          type percentile;
          description
            "The percentile value of the metric type.";
        }
        leaf bound {
          type uint64;
          default "0";
          description
            "The Bound on the slice service connection metric.
             A zero indicate an unbounded upper limit for the
             specific metric-type.";
        }
      }
      leaf availability {
        type identityref {
          base availability-type;
        }
        description
          "Service availability level";
      }
      leaf mtu {
        type uint16;
        units "bytes";
        description
          "The MTU specifies the maximum length in octets of data
           packets of the slice service.
           The value needs to be less than or equal to the
           minimum MTU value of all 'attachment-circuits'
           in the SDPs.";
      }
    }
  }

  grouping service-sles {
    description
      "Indirectly Measurable Objectives of a slice service.";
    container sle-policy {
      description
        "Contains the SLE policy.";
      leaf-list security {
        type identityref {
          base service-security-type;
        }
        description
          "The security functions that the customer requests
           the operator to apply to traffic between the two SDPs.";
      }
      leaf-list isolation {
        type identityref {
          base service-isolation-type;
        }
        description
          "The slice service isolation requirement.";
      }
      leaf max-occupancy-level {
        type uint8 {
          range "1..100";
        }
        description
          "The maximal occupancy level specifies the number of flows
           to be admitted.";
      }
      container steering-constraints {
        description
          "Container for the policy of steering constraints
           applicable to the slice service.";
        container path-constraints {
          description
            "Container for the policy of path constraints
             applicable to the slice service.";
        }
        container service-function {
          description
            "Container for the policy of service function
             applicable to the slice service.";
        }
      }
    }
  }

  grouping sdp-peering {
    description
      "A grouping for the slice service SDP peering.";
    container sdp-peering {
      description
        "Describes SDP peering attributes.";
      leaf peer-sap-id {
        type string;
        description
          "Indicates a reference to the remote endpoints of an
           attachment circuit. This information can be used for
           correlation purposes, such as identifying a service
           attachment point (SAP) of a provider equipment when
           requesting a service with CE based SDP attributes.";
      }
      container protocols {
        description
          "Serves as an augmentation target.
           Protocols can be augmented into this container,
           e.g. BGP, static routing.";
      }
    }
  }

  grouping sdp-attachment-circuits {
    description
      "Grouping for the SDP attachment circuit definition.";
    container attachment-circuits {
      description
        "List of attachment circuit.";
      list attachment-circuit {
        key "id";
        description
          "The IETF Network Slice service SDP attachment circuit
           related parameters.";
        leaf id {
          type string;
          description
            "Uniquely identifier a attachment circuit.";
        }
        leaf ac-svc-name {
          type string;
          description
            "Indicates an attachment circuit service name,
             for association purposes, to refer to an AC that has been
             created before the slice creation.
             This node can override 'ac-svc-name' of the parent SDP.";
        }
        leaf description {
          type string;
          description
            "The attachment circuit description.";
        }
        leaf ac-node-id {
          type string;
          description
            "The attachment circuit node ID in the case of
             multi-homing.";
        }
        leaf ac-tp-id {
          type string;
          description
            "The termination port ID of the attachment circuit.";
        }
        leaf ac-ipv4-address {
          type inet:ipv4-address;
          description
            "The IPv4 address of the AC.";
        }
        leaf ac-ipv4-prefix-length {
          type uint8;
          description
            "The IPv4 subnet prefix length expressed in bits.";
        }
        leaf ac-ipv6-address {
          type inet:ipv6-address;
          description
            "The IPv6 address of the AC.";
        }
        leaf ac-ipv6-prefix-length {
          type uint8;
          description
            "The IPv6 subnet prefix length expressed in bits.";
        }
        leaf mtu {
          type uint16;
          units "bytes";
          description
            "Maximum size in octets of the slice service data packet
             that can traverse an SDP.";
        }
        container ac-tags {
          description
            "Container for the attachment circuit tags.";
          list ac-tags {
            key "tag-type";
            description
              "The attachment circuit tags list.";
            leaf tag-type {
              type identityref {
                base attachment-circuit-tag-type;
              }
              description
                "The attachment circuit tag type.";
            }
            leaf-list value {
              type string;
              description
                "The attachment circuit tag values. For example, the
                 tag may indicate 'c-vlan' and 's-vlan'.";
            }
          }
        }
        /* Per ac rate limits */
        uses service-qos;
        uses sdp-peering;
        uses vpn-common:service-status;
      }
    }
  }

  grouping sdp-monitoring-metrics {
    description
      "Grouping for the SDP monitoring metrics.";
    container sdp-monitoring {
      config false;
      description
        "Container for SDP monitoring metrics.";
      leaf incoming-bw-value {
        type te-types:te-bandwidth;
        description
          "Indicates, in octets per second, incoming bandwidth at
           an SDP.";
      }
      leaf incoming-bw-percent {
        type decimal64 {
          fraction-digits 5;
          range "0..100";
        }
        units "percent";
        mandatory true;
        description
          "Indicates a percentage of the incoming bandwidth at
           an SDP.";
      }
      leaf outgoing-bw-value {
        type te-types:te-bandwidth;
        description
          "Indicates, in octets per second, outgoing bandwidth at
           an SDP.";
      }
      leaf outgoing-bw-percent {
        type decimal64 {
          fraction-digits 5;
          range "0..100";
        }
        units "percent";
        mandatory true;
        description
          "Indicates a percentage of the outgoing bandwidth at
           an SDP.";
      }
    }
  }

  grouping connectivity-construct-monitoring-metrics {
    description
      "Grouping for connectivity construct monitoring metrics.";
    uses te-packet-types:one-way-performance-metrics-packet;
    uses te-packet-types:two-way-performance-metrics-packet;
  }

  grouping geolocation-container {
    description
      "A grouping containing a GPS location.";
    container location {
      description
        "A container containing a GPS location.";
      leaf altitude {
        type int64;
        units "millimeter";
        description
          "Distance above the sea level.";
      }
      leaf latitude {
        type decimal64 {
          fraction-digits 8;
          range "-90..90";
        }
        description
          "Relative position north or south on the Earth's surface.";
      }
      leaf longitude {
        type decimal64 {
          fraction-digits 8;
          range "-180..180";
        }
        description
          "Angular distance east or west on the Earth's surface.";
      }
    }
    // gps-location
  }

  // geolocation-container

  grouping bw-rate-limits {
    description
      "Bandwidth rate limits grouping.";
    reference
      "RFC 7640: Traffic Management Benchmarking";
    leaf cir {
      type uint64;
      units "bps";
      description
        "Committed Information Rate. The maximum number of bits
         that a port can receive or send during one-second over an
         interface.";
    }
    leaf cbs {
      type uint64;
      units "bytes";
      description
        "Committed Burst Size. CBS controls the bursty nature
         of the traffic. Traffic that does not use the configured
         CIR accumulates credits until the credits reach the
         configured CBS.";
    }
    leaf eir {
      type uint64;
      units "bps";
      description
        "Excess Information Rate, i.e., excess frame delivery
         allowed not subject to SLA. The traffic rate can be
         limited by EIR.";
    }
    leaf ebs {
      type uint64;
      units "bytes";
      description
        "Excess Burst Size. The bandwidth available for burst
         traffic from the EBS is subject to the amount of
         bandwidth that is accumulated during periods when
         traffic allocated by the EIR policy is not used.";
    }
    leaf pir {
      type uint64;
      units "bps";
      description
        "Peak Information Rate, i.e., maximum frame delivery
         allowed. It is equal to or less than sum of CIR and EIR.";
    }
    leaf pbs {
      type uint64;
      units "bytes";
      description
        "Peak Burst Size.";
    }
  }

  grouping service-qos {
    description
      "The rate limits grouping.";
    container incoming-qos-policy {
      description
        "Container for the asymmetric traffic control.";
      leaf qos-policy-name {
        type string;
        description
          "The name of the QoS policy that is applied to the
           attachment circuit. The name can reference a QoS
           profile that is pre-provisioned on the device.";
      }
      container rate-limits {
        description
          "Container for the asymmetric traffic control.";
        uses bw-rate-limits;
      }
    }
    container outgoing-qos-policy {
      description
        "The QoS policy imposed on outgoing traffic.";
      leaf qos-policy-name {
        type string;
        description
          "The name of the QoS policy that is applied to the
           attachment circuit. The name can reference a QoS
           profile that is pre-provisioned on the device.";
      }
      container rate-limits {
        description
          "The rate-limit imposed on outgoing traffic.";
        uses bw-rate-limits;
      }
    }
  }

  grouping sdp {
    description
      "Slice service SDP related information";
    leaf id {
      type string;
      description
        "Unique identifier for the referred slice service SDP.";
    }
    leaf description {
      type string;
      description
        "Give more description of the SDP.";
    }
    uses geolocation-container;
    leaf node-id {
      type string;
      description
        "Uniquely identifies an edge node of the SDP.";
    }
    leaf-list sdp-ip-address {
      type inet:ip-address;
      description
        "IPv4 or IPv6 address of the SDP.";
    }
    leaf tp-ref {
      type leafref {
        path
          "/nw:networks/nw:network[nw:network-id =current()/../../"
        + "../custom-topology-ref/network-ref]/"
        + "nw:node/nt:termination-point/nt:tp-id";
      }
      description
        "A reference to Termination Point (TP) in the custom
         topology";
      reference
        "RFC 8345: A YANG Data Model for Network Topologies";
    }
    container service-match-criteria {
      description
        "Describes the slice service match criteria.";
      list match-criterion {
        key "index";
        description
          "List of the slice service traffic match criteria.";
        leaf index {
          type uint32;
          description
            "The entry index.";
        }
        leaf match-type {
          type identityref {
            base service-match-type;
          }
          mandatory true;
          description
            "Identifies an entry in the list of the slice service
             match criteria.";
        }
        leaf-list value {
          type string;
          description
            "Describes the slice service match criteria, e.g.
             IP prefix, VLAN, etc.";
        }
        leaf target-connection-group-id {
          type leafref {
            path "../../../../../ietf-nss:connection-groups"
               + "/ietf-nss:connection-group"
               + "/ietf-nss:id";
          }
          mandatory true;
          description
            "Reference to the slice service connection group.";
        }
        leaf connection-group-sdp-role {
          type identityref {
            base vpn-common:role;
          }
          default "vpn-common:any-to-any-role";
          description
            "Specifies the role of SDP in the connection group
             When the service connection type is MP2MP,
             such as hub and spoke service connection type. In addition,
             this helps to create connectivity construct automatically
             , rather than explicitly specifying each one.";
        }
        leaf target-connectivity-construct-id {
          type leafref {
            path "/ietf-nss:network-slice-services"
               + "/ietf-nss:slice-service"
               + "/ietf-nss:connection-groups"
               + "/ietf-nss:connection-group[id"
               + "=current()/../target-connection-group-id]"
               + "/ietf-nss:connectivity-construct/ietf-nss:id";
          }
          description
            "Reference to a Network Slice connection construct.";
        }
      }
    }
    uses service-qos;
    container sdp-peering {
      description
        "Describes SDP peering attributes.";
      leaf-list peer-sap-id {
        type string;
        description
          "Indicates the reference to the remote endpoints of the
           attachment circuits. This information can be used for
           correlation purposes, such as identifying service
           attachment points (SAPs) of provider equipments when
           requesting a service with CE based SDP attributes.";
      }
      container protocols {
        description
          "Serves as an augmentation target.
           Protocols can be augmented into this container,
           e.g. BGP, static routing.";
      }
    }
    leaf-list ac-svc-name {
      type string;
      description
        "Indicates the attachment circuit service name,
         for association purposes, to refer to ACs that have been
         created before the slice creation.";
    }
    uses sdp-attachment-circuits;
    uses vpn-common:service-status;
    uses sdp-monitoring-metrics;
  }
  //service-sdp

  grouping connectivity-construct {
    description
      "Grouping for slice service connectivity construct.";
    list connectivity-construct {
      key "id";
      description
        "List of connectivity constructs.";
      leaf id {
        type uint32;
        description
          "The connectivity construct identifier.";
      }
      choice type {
        default "p2p";
        description
          "Choice for connectivity construct type.";
        case p2p {
          description
            "P2P connectivity construct.";
          leaf p2p-sender-sdp {
            type leafref {
              path "../../../../sdps/sdp/id";
            }
            description
              "Reference to a sender SDP.";
          }
          leaf p2p-receiver-sdp {
            type leafref {
              path "../../../../sdps/sdp/id";
            }
            description
              "Reference to a receiver SDP.";
          }
        }
        case p2mp {
          description
            "P2MP connectivity construct.";
          leaf p2mp-sender-sdp {
            type leafref {
              path "../../../../sdps/sdp/id";
            }
            description
              "Reference to a sender SDP.";
          }
          leaf-list p2mp-receiver-sdp {
            type leafref {
              path "../../../../sdps/sdp/id";
            }
            description
              "Reference to a receiver SDP.";
          }
        }
        case a2a {
          description
            "A2A connectivity construct.";
          list a2a-sdp {
            key "sdp-id";
            description
              "List of included A2A SDPs.";
            leaf sdp-id {
              type leafref {
                path "../../../../../sdps/sdp/id";
              }
              description
                "Reference to an SDP.";
            }
            uses service-slo-sle-policy;
          }
        }
      }
      uses service-slo-sle-policy;
      /* Per connectivity construct service-slo-sle-policy
       * overrides the per slice service-slo-sle-policy.
       */
      uses service-slo-sle-policy-override;
      uses vpn-common:service-status;
      container connectivity-construct-monitoring {
        config false;
        description
          "SLO status per connectivity construct.";
        uses connectivity-construct-monitoring-metrics;
      }
    }
  }

  //connectivity-construct

  grouping connection-group {
    description
      "Grouping for slice service connection group.";
    leaf id {
      type string;
      description
        "The connection group identifier.";
    }
    leaf connectivity-type {
      type identityref {
        base vpn-common:vpn-topology;
      }
      default "vpn-common:any-to-any";
      description
        "Connection group connectivity type.";
    }
    uses service-slo-sle-policy;
    uses service-slo-sle-policy-override;
    uses connectivity-construct;
    /* Per connection group service-slo-sle-policy overrides
     * the per slice service-slo-sle-policy.
     */
    container connection-group-monitoring {
      config false;
      description
        "SLO status per connection group.";
      uses connectivity-construct-monitoring-metrics;
    }
  }

  //connection-group

  grouping slice-service-template {
    description
      "Grouping for slice service templates.";
    container slo-sle-templates {
      description
        "Contains a set of slice service templates.";
      list slo-sle-template {
        key "id";
        description
          "List for SLO and SLE template identifiers.";
        leaf id {
          type string;
          description
            "Identification of the Service Level Objective (SLO)
             and Service Level Expectation (SLE) template to be used.
             Local administration meaning.";
        }
        leaf description {
          type string;
          description
            "Description of the SLO and SLE policy template.";
        }
        leaf template-ref {
          type leafref {
            path "/ietf-nss:network-slice-services"
               + "/ietf-nss:slo-sle-templates"
               + "/ietf-nss:slo-sle-template"
               + "/ietf-nss:id";
          }
          description
            "The reference to a standard template. When set it
              indicates the base template over which further
              SLO/SLE policy changes are made.";
        }
        uses service-slos;
        uses service-sles;
      }
    }
  }

  /* Configuration data nodes */

  grouping service-slo-sle-policy {
    description
      "Slice service policy grouping.";
    choice slo-sle-policy {
      description
        "Choice for SLO and SLE policy template.
         Can be standard template or customized template.";
      case standard {
        description
          "Standard SLO template.";
        leaf slo-sle-template {
          type leafref {
            path "/ietf-nss:network-slice-services"
               + "/ietf-nss:slo-sle-templates"
               + "/ietf-nss:slo-sle-template"
               + "/ietf-nss:id";
          }
          description
            "Standard SLO and SLE template to be used.";
        }
      }
      case custom {
        description
          "Customized SLO and SLE template.";
        container service-slo-sle-policy {
          description
            "Contains the SLO and SLE policy.";
          leaf description {
            type string;
            description
              "Description of the SLO and SLE policy.";
          }
          uses service-slos;
          uses service-sles;
        }
      }
    }
  }

  grouping service-slo-sle-policy-override {
    description
      "Slice service policy override grouping.";
    leaf service-slo-sle-policy-override {
      type identityref {
        base slo-sle-policy-override;
      }
      default "ietf-nss:slo-sle-policy-full-override";
      description
        "SLO/SLE policy override option.";
    }
  }

  container network-slice-services {
    description
      "Contains a list of IETF network slice services";
    uses slice-service-template;
    list slice-service {
      key "id";
      description
        "A slice service is identified by a service id.";
      leaf id {
        type string;
        description
          "A unique slice service identifier.";
      }
      leaf description {
        type string;
        description
          "Textual description of the slice service.";
      }
      container service-tags {
        description
          "Container for the list of service tags.";
        list tag-type {
          key "tag-type";
          description
            "The service tag list.";
          leaf tag-type {
            type identityref {
              base service-tag-type;
            }
            description
              "Slice service tag type.";
          }
          leaf-list value {
            type string;
            description
              "The tag values, e.g. customer names when multiple
               customers sharing same slice service in 5G scenario.";
          }
        }
      }
      uses service-slo-sle-policy;
      leaf compute-only {
        type empty;
        description
          "When present, the slice is computed. No resources are
           committed or reserved in the network.";
      }
      uses vpn-common:service-status;
      container sdps {
        description
          "Slice service SDPs.";
        list sdp {
          key "id";
          min-elements 2;
          uses sdp;
          description
            "List of SDPs in this slice service.";
        }
      }
      container connection-groups {
        description
          "Contains connections group.";
        list connection-group {
          key "id";
          description
            "List of connection groups.";
          uses connection-group;
        }
      }
      container custom-topology-ref {
        description
          "Container for the custom topology reference.";
        uses nw:network-ref;
      }
    }
    //ietf-network-slice-service list
  }
}
