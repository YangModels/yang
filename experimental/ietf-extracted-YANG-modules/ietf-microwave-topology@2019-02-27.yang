module ietf-microwave-topology {
 yang-version 1.1;
  namespace "urn:ietf:params:xml:ns:yang:ietf-microwave-topology";

  prefix "mwtopo";

  import ietf-network {
    prefix "nw";
        reference "RFC 8345: A YANG Data Model for Network
               Topologies";
  }

  import ietf-network-topology {
    prefix "nt";
        reference "RFC 8345: A YANG Data Model for Network Topologies";
  }

// Note to RFC Editor:  please replace YYYY with the number assigned
// to draft-ietf-teas-yang-te-topo
  import ietf-te-topology {
    prefix "tet";
        reference "RFC xxxx: YANG Data Model for Traffic Engineering
                  (TE) Topologies";
  }

/*
 *import ietf-routing-types {
 * prefix "rt-types";
 * }
 */

  import ietf-yang-schema-mount {
       prefix yangmnt;
       reference "RFC 8528: YANG Schema Mount";
     }

 organization
  "Internet Engineering Task Force (IETF) CCAMP WG";
 contact
  "
  WG List: <mailto:ccamp@ietf.org>

  Editor: Min Ye
          <mailto:amy.yemin@huawei.com>
  Editor: Aihua Guo
          <mailto:aihuaguo@huawei.com>
  Editor: Jonas Ahlberg
          <mailto:jonas.ahlberg@ericsson.com>
  Editor: Xi Li
          <mailto:Xi.Li@neclab.eu>
  Editor: Daniela Spreafico
          <mailto:daniela.spreafico@nokia.com>";

// Note to RFC Editor: replace XXXX with actual RFC number and
// remove this note.
 description
  "This is a module for microwave topology.
  Copyright (c) 2019 IETF Trust and the persons identified as
  authors of the code.  All rights reserved.
  Redistribution and use in source and binary forms, with or
  without modification, is permitted pursuant to, and subject to
  the license terms contained in, the Simplified BSD License set
  forth in Section 4.c of the IETF Trust's Legal Provisions
  Relating to IETF Documents
  (http://trustee.ietf.org/license-info).
  This version of this YANG module is part of RFC XXXX
  (https://tools.ietf.org/html/rfcXXXX); see the RFC itself for
  full legal notices.";

  revision 2019-02-27 {
    description
    "Update microwave link key.";
    reference "";
  }

  revision 2019-01-03 {
    description
    "Align with the TE topology YANG model.";
    reference "";
  }

  revision 2018-10-22 {
    description
    "change the type of serveral data nodes.";
    reference "";
  }

   revision 2018-06-30 {
    description
    "Updated version to add mount point to the interface model.";
    reference "";
  }

   revision 2018-03-05 {
    description
    "Initial version.";
    reference "";
  }

   feature root-radio-if{
    description
        "This feature means that root for microwave radio
     interface model is supported.";
   }

  /*
   * Groupings
   */
   grouping mw-bandwidth {
    description "Microwave bandwidth attributes";
    leaf mw-bandwidth {
      type uint64;
      units "Kbps";
      config false;
      description "Microwave nominal bandwidth. Calcualtion
      of microwave nominal bandwidth is implementation specific.
      For example, if there's only one channel in the mw-channels
      list, the microwave nominal bandwidth is equal to the
      channel bandwidth. If there's two channels in the mw-channels
      list, depending on the configuration of the channels, the
      microwave nominal bandwidth is the sum of channel
      bandwidth(2+0), or just one channel bandwidth
      (1+1 with protection).";
    }

        leaf mw-unreserved-bandwidth {
           type uint64;
           units "Kbps";
           config false;
           description "The unreserved bandwidth of the link is
                    mw-bandwidth minus occupied bandwidth
                    on mw link";
           }
  }

  grouping mw-link-attributes {
    description "Microwave link attributes.";
        list mw-channels {
          key "mw-channel-frequency mw-channel-id";
          description "List of microwave channels supporting the link.";
          uses mw-channel-attributes;
        }
  }

  grouping mw-channel-attributes {
    description "Microwave channel attributes";

    leaf mw-channel-id {
      type string;
      description "Microwave channel identifier";
    }

    leaf mw-channel-frequency {
      type uint32;
      units "kHz";
      description "Microwave channel frequency";
    }

    leaf mw-channel-separation {
      type uint32;
      units "kHz";
      description
            "The distance between adjacent channels
             in a radio frequency channel arrangement
                 used in this link";
      reference "ETSI EN 302 217-1";
    }

    leaf mw-channel-nominal-bandwidth {
      type uint64;
      units "Kbps";
      config false;
      description "The nominal channel bandwidth";
    }

    leaf mw-channel-current-bandwidth {
      type uint64;
      units "Kbps";
      config false;
      description "The current channel bandwidth";
    }

    list mw-channel-availability{
      key "availability";
      description
            "List of availability and corresponding
         channel bandwidth";

      leaf availability {
        type decimal64 {
          fraction-digits 4;
          range "0..99.9999";
        }
        description "Availability level";
      }

      leaf channel-bandwidth {
        type uint64;
        units "Kbps";
        config false;
        description
              "The channel bandwidth corresponding
           to the availability level";
      }
    }

        container "interface-root" {
      if-feature root-radio-if;
      description
        "Container for mount point.";
      yangmnt:mount-point "interface-root" {
        description
          "Root for microwave radio interface model.
           It could contain an interface instance.";
      }
    }
  }

  /*
   * Data nodes
   */
   augment "/nw:networks/nw:network/nw:network-types/"
        + "tet:te-topology" {
    container mw-topology {
      presence "indicates a topology type of microwave.";
      description "Microwave topology type";
    }
    description "augment network types to include microwave network";
  }

  augment "/nw:networks/nw:network/nt:link/tet:te/"
        + "tet:te-link-attributes" {
    when "../../../nw:network-types/tet:te-topology/"
       + "mwtopo:mw-topology" {
      description "This augment is only valid for microwave.";
    }
    description "Microwave link augmentation";

    uses mw-link-attributes;
  }

   /*
   * Augment TE bandwidth
   */

  /* Augment maximum LSP bandwidth of link terminationpoint (LTP) */
  augment "/nw:networks/nw:network/nw:node/nt:termination-point/"
        + "tet:te/"
        + "tet:interface-switching-capability/tet:max-lsp-bandwidth/"
        + "tet:te-bandwidth/tet:technology" {
    when "../../../../../../nw:network-types/tet:te-topology/"
       + "mwtopo:mw-topology" {
      description "Augment microwave TE bandwidth";
    }
    description "microwave bandwidth.";
    case mw {
      uses mw-bandwidth;
    }
  }
  /* Augment bandwidth path constraints of connectivity-matrices */
  augment "/nw:networks/nw:network/nw:node/tet:te/"
        + "tet:te-node-attributes/tet:connectivity-matrices/"
        + "tet:path-constraints/tet:te-bandwidth/tet:technology" {
    when "../../../../../../nw:network-types/tet:te-topology/"
       + "mwtopo:mw-topology" {
      description "Augment microwave TE bandwidth";
    }
    description "microwave bandwidth.";
    case mw {
      uses mw-bandwidth;
    }
  }

  /* Augment bandwidth path constraints of connectivity-matrix */
  augment "/nw:networks/nw:network/nw:node/tet:te/"
        + "tet:te-node-attributes/tet:connectivity-matrices/"
        + "tet:connectivity-matrix/"
        + "tet:path-constraints/tet:te-bandwidth/tet:technology" {
    when "../../../../../../../nw:network-types/tet:te-topology/"
       + "mwtopo:mw-topology" {
      description "Augment microwave TE bandwidth";
    }
    description "microwave bandwidth.";
    case mw {
      uses mw-bandwidth;
    }
  }

  /* Augment bandwidth path constraints of connectivity-matrices
   * information-source */
  augment "/nw:networks/nw:network/nw:node/tet:te/"
        + "tet:information-source-entry/tet:connectivity-matrices/"
        + "tet:path-constraints/tet:te-bandwidth/tet:technology" {
    when "../../../../../../nw:network-types/tet:te-topology/"
       + "mwtopo:mw-topology" {
      description "Augment microwave TE bandwidth";
    }
    description "microwave bandwidth.";
    case mw {
      uses mw-bandwidth;
    }
  }

  /* Augment bandwidth path constraints of connectivity-matrix
   * information-source */
  augment "/nw:networks/nw:network/nw:node/tet:te/"
        + "tet:information-source-entry/tet:connectivity-matrices/"
        + "tet:connectivity-matrix/"
        + "tet:path-constraints/tet:te-bandwidth/tet:technology" {
    when "../../../../../../../nw:network-types/tet:te-topology/"
       + "mwtopo:mw-topology" {
      description "Augment microwave TE bandwidth";
    }
    description "microwave bandwidth.";
    case mw {
      uses mw-bandwidth;
    }
  }

  /* Augment client bandwidth of tunnel termination point (TTP) */
  augment "/nw:networks/nw:network/nw:node/tet:te/"
        + "tet:tunnel-termination-point/"
        + "tet:client-layer-adaptation/tet:switching-capability/"
        + "tet:te-bandwidth/tet:technology" {
    when "../../../../../../nw:network-types/tet:te-topology/"
       + "mwtopo:mw-topology" {
      description "Augment microwave TE bandwidth";
    }
    description "microwave bandwidth.";
    case mw {
      uses mw-bandwidth;
    }
   }

  /* Augment bandwidth path constraints of local-link-connectivities */
  augment "/nw:networks/nw:network/nw:node/tet:te/"
        + "tet:tunnel-termination-point/"
        + "tet:local-link-connectivities/tet:path-constraints/"
        + "tet:te-bandwidth/tet:technology" {
    when "../../../../../../nw:network-types/tet:te-topology/"
       + "mwtopo:mw-topology" {
      description "Augment microwave TE bandwidth";
    }
    description "microwave bandwidth.";
    case mw {
      uses mw-bandwidth;
    }
   }

  /* Augment bandwidth path constraints of
  *local-link-connectivity (LLC) */
  augment "/nw:networks/nw:network/nw:node/tet:te/"
        + "tet:tunnel-termination-point/"
        + "tet:local-link-connectivities/"
        + "tet:local-link-connectivity/tet:path-constraints/"
        + "tet:te-bandwidth/tet:technology" {
    when "../../../../../../../nw:network-types/tet:te-topology/"
       + "mwtopo:mw-topology" {
      description "Augment microwave TE bandwidth";
    }
    description "microwave bandwidth.";
    case mw {
      uses mw-bandwidth;
    }
  }

  /* Augment maximum LSP bandwidth of TE link */
  augment "/nw:networks/nw:network/nt:link/tet:te/"
        + "tet:te-link-attributes/"
        + "tet:interface-switching-capability/tet:max-lsp-bandwidth/"
        + "tet:te-bandwidth/tet:technology" {
    when "../../../../../../nw:network-types/tet:te-topology/"
       + "mwtopo:mw-topology" {
      description "Augment microwave TE bandwidth";
    }
    description "microwave bandwidth.";
    case mw {
      uses mw-bandwidth;
    }
  }

  /* Augment maximum bandwidth of TE link */
  augment "/nw:networks/nw:network/nt:link/tet:te/"
        + "tet:te-link-attributes/"
        + "tet:max-link-bandwidth/"
        + "tet:te-bandwidth/tet:technology" {
    when "../../../../../nw:network-types/tet:te-topology/"
       + "mwtopo:mw-topology" {
      description "Augment microwave TE bandwidth";
    }
    description "microwave bandwidth.";
    case mw {
      uses mw-bandwidth;
    }
  }

  /* Augment maximum reservable bandwidth of TE link */
  augment "/nw:networks/nw:network/nt:link/tet:te/"
        + "tet:te-link-attributes/"
        + "tet:max-resv-link-bandwidth/"
        + "tet:te-bandwidth/tet:technology" {
    when "../../../../../nw:network-types/tet:te-topology/"
       + "mwtopo:mw-topology" {
      description "Augment microwave TE bandwidth";
    }
    description "microwave bandwidth.";
    case mw {
      uses mw-bandwidth;
    }
  }

  /* Augment unreserved bandwidth of TE Link */
  augment "/nw:networks/nw:network/nt:link/tet:te/"
        + "tet:te-link-attributes/"
        + "tet:unreserved-bandwidth/"
        + "tet:te-bandwidth/tet:technology" {
    when "../../../../../nw:network-types/tet:te-topology/"
       + "mwtopo:mw-topology" {
      description "Augment microwave TE bandwidth";
    }
    description "microwave bandwidth.";
    case mw {
      uses mw-bandwidth;
    }
  }
  /* Augment maximum LSP bandwidth of TE link information-source */
  augment "/nw:networks/nw:network/nt:link/tet:te/"
        + "tet:information-source-entry/"
        + "tet:interface-switching-capability/"
        + "tet:max-lsp-bandwidth/"
        + "tet:te-bandwidth/tet:technology" {
    when "../../../../../../nw:network-types/tet:te-topology/"
       + "mwtopo:mw-topology" {
      description "Augment microwave TE bandwidth";
    }
    description "microwave bandwidth.";
    case mw {
      uses mw-bandwidth;
    }
  }

  /* Augment maximum bandwidth of TE link information-source */
  augment "/nw:networks/nw:network/nt:link/tet:te/"
        + "tet:information-source-entry/"
        + "tet:max-link-bandwidth/"
        + "tet:te-bandwidth/tet:technology" {
    when "../../../../../nw:network-types/tet:te-topology/"
       + "mwtopo:mw-topology" {
      description "Augment microwave TE bandwidth";
    }
    description "microwave bandwidth.";
    case mw {
      uses mw-bandwidth;
    }
  }

  /* Augment maximum reservable bandwidth of TE link
   * information-source */
  augment "/nw:networks/nw:network/nt:link/tet:te/"
        + "tet:information-source-entry/"
        + "tet:max-resv-link-bandwidth/"
        + "tet:te-bandwidth/tet:technology" {
    when "../../../../../nw:network-types/tet:te-topology/"
       + "mwtopo:mw-topology" {
      description "Augment microwave TE bandwidth";
    }
    description "microwave bandwidth.";
    case mw {
      uses mw-bandwidth;
    }
  }

  /* Augment unreserved bandwidth of TE link information-source */
  augment "/nw:networks/nw:network/nt:link/tet:te/"
        + "tet:information-source-entry/"
        + "tet:unreserved-bandwidth/"
        + "tet:te-bandwidth/tet:technology" {
    when "../../../../../nw:network-types/tet:te-topology/"
       + "mwtopo:mw-topology" {
      description "Augment microwave TE bandwidth";
    }
    description "microwave bandwidth.";
    case mw {
      uses mw-bandwidth;
    }
  }

  /* Augment maximum LSP bandwidth of TE link template */
  augment "/nw:networks/tet:te/tet:templates/"
        + "tet:link-template/tet:te-link-attributes/"
        + "tet:interface-switching-capability/"
        + "tet:max-lsp-bandwidth/"
        + "tet:te-bandwidth/tet:technology" {
    description "microwave bandwidth.";
    case mw {
      uses mw-bandwidth;
    }
  }

  /* Augment maximum bandwidth of TE link template */
  augment "/nw:networks/tet:te/tet:templates/"
        + "tet:link-template/tet:te-link-attributes/"
        + "tet:max-link-bandwidth/"
        + "tet:te-bandwidth/tet:technology" {
    description "microwave bandwidth.";
    case mw {
      uses mw-bandwidth;
    }
  }

  /* Augment maximum reservable bandwidth of TE link template */
  augment "/nw:networks/tet:te/tet:templates/"
        + "tet:link-template/tet:te-link-attributes/"
        + "tet:max-resv-link-bandwidth/"
        + "tet:te-bandwidth/tet:technology" {
    description "microwave bandwidth.";
    case mw {
      uses mw-bandwidth;
    }
  }

  /* Augment unreserved bandwidth of TE link template */
  augment "/nw:networks/tet:te/tet:templates/"
        + "tet:link-template/tet:te-link-attributes/"
        + "tet:unreserved-bandwidth/"
        + "tet:te-bandwidth/tet:technology" {
    description "microwave bandwidth.";
    case mw {
      uses mw-bandwidth;
    }
  }

 }
