module ietf-tcp {
  yang-version "1.1";
  namespace "urn:ietf:params:xml:ns:yang:ietf-tcp";
  prefix "tcp";

  import ietf-yang-types {
    prefix "yang";
    reference
      "RFC 6991: Common YANG Data Types.";
  }
  import ietf-tcp-common {
    prefix "tcpcmn";
    reference
      "I-D.ietf-netconf-tcp-client-server: YANG Groupings for TCP
       Clients and TCP Servers.";
  }
  import ietf-inet-types {
    prefix "inet";
    reference
      "RFC 6991: Common YANG Data Types.";
  }
  import ietf-netconf-acm {
    prefix nacm;
    reference
      "RFC 8341: Network Configuration Access Control Model";
  }
  import ietf-key-chain {
    prefix key-chain;
    reference
      "RFC 8177: YANG Key Chain.";
  }

  organization
    "IETF TCPM Working Group";

  contact
    "WG Web:   <https://datatracker.ietf.org/wg/tcpm/about>
     WG List:  <tcpm@ietf.org>

     Authors: Michael Scharf (michael.scharf at hs-esslingen dot de)
              Mahesh Jethanandani (mjethanandani at gmail dot com)
              Vishal Murgai (vmurgai at gmail dot com)";

  description
    "This module focuses on fundamental TCP functions and basic
     statistics. The model can be augmented to address more advanced
     or implementation specific TCP features.

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "2022-08-31" {
    description
      "Initial Version";
    reference
      "RFC XXXX, A YANG Model for Transmission Control Protocol (TCP)
                 Configuration and State.";
  }

  // Typedefs
  typedef mss {
    type uint16;
    description
      "Type definition for Maximum Segment Size.";
  }

  // Features
  feature statistics {
    description
      "This implementation supports statistics reporting.";
  }

  feature authentication {
    description
      "This implementation supports authentication.";
  }

  // Identities
  identity aes-128 {
    base key-chain:crypto-algorithm;
    description
      "AES128 authentication algorithm.";
  }

  // TCP-AO Groupings

  grouping ao {
    leaf send-id {
      type uint8 {
        range "0..max";
      }
      description
        "The SendID is inserted as the KeyID of the TCP-AO option
         of outgoing segments. In a consistent configuration, the
         SendID matches the RecvID at the other endpoint.";
      reference
        "RFC 5925: The TCP Authentication Option, Section 3.1.";
    }

    leaf recv-id {
      type uint8 {
        range "0..max";
      }
      description
        "The RecvID is matched against the TCP-AO KeyID of incoming
         segments. In a consistent configuration, the RecvID matches
         the SendID at the other endpoint.";
      reference
        "RFC 5925: The TCP Authentication Option, Section 3.1.";
    }

    leaf include-tcp-options {
      type boolean;
      default true;
      description
        "When set to true, TCP options are included in MAC
         calculation.";
      reference
        "RFC 5925: The TCP Authentication Option, Section 3.1.";
    }

    leaf accept-key-mismatch {
      type boolean;
      description
        "Accept, when set to true, TCP segments with a Master Key
         Tuple (MKT) that is not configured.";
      reference
        "RFC 5925: The TCP Authentication Option, Section 7.3.";
    }

    leaf r-next-key-id {
      type uint8;
      config false;
      description
        "A field indicating the Master Key Tuple (MKT) that is ready
         at the sender to be used to authenticate received segments,
         i.e., the desired 'receive next' key ID.";
      reference
        "RFC 5925: The TCP Authentication Option.";
    }

    description
      "Authentication Option (AO) for TCP.";
    reference
      "RFC 5925: The TCP Authentication Option.";
  }

  // TCP configuration

  container tcp {
    presence "The container for TCP configuration.";

    description
      "TCP container.";

    container connections {
      list connection {
        key "local-address remote-address local-port remote-port";

        leaf local-address {
          type inet:ip-address;
          description
            "Identifies the address that is used by the local
             endpoint for the connection, and is one of the four
             elements that form the connection identifier.";
        }

        leaf remote-address {
          type inet:ip-address;
          description
            "Identifies the address that is used by the remote
             endpoint for the connection, and is one of the four
             elements that form the connection identifier.";
        }

        leaf local-port {
          type inet:port-number;
          description
            "Identifies the local TCP port used for the connection,
             and is one of the four elements that form the
             connection identifier.";
        }

        leaf remote-port {
          type inet:port-number;
          description
            "Identifies the remote TCP port used for the connection,
             and is one of the four elements that form the
             connection identifier.";
        }

        leaf mss {
          type mss;
          description
            "Maximum Segment Size (MSS) desired on this connection.
             Note, the 'effective send MSS' can be smaller than
             what is configured here.";
          reference
            "RFC 9293: Transmission Control Protocol (TCP)
                       Specification.";
        }

        leaf pmtud {
          type boolean;
          default false;
          description
            "Turns Path Maximum Transmission Unit Discovery (PMTUD)
             on (true) or off (false).";
          reference
            "RFC 9293: Transmission Control Protocol (TCP)
                       Specification.";
        }

        uses tcpcmn:tcp-common-grouping;

        leaf state {
          type enumeration {
            enum closed {
              value 1;
              description
                "Connection is closed. Connections in this state
                 may not appear in this list.";
            }
            enum listen {
              value 2;
              description
                "Represents waiting for a connection request from any
                 remote TCP peer and port.";
            }
            enum syn-sent {
              value 3;
              description
                "Represents waiting for a matching connection request
                 after having sent a connection request.";
            }
            enum syn-received {
              value 4;
              description
                "Represents waiting for a confirming connection
                 request acknowledgment after having both received
                 and sent a connection request.";
            }
            enum established {
              value 5;
              description
                "Represents an open connection, data received can be
                 delivered to the user. The normal state for the data
                 transfer phase of the connection.";
            }
            enum fin-wait-1 {
              value 6;
              description
                "Represents waiting for a connection termination
                 request from the remote TCP peer, or an
                 acknowledgment of the connection termination request
                 previously sent.";
            }
            enum fin-wait-2 {
              value 7;
              description
                "Represents waiting for a connection termination
                 request from the remote TCP peer.";
            }
            enum close-wait {
              value 8;
              description
                "Represents waiting for a connection termination
                 request from the local user.";
            }
            enum last-ack {
              value 9;
              description
                "Represents waiting for an acknowledgment of the
                 connection termination request previously sent to
                 the remote TCP peer (this termination request sent
                 to the remote TCP peer already included an
                 acknowledgment of the termination request sent from
                 the remote TCP peer)";
            }
            enum closing {
              value 10;
              description
                "Represents waiting for a connection termination
                 request acknowledgment from the remote TCP peer.";
            }
            enum time-wait {
              value 11;
              description
                "Represents waiting for enough time to pass to be
                 sure the remote TCP peer received the acknowledgment
                 of its connection termination request, and to avoid
                 new connections being impacted by delayed segments
                 from previous connections.";
            }
          }
          config false;
          description
            "The state of this TCP connection.";
        }
        description
          "List of TCP connections with their parameters.

           The list is modeled as writeable even though only some of
           the nodes are writeable, e.g. keepalive. Connections
           that are created and match this list SHOULD apply the
           writeable parameters. At the same time, implementations
           may not allow creation of new TCP connections simply by
           adding entries to the list. Furthermore, the behavior
           upon removal is implementation-specific. Implementations
           may not support closing or resetting a TCP connection
           upon an operation that removes the entry from the list.

           The operational state of this list SHOULD reflect
           connections that have configured, but not created, and
           connections that have been created. Connections in
           CLOSED state are not reflected on this list.";
      }
      description
        "A container of all TCP connections.";
    }

    list tcp-listeners {
      key "type address port";
      config false;

      description
        "A table containing information about a particular
         TCP listener.";

      leaf type {
        type inet:ip-version;
        description
          "The address type of address.  The value
           should be unspecified (0) if connection initiations
           to all local IP addresses are accepted.";
      }

      leaf address {
        type union {
          type inet:ip-address;
          type string;
        }
        description
          "The local IP address for this TCP connection.

           The value of this node can be represented in three
           possible ways, depending on the characteristics of the
           listening application:

           1. For an application willing to accept both IPv4 and
              IPv6 datagrams, the value of this node must be
              ''h (a zero-length octet-string), with the value
              of the corresponding 'type' object being
              unspecified (0).

           2. For an application willing to accept only IPv4 or
              IPv6 datagrams, the value of this node must be
              '0.0.0.0' or '::' respectively, with
              'type' representing the appropriate address type.

           3. For an application which is listening for data
              destined only to a specific IP address, the value
              of this node is the specific local address, with
              'type' representing the appropriate address type.";
      }

      leaf port {
        type inet:port-number;
        description
          "The local port number for this TCP connection.";
      }
    }

    container statistics {
      if-feature statistics;
      config false;

      leaf active-opens {
        type yang:counter64;
        description
          "The number of times that TCP connections have made a
           direct transition to the SYN-SENT state from the CLOSED
           state.";
        reference
          "RFC 9293: Transmission Control Protocol (TCP)
                     Specification.";
      }

      leaf passive-opens {
        type yang:counter64;
        description
          "The number of times TCP connections have made a direct
           transition to the SYN-RCVD state from the LISTEN state.";
        reference
          "RFC 9293: Transmission Control Protocol (TCP)
                     Specification.";
      }

      leaf attempt-fails {
        type yang:counter64;
        description
          "The number of times that TCP connections have made a
           direct transition to the CLOSED state from either the
           SYN-SENT state or the SYN-RCVD state, plus the number of
           times that TCP connections have made a direct transition
           to the LISTEN state from the SYN-RCVD state.";
        reference
          "RFC 9293: Transmission Control Protocol (TCP)
                     Specification.";
      }

      leaf establish-resets {
        type yang:counter64;
        description
          "The number of times that TCP connections have made a
           direct transition to the CLOSED state from either the
           ESTABLISHED state or the CLOSE-WAIT state.";
        reference
          "RFC 9293: Transmission Control Protocol (TCP)
                     Specification.";
      }

      leaf currently-established {
        type yang:gauge32;
        description
          "The number of TCP connections for which the current state
           is either ESTABLISHED or CLOSE-WAIT.";
        reference
          "RFC 9293: Transmission Control Protocol (TCP)
                     Specification.";
      }

      leaf in-segments {
        type yang:counter64;
        description
          "The total number of TCP segments received, including those
           received in error. This count includes TCP segments
           received on currently established connections.";
        reference
          "RFC 9293: Transmission Control Protocol (TCP)
                     Specification.";
      }

      leaf out-segments {
        type yang:counter64;
        description
          "The total number of TCP segments sent, including those on
           current connections but excluding those containing only
           retransmitted octets.";
        reference
          "RFC 9293: Transmission Control Protocol (TCP)
                     Specification.";
      }

      leaf retransmitted-segments {
        type yang:counter64;
        description
          "The total number of TCP segments retransmitted; that is,
           the number of TCP segments transmitted containing one or
           more previously transmitted octets.";
        reference
          "RFC 9293: Transmission Control Protocol (TCP)
                     Specification.";
      }

      leaf in-errors {
        type yang:counter64;
        description
          "The total number of TCP segments received in error
           (e.g., bad TCP checksums).";
        reference
          "RFC 9293: Transmission Control Protocol (TCP)
                     Specification.";
      }

      leaf out-resets {
        type yang:counter64;
        description
          "The number of TCP segments sent containing the RST flag.";
        reference
          "RFC 9293: Transmission Control Protocol (TCP)
                     Specification.";
      }

      leaf auth-failures {
        if-feature authentication;
        type yang:counter64;
        description
          "The number of times that authentication has failed either
           with TCP-AO or MD5.";
      }

      action reset {
        nacm:default-deny-all;
        description
          "Reset statistics action command.";
        input {
          leaf reset-at {
            type yang:date-and-time;
            description
              "Time when the reset action needs to be
               executed.";
          }
        }
        output {
          leaf reset-finished-at {
            type yang:date-and-time;
            description
              "Time when the reset action command completed.";
          }
        }
      }
      description
        "Statistics across all connections.";
    }
  }

  augment "/key-chain:key-chains/key-chain:key-chain/key-chain:key" {
    description
      "Augmentation of the key-chain model to add TCP-AO and TCP-MD5
       authentication.";

    container authentication {
      if-feature authentication;
      leaf keychain {
        type key-chain:key-chain-ref;
        description
          "Reference to the key chain that will be used by
           this model. Applicable for TCP-AO and TCP-MD5
           only";
        reference
          "RFC 8177: YANG Key Chain.";
      }

      choice authentication {
        container ao {
          presence "Presence container for all TCP-AO related" +
                   " configuration";
          uses ao;
          description
            "Use TCP-AO to secure the connection.";
        }

        container md5 {
          presence "Presence container for all MD5 related" +
                   " configuration";
          description
            "Use TCP-MD5 to secure the connection. As the TCP MD5
             signature option is obsoleted by TCP-AO, it is
             RECOMMENDED to use TCP-AO instead.";
          reference
            "RFC 2385: Protection of BGP Sessions via the TCP MD5
                       Signature.";
        }
        description
          "Choice of TCP authentication.";
      }
      description
        "Authentication definitions for TCP configuration.
         This includes parameters such as how to secure the
         connection, that can be part of either the client
         or server.";
    }
  }
}
