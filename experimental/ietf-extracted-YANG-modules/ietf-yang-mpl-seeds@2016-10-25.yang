module ietf-yang-mpl-seeds {

  yang-version 1;

  namespace
      "urn:ietf:params:xml:ns:yang:ietf-yang-mpl-seeds";

  prefix mpl;

  organization
    "IETF ROLL (Routing over Low power and lossy networks)
 Working Group";

  contact
     "WG Web:   http://tools.ietf.org/wg/roll/
     WG List:  mailto:roll@ietf.org

     WG Chair: Peter van der Stok
               mailto:consultancy@vanderstok.org

     WG Chair: Ines Robles
               mailto:maria.ines.robles@ericsson.com

     Editor:   Peter van der Stok
               mailto:consultancy@vanderstok.org";

  description
    "This module contains information about the operation
of the MPL protocol.

     Copyright (c) 2016 IETF Trust and the persons identified as
     authors of the code.  All rights reserved.

     Redistribution and use in source and binary forms, with or

     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

revision "2016-10-25" {
      description "Initial revision.";
      reference
        "I-D:draft-ietf-roll-mpl-yang: A YANG model for Multicast
 Protocol for Low power and lossy Networks (MPL)";
    }

     list mpl-seeds{
     key "seedID domainID";
     config false;
     description
        "List describes all seeds that are active in the server.
 Seed information contains the message buffer contents and the
 operational values of I, c, sequence number and the life-times
 per message.";

      leaf seedID{
      type uint64;
      description
          "value uniquely identifies the MPL Seed within a MPL
           domain.";
      }

      leaf domainID{
      type uint16;
      description
         "together with seedID uniquely identifies buffer set.";
      }

      leaf local {
      type boolean;
      description
         "When local == TRUE, seed is located in this forwarder.
          WHEN local == false, seed is located in different
          forwarder.";
     }

     leaf generate-seqno {
     type uint8;
     description
          "Sequence number of next message to be generated by
this local seed.";
     }

     leaf life-time {
     type uint64;
     description
          " Minimum remaining lifetime of the seed entry in
           SE_LIFETIME units.";
     }

     leaf min-seqno{
     type uint8;
     description
        "Lower bound sequence number in the buffer of the seed.";
     }

     leaf data-number{
     type uint8;
     description
         "Number of currently buffered data messages.";
     }

     leaf control-number{
     type uint8;
     description
         "Number of currently buffered control messages.";
     }

      list buffered-messages{
      key seqno;
      description
          " status of trickle intervals of the buffered message
identified by seqno. and seed/domain";

      leaf seqno{
      type uint8;
      description
          "Sequence number of message.";
      }

      leaf I{
      type uint8;
      description
          "Current Trickle timer interval size in SE-LIFETIME
units.";
      }

      leaf c{
      type uint8;
      description
           "number of times that copy of this message has been
            received in this interval.";
      }

      leaf e{
      type uint8;
      description
            "number of Trickle time expirations since last
             Trickle timer reset.";
      }

      leaf t{
      type uint8;
      description
            " Time expressed in SE-LIFETIME units
             that message will be (is) forwarded";
      }
     } // list seed-timers
   } // list MPL-seeds
} // module ietf-yang-mpl-seeds
