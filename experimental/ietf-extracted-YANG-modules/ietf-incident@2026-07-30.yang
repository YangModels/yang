module ietf-incident {
  yang-version 1.1;
  namespace "urn:ietf:params:xml:ns:yang:ietf-incident";
  prefix inc;

  import ietf-yang-types {
    prefix yang;
    reference
      "RFC 9911: Common YANG Data Types";
  }
  import ietf-inet-types {
    prefix inet;
    reference
      "RFC 9911: Common YANG Data Types";
  }
  import ietf-alarms {
    prefix al;
    reference
      "RFC 8632: A YANG Data Model for Alarm Management";
  }
  import ietf-network {
    prefix nw;
    reference
      "RFC 8345: A YANG Data Model for Network Topologies";
  }
  import ietf-yang-structure-ext {
    prefix sx;
    reference
      "RFC 8791: YANG Data Structure Extensions";
  }

  organization
    "IETF NMOP Working Group";
  contact
    "WG Web:   <https://datatracker.ietf.org/wg/nmop/>;
     WG List:  <mailto:nmop@ietf.org>

     Author:   Chong Feng
               <mailto:fengchongllly@gmail.com>
     Author:   Tong Hu
               <mailto:hutong@cmhi.chinamobile.com>
     Author:   Luis Miguel Contreras Murillo
               <mailto:luismiguel.contrerasmurillo@telefonica.com>
     Author:  Qin Wu
               <mailto:bill.wu@huawei.com>
     Author:   Nigel Davis
               <mailto:ndavis@ciena.com>";
  description
    "This module defines the interfaces for incident management
     lifecycle.

     This module is intended for the following use cases:
     * incident lifecycle management:
       - incident report: report incident instance to client
                          when an incident instance is detected.
       - incident acknowledge: acknowledge an incident instance.
       - incident diagnose: diagnose an incident instance.
       - incident resolve: resolve an incident instance.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here. ";

  revision 2026-07-30 {
    description
      "Merge incident yang with incident type yang
       and fix broken ref.";
    reference
      "RFC XXXX: YANG module for network incident management.";
  }

  // Identities

  identity incident-domain {
    description
      "The abstract identity to indicate the domain of
       an incident.";
  }

  identity single-domain {
    base incident-domain;
    description
      "Single domain.";
  }

  identity access {
    base single-domain;
    description
      "access domain.";
  }

  identity ran {
    base access;
    description
      "Radio access network domain.";
  }

  identity transport {
    base single-domain;
    description
      "Transport domain.";
  }

  identity otn {
    base transport;
    description
      "Optical transport network domain.";
    reference
      "RFC9376: Applicability of GMPLS for beyond 100 Gbit/s Optical
       Transport Network";
  }

  identity ip {
    base single-domain;
    description
      "Ip domain.";
    reference
      "RFC1136: Administrative Domains and Routing Domains A Model
          for Routing in the Internet";
  }

  identity ptn {
    base ip;
    description
      "Packet transport network domain.";
    reference
      "RFC6373: MPLS Transport Profile (MPLS-TP) Control Plane
       Framework";
  }

  identity cross-domain {
    base incident-domain;
    description
      "Cross domain.";
  }

  identity incident-category {
    description
      "The abstract identity for incident category.";
  }

  identity device {
    base incident-category;
    description
      "Device category.";
    reference
      "RFC8348: A YANG Data Model for Hardware Management";
  }

  identity power-environment {
    base device;
    description
      "Power environment category.";
    reference
      "RFC8348: A YANG Data Model for Hardware Management";
  }

  identity device-hardware {
    base device;
    description
      "Device hardware category.";
    reference
      "RFC8348: A YANG Data Model for Hardware Management";
  }

  identity device-software {
    base device;
    description
      "Device software category";
    reference
      "RFC8348: A YANG Data Model for Hardware Management";
  }

  identity line-card {
    base device-hardware;
    description
      "Line card category.";
    reference
      "RFC8348: A YANG Data Model for Hardware Management";
  }

  identity maintenance {
    base incident-category;
    description
      "Maintenance category.";
  }

  identity network {
    base incident-category;
    description
      "Network category.";
  }

  identity protocol {
    base incident-category;
    description
      "Protocol category.";
  }

  identity overlay {
    base incident-category;
    description
      "Overlay category";
  }

  identity vm {
    base incident-category;
    description
      "VM category.";
  }

  identity event-type {
    description
      "The abstract identity for Event type";
    reference
      "RFC9940: Some Key Terms for Network Fault and Problem
       Management";
  }

  identity alarm {
    base event-type;
    description
      "Alarm event type.";
    reference
      "RFC8632: A YANG Data Model for Alarm Management";
  }

  identity notif {
    base event-type;
    description
      "Notification event type.";
    reference
      "RFC5277: NETCONF Event Notifications";
  }

  identity metric {
    base event-type;
    description
      "Metric event type.";
    reference
      "RFC9375: A YANG Data Model for Network and VPN
      Service Performance Monitoring";
  }

  identity unknown {
    base event-type;
    description
      "Unknown event type.";
  }

  identity incident-type {
    description
      "The abstract identity for Incident category.";
  }

  identity problem {
    base incident-type;
    description
      "It indicates the class of the incident is a problem
       (i.e.,cause of the incident) for example an interface
       fails to work.";
    reference
      "RFC9940: Some Key Terms for Network Fault and Problem
       Management";
  }

  identity sla-violation {
    base incident-type;
    description
      "It indicates the class of the incident is a sla
       violation, for example high CPU rate may cause
       a fault in the future.";
  }

  identity acknowledge-error {
    description
      "Base identity for the problem found while attempting
       to fulfill an 'incident-acknowledge' RPC request.";
  }

  identity diagnose-error {
    description
      "Base identity for the problem found while attempting
       to fulfill an 'incident-diagnose' RPC request.";
  }

  identity resolve-error {
    description
      "Base identity for the problem found while attempting
       to fulfill an 'incident-resolve' RPC request.";
  }

  identity repeated-acknowledge {
    base acknowledge-error;
    description
      "The incident referred to has already been acknowledged.";
  }

  identity probable-cause-unlocated {
    base diagnose-error;
    description
      "Fail to locate the Probable Root Causes when performing the
       diagnosis operation. The detailed reason MUST be included
       in the 'description'.";
  }

  identity probable-cause-unresolved {
    base resolve-error;
    description
      "Fail to resolve the Probable Root Causes when performing the
       resolution operation. The detailed reason MUST be included
       in the 'description'";
  }

  identity permission-denied {
    base diagnose-error;
    base resolve-error;
    description
      "The permission required for performing specific
       detection/resolution task is not granted.";
  }

  identity operation-timeout {
    base diagnose-error;
    base resolve-error;
    description
      "The diagnosis/resolution time exceeds the preset time.";
  }

  identity resource-unavailable {
    base diagnose-error;
    base resolve-error;
    description
      "The resource is unavailable to perform
       the diagnosis/resolution operation.";
  }

  // Typedefs

  typedef incident-priority {
    type enumeration {
      enum critical {
        description
          "The incident MUST be handled immediately.";
      }
      enum high {
        description
          "The incident should be handled as soon as
           possible.";
      }
      enum medium {
        description
          "Network services are not affected, or the
           services are slightly affected, but corrective
           measures need to be taken.";
      }
      enum low {
        description
          "Potential or imminent service-affecting
           incidents are detected,but services are
           not affected currently.";
      }
    }
    description
      "Define the priority of incident.";
  }

  typedef incident-ref {
    type leafref {
      path "/inc:incidents/inc:incident/inc:incident-no";
    }
    description
      "Reference a network incident.";
  }

  // Groupings

  grouping probable-cause-info {
    description
      "The information of Probable Root Cause.";
    leaf cause-name {
      type string;
      description
        "The name of cause.";
    }
    leaf detail {
      type string;
      description
        "The detail information of the cause.";
    }
  }

  grouping resources-info {
    description
      "The grouping which defines the network
       resources of a node.";
    uses nw:node-ref;
    list resource {
      key "name";
      description
        "The resources of a network node.";
      leaf name {
        type al:resource;
        description
          "Network resource name.";
      }
    }
  }

  grouping incident-time-info {
    description
      "The grouping defines incident time information.";
    leaf raise-time {
      type yang:date-and-time;
      description
        "The time when an incident instance is raised.";
    }
    leaf occur-time {
      type yang:date-and-time;
      description
        "The time when an incident instance occurs.
         It's the occur time of the first event during
         incident detection.";
    }
    leaf clear-time {
      type yang:date-and-time;
      description
        "The time when an incident instance is
         resolved.";
    }
    leaf ack-time {
      type yang:date-and-time;
      description
        "The time when an incident instance is
         acknowledged.";
    }
    leaf last-updated {
      type yang:date-and-time;
      description
        "The latest time when an incident instance is
         updated";
    }
  }

  grouping incident-info {
    description
      "The grouping defines the information of an
       incident.";
    leaf name {
      type string;
      description
        "The name of an incident.";
    }
    leaf type {
      type identityref {
        base incident-type;
      }
      description
        "The type of an incident.";
    }
    leaf incident-qualifier {
      type string;
      description
        "The unique qualifier of an incident instance type.
         This leaf is used when the 'type' leaf cannot
         uniquely identify the incident instance type.  Normally,
         this is not the case, and this leaf is the empty string.
        ";
    }
    leaf-list service-instance {
      type string;
      description
        "The related network service instances of
         the incident instance.";
    }
    leaf domain {
      type identityref {
        base incident-domain;
      }
      mandatory true;
      description
        "The domain of an incident.";
    }
    leaf priority {
      type incident-priority;
      mandatory true;
      description
        "The priority of an incident instance.";
    }
    leaf status {
      type enumeration {
        enum raised {
          description
            "An incident instance is raised.";
        }
        enum updated {
          description
            "The information of an incident instance
             is updated.";
        }
        enum cleared {
          description
            "An incident is cleared.";
        }
      }
      default "raised";
      description
        "The status of an incident instance.";
    }
    leaf ack-status {
      type enumeration {
        enum acknowledged {
          description
            "The incident has been acknowledged by user.";
        }
        enum unacknowledged {
          description
            "The incident hasn't been acknowledged.";
        }
      }
      default "unacknowledged";
      description
        "The acknowledge status of an incident.";
    }
    leaf category {
      type identityref {
        base incident-category;
      }
      mandatory true;
      description
        "The category of an incident.";
    }
    leaf detail {
      type string;
      description
        "Detailed information of this incident.";
    }
    leaf resolve-advice {
      type string;
      description
        "The advice to resolve this incident.";
    }
    container sources {
      description
        "The source components.";
      list source {
        key "node-ref";
        description
          "The source components of incident. An Incident might
           be created even if we don't know yet the sources
           (hence we can not populate source list in the sources
           container). Therefore the min-elements for the source
           list is set to 0. Once the Incident is diagnosed, the
           source(s) will be populated.";
        uses resources-info;
      }
    }
    container probable-causes {
      description
        "The Probable Root Cause objects.";
      list probable-cause {
        key "node-ref";
        description
          "The Probable Root Causes of incident.";
        uses resources-info {
          augment "resource" {
            description
              "Augment Probable Root Cause information.";
            //if Probable Root Cause object is a resource of a node
            uses probable-cause-info;
          }
        }
        //if Probable Root Cause object is a node
        uses probable-cause-info;
      }
    }
    container probable-events {
      description
        "The Probable Root Cause related events of the incident.";
      list probable-event {
        key "type event-id";
        description
          "The Probable Root Cause related event of the incident.";
        leaf type {
          type leafref {
            path "../../../events/event/type";
          }
          description
            "The event type.";
        }
        leaf event-id {
          type leafref {
            path "../../../events/event[type = current()/../type]"
               + "/event-id";
          }
          description
            "The event identifier, such as uuid,
             sequence number, etc.";
        }
      }
    }
    container events {
      description
        "Related events.";
      list event {
        key "type event-id";
        description
          "Related events.";
        leaf type {
          type identityref {
            base event-type;
          }
          description
            "Event type.";
        }
        leaf event-id {
          type string;
          description
            "The event identifier, such as uuid,
             sequence number, etc.";
        }
        choice event-type-info {
          description
            "Various different event type information.";
          case alarm {
            when "derived-from-or-self(type, 'alarm')" {
              description
                "Only applies when type is alarm.";
            }
            container alarm {
              description
                "Alarm type event.";
              leaf resource {
                type leafref {
                  path "/al:alarms/al:alarm-list/al:alarm"
                     + "/al:resource";
                }
                description
                  "Network resource.";
                reference
                  "RFC 8632: A YANG Data Model for Alarm
                   Management";
              }
              leaf alarm-type-id {
                type leafref {
                  path "/al:alarms/al:alarm-list/al:alarm"
                     + "[al:resource = current()/../resource]"
                     + "/al:alarm-type-id";
                }
                description
                  "Alarm type id";
                reference
                  "RFC 8632: A YANG Data Model for Alarm
                    Management";
              }
              leaf alarm-type-qualifier {
                type leafref {
                  path "/al:alarms/al:alarm-list/al:alarm"
                     + "[al:resource = current()/../resource]"
                     + "[al:alarm-type-id = current()/.."
                     + "/alarm-type-id]/al:alarm-type-qualifier";
                }
                description
                  "Alarm type qualifier";
                reference
                  "RFC 8632: A YANG Data Model for Alarm
                   Management";
              }
            }
          }
          case metric {
            when "derived-from-or-self(type, 'metric')" {
              description
                "Only applies when type is metric.";
            }
            container metric {
              description
                "Metric type event. Performance metrics
                 exceeding SLO thresholds.";
              leaf resource {
                type leafref {
                  path "/al:alarms/al:alarm-list/al:alarm"
                     + "/al:resource";
                }
                description
                  "Network resource.";
                reference
                  "RFC 8632: A YANG Data Model for Alarm
                   Management";
              }
              leaf metric-name {
                type string;
                description
                  "Metric Name.";
              }
              leaf threshold-value {
                type string;
                description
                  "Threshold value for the specific metric.";
              }
              leaf observed-value {
                type string;
                description
                  "Observed value for the specific metric";
              }
            }
          }
          case notification {
            when "derived-from-or-self(type, 'notif')" {
              description
                "Only applies when type is notification.";
            }
            container notification {
              description
                "Notification type event.";
              leaf event-time {
                type yang:date-and-time;
                description
                  "The date and time the event was generated by
                   the network node.";
              }
              leaf hostname {
                type inet:host;
                description
                  "The hostname of the network node. This value
                   is usually configured on the node by the
                   administrator to identify the node in the
                   network uniquely.";
              }
              leaf sequence-number {
                type yang:counter32;
                description
                  "Unique sequence number for each published
                   message by the publisher process. The initial
                   number is 1 and counts up by 1 at every
                   published notification message until it reaches
                   4294967295. Then, it wraps around and restarts
                   at 0. The value 0 is used to detect wrap
                   arounds.";
              }
            }
          }
        }
      }
    }
  }

  // RPCs

  rpc incident-acknowledge {
    description
      "This rpc can be used to acknowledge the specified
       incidents.";
    input {
      leaf-list incident-no {
        type incident-ref;
        description
          "The unique sequence number of an incident instance
           based on the name type incident-id keys.";
      }
    }
  }

  rpc incident-diagnose {
    description
      "This rpc can be used to diagnose the specified
       incidents. The result of diagnosis will be reported
       by incident notification.";
    input {
      leaf-list incident-no {
        type incident-ref;
        description
          "The unique sequence number of an incident instance
           based on the name type incident-id keys.";
      }
    }
  }

  rpc incident-resolve {
    description
      "This rpc can be used to resolve the specified
       incidents. The result of resolution will be reported
       by incident notification.";
    input {
      leaf-list incident-no {
        type incident-ref;
        description
          "The unique sequence number of an incident instance
           based on the name type incident-id keys.";
      }
    }
  }

  sx:structure incident-acknowledge-error-info {
    container incident-acknowledge-error-info {
      description
        "This structure data MAY be inserted in the RPC error
         response to indicate the reason for the
         incident acknowledge failure.";
      leaf incident-no {
        type uint64;
        description
          "Indicates the incident identifier that
           fails the operation.";
      }
      leaf reason {
        type identityref {
          base acknowledge-error;
        }
        description
          "Indicates the reason why the operation
           is failed.";
      }
      leaf description {
        type string;
        description
          "Indicates the detailed description about
           the failure.";
      }
    }
  }
  sx:structure incident-diagnose-error-info {
    container incident-diagnose-error-info {
      description
        "This structure data MAY be inserted in
         the RPC error response to indicate the
         reason for the incident diagnose failure.";
      leaf incident-no {
        type uint64;
        description
          "Indicates the incident identifier that
           fails the operation.";
      }
      leaf reason {
        type identityref {
          base diagnose-error;
        }
        description
          "Indicates the reason why the operation
           is failed.";
      }
      leaf description {
        type string;
        description
          "Indicates the detailed description about
           the failure.";
      }
    }
  }
  sx:structure incident-resolve-error-info {
    container incident-resolve-error-info {
      description
        "This structure data MAY be inserted in
         the RPC error response to indicate the
         reason for the incident resolution failure.";
      leaf incident-no {
        type uint64;
        description
          "Indicates the incident identifier that
           fails the operation.";
      }
      leaf reason {
        type identityref {
          base resolve-error;
        }
        description
          "Indicates the reason why the operation is failed.";
      }
      leaf description {
        type string;
        description
          "Indicates the detailed description about the failure.";
      }
    }
  }

  // Notifications

  notification incident-notification {
    description
      "Incident notification. It will be triggered when
       the incident is raised, updated or cleared.";
    leaf incident-no {
      type incident-ref;
      mandatory true;
      description
        "The identifier of an incident instance.";
    }
    uses incident-info;
    leaf time {
      type yang:date-and-time;
      description
        "Occurring time of an incident instance.";
    }
  }

  // Data definitions

  container incidents {
    config false;
    description
      "The information of incidents.";
    list incident {
      key "name type incident-qualifier";
      description
        "The information of incident.";
      leaf incident-no {
        type uint64;
        mandatory true;
        description
          "The unique sequence number of the incident
           instance based on the name type incident-id keys.";
      }
      uses incident-info;
      uses incident-time-info;
    }
  }
}
