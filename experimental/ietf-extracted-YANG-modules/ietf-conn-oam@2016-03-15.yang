module ietf-conn-oam {
  namespace "urn:ietf:params:xml:ns:yang:ietf-conn-oam";
  prefix goam;

  import ietf-interfaces {
    prefix if;
  }
  import ietf-yang-types {
    prefix yang;
  }
  import ietf-inet-types {
    prefix inet;
  }

  organization "IETF LIME Working Group";
  contact
    "WG Web:    http://tools.ietf.org/wg/lime
     WG List:   mailto:lime@ietf.org
     WG Chair:  Carlos Pignataro cpignata@cisco.com
     WG Chair:  Ron Bonica rbonica@juniper.net
     Editor:    Deepak Kumar dekumar@cisco.com
     Editor:    Qin Wu bill.wu@huawei.com
     Editor:    Zitao Wang wangzitao@huawei.com";
  description
    "This YANG module defines the generic configuration,
  statistics and rpc for connection oriented OAM
  to be used within IETF in a protocol indpendent manner.
  Functional level abstraction is indendent
  with YANG modeling. It is assumed that each protocol
  maps corresponding abstracts to its native format.
  Each protocol may extend the YANG model defined
  here to include protocol specific extensions";

  revision 2016-03-15 {
    description
      "Initial revision. - 05 version";
    reference "draft-ietf-lime-yang-oam-model";
  }

  /* features */
  feature connectivity-verification {
    description
      "This feature indicates that the server supports
    executing connectivity verification OAM command and
    returning a response. Servers that do not advertise
    this feature will not support executing
    connectivity verification command or rpc model for
    connectivity verification command.";
  }
  feature continuity-check{
    description
      "This feature indicates that the server supports
    executing continuity check OAM command and
    returning a response. Servers that do not advertise
    this feature will not support executing
    continuity check command or rpc model for
    continuity check command.";
  }

  feature traceroute{
    description
      "This feature indicates that the server supports
    executing traceroute OAM command and
    returning a response. Servers that do not advertise
    this feature will not support executing
    traceroute command or rpc model for
    traceroute command.";
   }

  /* Identities */

  identity technology-types {
    description
      "this is the base identy of technology types which are
    TRILL,MPLS-TP,vpls etc";
  }

  identity command-sub-type {
    description
      "defines different rpc command subtypes,
    e.g rfc6905 trill OAM, this is optional for most cases";
  }

  identity name-format {
    description
      "This defines the name format, IEEE 8021Q CFM defines varying
      styles of names. It is expected name format as an identity ref
      to be extended with new types.";
  }

  identity name-format-null {
    base name-format;
    description
      "defines name format as null";
  }

  identity identifier-format {
    description
      "identifier-format identity can be augmented to define other
     format identifiers used in MEP-ID etc";
  }

  identity identifier-format-integer {
    base identifier-format;
    description
      "defines identifier-format to be integer";

  }

  identity defect-types {
    description
      "defines different defect types, e.g. remote rdi,
       mis-connection defect, loss of continuity";
  }
  identity rdi {
    base defect-types;
    description
      "Indicates the aggregate health of the remote MEPs. ";
  }

  identity remote-mep-defect{
    base defect-types;
    description
      "Indicates that one or more of the remote MEPs is
       reporting a failure ";
  }

  identity loss-of-continuity{
    base defect-types;
    description
    "If no proactive CC-V OAM packets from the source
     MEP (and in the case of CV, this includes the
     requirement to have the expected globally unique
     Source MEP identifier) are received within the interval
     equal to 3.5 times the receiving MEP's
     configured CC-V reception period. ";
   }

  identity invalid-oam-defect{
    base defect-types;
    description
    "Indicates that one or more invalid OAM messages has been
    received and that 3.5 times that OAM message transmission
    interval has not yet expired.";
  }

  identity cross-connect-defect{
    base defect-types;
    description
    "Indicates that one or more cross-connect defect
    (for example, a service ID does not match the VLAN.)
     messages has been received and that 3.5 times that OAM message
     transmission interval has not yet expired.";
  }

  /* typedefs */

  typedef MEP-name {
    type string;
    description
      "Generic administrative name for a MEP";
  }

  typedef Interval{
    type decimal64{
    fraction-digits 2;
   }
   units "milliseconds";
    description
    "Interval between packets in milliseconds.
    0 means no packets are sent.";
  }

  typedef MD-name-string {
    type string;
    description
      "Generic administrative name for an MD";
  }

  typedef MA-name-string {
    type string;
    description
      "Generic administrative name for an MA";
  }

  typedef oam-counter32 {
    type yang:zero-based-counter32;
    description
      "defines 32 bit counter for OAM";
  }

  typedef MD-level {
    type uint32 {

      range "0..255";
    }
    description
      "Maintenance Domain level.  The level may be restricted in
       certain protocols (eg to 0-7)";
  }

  /* groupings */

  grouping MEG-ID{
    leaf meg-id{
      type string;
      description
       "concatenation of domain and ma, For example a co-routed
        bidirectional LSP, MEG_ID is A1-{Global_ID::Node_ID::
        Tunnel_Num}::Z9-{Global_ID::Node_ID::Tunnel_Num}::LSP_Num.";
    }
    description
      "MEG-ID grouping.";
  }
