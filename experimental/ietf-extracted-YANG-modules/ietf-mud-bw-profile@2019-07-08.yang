module ietf-mud-bw-profile {
  yang-version 1.1;
  namespace "urn:ietf:params:xml:ns:yang:ietf-mud-bw-profile";
  prefix mud-qos;

  import ietf-access-control-list {
    prefix acl;
  }
  import ietf-inet-types {
    prefix inet;
  }
  import ietf-mud {
    prefix mud;
  }

  organization
    "IETF OPSAWG (Ops Area) Working Group";
  contact
    "WG Web: http://tools.ietf.org/wg/opsawg/
     WG List: opsawg@ietf.org
     Author: Eliot Lear
     lear@cisco.com
     Author: Jerome Henry
     jerhenry@cisco.com
    ";
  description

    "This YANG module augments the ietf-mud model to provide the
     network with some understanding as to the QoS requirements and
     anticipated behavior of a device.

     The to-device-policy and from-device-policy containers are
     augmented with one additional container, which expresses how many
     packets per second a device is expected to transmit, how much
     bandwidth it is expected to use, and what QoS is required, and
     how much bandwidth is to be expected to be prioritized.  An
     access-list is further specified to indicate how QoS should be
     marked on ingress and egress.

     Copyright (c) 2016,2017,2018 IETF Trust and the persons
     identified as the document authors.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).
     This version of this YANG module is part of RFC XXXX; see
     the RFC itself for full legal notices.";

  revision 2019-07-08 {
    description
      "Initial proposed standard.";
    reference "RFC XXXX: Bandwidth Descriptions for MUD Specification";
  }

  grouping mud-bw-params {
    description
      "QoS and Bandwidth additions for MUD";
    container bw-params {
      description
        "Expected Bandwidth to/from device";
      list service {
        key "name";
        description
          "a list of services that are being described.";
        leaf name {
          type string;
          description
            "Service Name";
        }
        leaf timeframe {
          type uint32;
          mandatory true;
          description
            "the period of time in seconds one
             expects a service to burst at described rates";
        }
        leaf pps {
          type uint32;
          description
            "number of packets per second to be expected.";
        }
        leaf bps {
          type uint64;
          description
            "number of bits per second to be expected.";
        }
        leaf dscp {
          type inet:dscp;
          description
            "The DSCP that packets for this service should
             treated with.  N.B., just because the manufacturer
             wants this, doesn't mean it will get it.  However,
             manufacturers who do set the DSCP value in their
             packets SHOULD indicate that in this description.

             This field differs from the dscp field in the matches
             portion of the access-list in that here the field is
             populated when the manufacturer states what the nominal
             value of the DSCP field MAY be, and how much bandwidth
             can be used when it is set.  Note that it is possible
             that the same service may use multiple DSCP values,
             depending on the circumstances.  In this case, service
             entry MUST be made.";
        }
        leaf aclname {
          type leafref {
            path "/acl:acls/acl:acl/acl:name";
          }
          description
            "The name of the ACL that will match packets
             for a given service.";
        }
      }
    }
  }

  augment "/mud:mud/mud:to-device-policy" {
    description
      "add inbound QoS parameters";
    uses mud-bw-params;
  }
  augment "/mud:mud/mud:from-device-policy" {
    description
      "add outbound QoS parameters";
    uses mud-bw-params;
  }
}
