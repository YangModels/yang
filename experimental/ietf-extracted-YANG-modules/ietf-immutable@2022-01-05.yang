module ietf-immutable {
  yang-version 1.1;
  namespace "urn:ietf:params:xml:ns:yang:ietf-immutable";
  prefix im;

  import ietf-yang-metadata {
    prefix md;
  }

  organization
    "IETF Network Modeling (NETMOD) Working Group";

  contact
    "WG Web: <https://datatracker.ietf.org/wg/netmod/>

     WG List: <mailto:netmod@ietf.org>

     Author: Qiufang Ma
             <mailto:maqiufang1@huawei.com>

     Author: Qin Wu
             <mailto:bill.wu@huawei.com>

     Author: Hongwei Li
             <mailto:flycoolman@gmail.com>";

  description
    "This module defines a metadata annotation named 'immutable'
     to indicate the immutability of a particular instantiated
     data node. Any instantiated data node marked with
     immutable='true' by the server is read-only to the clients
     of YANG-driven management protocols, such as NETCONF,
     RESTCONF as well as SNMP and CLI requests.

     Copyright (c) 2021 IETF Trust and the persons identified
     as authors of the code. All rights reserved.

     Redistribution and use in source and binary forms, with
     or without modification, is permitted pursuant to, and
     subject to the license terms contained in, the Simplified
     BSD License set forth in Section 4.c of the IETF Trust's
     Legal Provisions Relating to IETF Documents
     (https://trustee.ietf.org/license-info).

     This version of this YANG module is part of RFC HHHH
     (https://www.rfc-editor.org/info/rfcHHHH); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2022-01-05 {
    description
      "Initial revision.";
    reference
      "RFC XXX: Immutable Metadata Annotation";
  }

  md:annotation immutable {
    type boolean;
    description
      "The 'immutable' annotation indicates the immutability of an
       instantiated data node. Any data node instance marked as
       'immutable=true' is read-only to clients and cannot be
       created/deleted/changed through NETCONF, RESTCONF or CLI.
       It applies to the container, anydata, anyxml and leaf
       instances, list and leaf-list entries.
       If not specified for a given configuration data node
       instance, then the immutability is the same as its parent
       node instance in the data tree. The default for any top-level
       configuration data node instance is false if not specified.";
  }
}
