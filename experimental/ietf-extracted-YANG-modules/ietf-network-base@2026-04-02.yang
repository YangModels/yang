module ietf-network-base {
  yang-version 1.1;
  namespace "ari://ietf/network-base/";
  prefix network-base;

  import ietf-amm {
    prefix amm;
  }
  import ietf-amm-base {
    prefix amm-base;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module defines base IDENT objects for network-related
     entities such as protocol endpoints. The base objects are
     general purpose, and all derived objects are layer- and/or
     protocol-specific with appropriate parameters.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2026-04-02 {
    description
      "Updated for latest ADM document.";
    reference
      "draft-ietf-dtn-adm-yang";
  }
  amm:enum 26;

  // General purpose network data types and forms
  amm:typedef uri {
    amm:enum 0;
    description
      "A specialization of the textstr type to only contain a single
       Uniform Resource Identifier (URI) as defined by STD 66.

       Objects using the uri type MUST be in US-ASCII encoding,
       and MUST be normalized as described by RFC 3986 Sections
       6.2.1, 6.2.2.1, and 6.2.2.2.  All unnecessary
       percent-encoding is removed, and all case-insensitive
       characters are set to lowercase except for hexadecimal
       digits, which are normalized to uppercase as described in
       Section 6.2.2.1.

       The purpose of this normalization is to help provide
       unique URIs.  Note that this normalization is not
       sufficient to provide uniqueness.  Two URIs that are
       textually distinct after this normalization may still be
       equivalent.

       Objects using the uri type may restrict the schemes that
       they permit.  For example, 'data:' and 'urn:' schemes
       might not be appropriate.

       A zero-length URI is not a valid URI.  This can be used to
       express 'URI absent' where required.

       In the value set and its semantics, this type is equivalent
       to the Uri SMIv2 textual convention defined in RFC 5017.";
    reference
      "RFC 3986: Uniform Resource Identifier (URI): Generic Syntax
       RFC 3305: Report from the Joint W3C/IETF URI Planning Interest
                 Group: Uniform Resource Identifiers (URIs), URLs,
                 and Uniform Resource Names (URNs): Clarifications
                 and Recommendations
       RFC 5017: MIB Textual Conventions for Uniform Resource
                 Identifiers (URIs)";
    amm:type "/aritype/textstr" {
      // This pattern is on the normalized scheme
      pattern '[a-z][a-z0-9+-.]*:.*';
    }
  }
  amm:ident display-bstr-uuid {
    amm:enum 17;
    description
      "Interpret byte string values as UUID and display as
       human-friendly text according to RFC 9562 conventions.";
    reference
      "RFC 9562: Universally Unique IDentifiers (UUIDs)";
    amm:base "//ietf/amm-base/IDENT/display-hint-bstr";
  }
  amm:typedef uuid {
    amm:enum 5;
    description
      "A specialization of the bytestr type to contain a binary
       encoded UUID value.
       Values of this type SHALL contain a valid UUID value
       as defined in Section 4 of RFC 9562.";
    reference
      "RFC 9562: Universally Unique IDentifiers (UUIDs)";
    amm:type "/aritype/bytestr" {
      length "16";
    }
  }
  amm:ident display-bstr-oid {
    amm:enum 18;
    description
      "Interpret byte string values as ASN.1 BER-encoded OIDs
       and display as human-friendly dotted-decimal form of
       ITU-T X.660.";
    reference
      "ITU-T X.660-2011: General procedures and top arcs of the
         international object identifier tree";
    amm:base "//ietf/amm-base/IDENT/display-hint-bstr";
  }
  amm:typedef oid {
    amm:enum 4;
    description
      "A specialization of the bytestr type to contain an ASN.1
       BER-encoded object identifier (OID) value.
       This typedef gives no more specific AMM constraints on
       the byte string value but does constrain it by these
       requirements.
       Values of this type SHALL contain valid BER-encoded OID
       contents consistent with the definition of CBOR tag 111
       but without the actual tag, as defined in Section 2.1 of
       RFC 9090.
       Values of this type always contain an absolute OID.";
    reference
      "RFC 9090: Concise Binary Object Representation (CBOR) Tags
         for Object Identifiers
       ITU-T X.660-2011: General procedures and top arcs of the
         international object identifier tree
       ITU-T X.690-2021: ASN.1 encoding rules: Specification of
         Basic Encoding Rules (BER), Canonical Encoding
         Rules (CER) and Distinguished Encoding Rules (DER)";
    amm:type "/aritype/bytestr" {
      length "2..max";
    }
  }

  // Abstract base IDENTs and types
  amm:ident abstract-endpoint {
    amm:enum 0;
    description
      "This object defines an abstract base for all general purpose
       network/transport endpoint identifiers as seen from outside
       the endpoint node.
       Uses where the endpoint is being bound to from inside the
       node might require additional parameters outside of what is
       present in this object hierarchy.";
    amm:abstract true;
  }
  amm:typedef endpoint {
    amm:enum 1;
    description
      "A value which references a non-abstract derived object
       for specific types of network or transport endpoints.";
    amm:type "/aritype/ident" {
      amm:base "./IDENT/abstract-endpoint";
    }
  }
  amm:typedef endpoint-or-uri {
    amm:enum 3;
    description
      "A value which is either a specific parameterized endpoint
       IDENT reference or a text URI value identifying an endpoint.";
    amm:union {
      amm:type "./typedef/endpoint";
      amm:type "./typedef/uri";
    }
  }
}
