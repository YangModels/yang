module ietf-network-slice-phd {
  yang-version 1.1;
  namespace "urn:ietf:params:xml:ns:yang:ietf-network-slice-phd";
  prefix "ns-phd";

  import ietf-inet-types {
    prefix "inet";
    reference
      "RFC 6991: Common YANG Data Types";
  }

  import ietf-routing-types {
    prefix "rt-types";
    reference
      "RFC 8294: Common YANG Data Types for the Routing Area";
  }

  import ietf-access-control-list {
    prefix "acl";
    reference
      "RFC 8519: YANG Data Model for Network Access Control Lists
       (ACLs)";
  }

  import ietf-te-types {
    prefix te-types;
    reference
      "RFC 8776: Common YANG Data Types for Traffic Engineering";
  }

  organization
    "IETF Traffic Engineering Architecture and Signaling (TEAS)
     Working Group.";

  contact
    "WG Web:   <http://tools.ietf.org/wg/teas/>
     WG List:  <mailto:teas@ietf.org>

     Editor:   Vishnu Pavan Beeram
               <mailto:vbeeram@juniper.net>

     Editor:   Tarek Saad
               <mailto:tsaad@juniper.net>";

  description
    "This YANG module defines a data model for managing Network
     Slice Per-Hop Definitions (Slice-PHDs) on a network slicing
     capable node.

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX; see the
     RFC itself for full legal notices.";

  revision "2020-11-02" {
    description "Initial revision.";
    reference
      "RFC XXXX: YANG Data Model for Network Slice Per-Hop
       Definitions (Slice-PHDs).";
  }

  /*
   * I D E N T I T I E S
   */

  /*
   * Identity - MPLS Slice Selector Label Position Type
   */

  identity ss-mpls-label-position-type {
    description
      "Base identity for the position of the MPLS label that is used
       for slice selection.";
  }

  identity ss-mpls-label-position-top {
    base ss-mpls-label-position-type;
    description
      "MPLS label that is used for slice selection is at the top of
       the label stack.";
  }

  identity ss-mpls-label-position-bottom {
    base ss-mpls-label-position-type;
    description
      "MPLS label that is used for slice selection is either at the
       bottom or at a specific offset from the bottom of the label
       stack.";
  }

  identity ss-mpls-label-position-indicator {
    base ss-mpls-label-position-type;
    description
      "MPLS label that is used for slice selection is immediately
       preceded by a special purpose slice indicator label in the
       label stack.";
  }

  /*
   * Identity - Slice-PHB Class Direction
   */

  identity s-phb-class-direction {
    description
      "Base identity for the direction of traffic to which the Slice
       PHB class profile is applied.";
  }

  identity s-phb-class-direction-in {
    base s-phb-class-direction;
    description
      "Slice PHB class profile is applied to incoming traffic.";
  }

  identity s-phb-class-direction-out {
    base s-phb-class-direction;
    description
      "Slice PHB class profile is applied to outgoing traffic.";
  }

  identity s-phb-class-direction-in-out {
    base s-phb-class-direction;
    description
      "Slice PHB class profile is applied to both incoming and
       outgoing directions of traffic.";
  }

  /*
   * Identity - Slice-PHB Class Priority
   */

  identity s-phb-class-priority {
    description
      "Base identity for the priority of the child class scheduler.";
  }

  identity s-phb-class-priority-low {
    base s-phb-class-drop-probability;
    description
      "Priority of the child class scheduler is low.";
  }
  identity s-phb-class-priority-strict-high {
    base s-phb-class-drop-probability;
    description
      "Priority of the child class scheduler is strict-high.";
  }

  /*
   * Identity - Slice-PHB Class Drop Probability
   */

  identity s-phb-class-drop-probability {
    description
      "Base identity for the drop probability applied to packets
       exceeding the CIR of the class queue.";
  }

  identity s-phb-class-drop-probability-low {
    base s-phb-class-drop-probability;
    description
      "Low drop probability applied to packets exceeding the CIR of
       the class queue.";
  }

  identity s-phb-class-drop-probability-medium {
    base s-phb-class-drop-probability;
    description
      "Medium drop probability applied to packets exceeding the CIR
       of the class queue.";
  }

  identity s-phb-class-drop-probability-high {
    base s-phb-class-drop-probability;
    description
      "High drop probability applied to packets exceeding the CIR of
       the class queue.";
  }

  /*
   * T Y P E D E F S
   */

  typedef ns-acl-ref {
    type leafref {
      path "/acl:acls/acl:acl/acl:name";
    }
    description
      "This type is used to reference an ACL.";
  }
  typedef ns-ss-ref {
    type leafref {
      path "/network-slicing/network-slices/network-slice/"
        + "slice-selectors/slice-selector/id";
    }
    description
      "This type is used to reference a Slice Selector (SS).";
  }

  typedef ns-phb-ref {
    type leafref {
      path "/network-slicing/network-slice-phbs/network-slice-phb/"
        + "id";
    }
    description
      "This type is used to reference a Slice Per-Hop Behavior
       (Slice-PHB).";
  }

  /*
   * G R O U P I N G S
   */

  /*
   * Grouping - Slice Selector MPLS: Label location specific fields
   */
  grouping ns-ss-mpls-label-location {
    description
      "Grouping for MPLS (SS) label location specific fields.";
    leaf label-position {
      type identityref {
        base ss-mpls-label-position-type;
      }
      description
        "MPLS label position - top, bottom with offset, Slice label
         indicator.";
    }
    leaf label-position-offset {
      when "derived-from-or-self(../label-position,"
        + "'ns-phd:ss-mpls-label-position-bottom')" {
        description
          "MPLS label position offset is relevant only when the
           label-position is set to 'bottom'.";
      }
      type uint8;
      description
        "MPLS label position offset.";
    }
  }

  /*
   * Grouping - Slice Selector (SS)
   */
  grouping ns-slice-selector {
    description
      "Grouping for Slice Selectors.";
    container slice-selectors {
      description
        "Container for Slice Selectors.";
      list slice-selector {
        key "id";
        description
          "List of Slice Selectors - this includes the default
           selector and others used for overriding the default.";
        leaf id {
          type uint16;
          description
            "A 16-bit ID to uniquely identify the Slice Selector.
             The Slice Selector with the lowest ID is the default
             selector.";
        }
        container mpls {
          description
            "Container for MPLS Slice Selector.";
          choice ss-mpls-type {
            description
              "Choices for MPLS Slice Selector.";
            case label-value {
              leaf label {
                type rt-types:mpls-label;
                description
                  "MPLS Slice Selector Label is explicitly
                   specified.";
              }
              uses ns-ss-mpls-label-location;
            }
            case label-ranges {
              list label-range {
                key "index";
                unique "start-label end-label";
                description
                  "MPLS Slice Selector Label is picked from a
                   specified set of label ranges.";
                leaf index {
                  type string;
                  description
                    "A string that uniquely identifies a label
                     range.";
                }
                leaf start-label {
                  type rt-types:mpls-label;
                  must '. <= ../end-label' {
                    error-message
                      "The start-label must be less than or equal "
                    + "to end-label";
                  }
                  description
                    "Label-range start.";
                }
                leaf end-label {
                  type rt-types:mpls-label;
                  must '. >= ../start-label' {
                    error-message
                      "The end-label must be greater than or equal "
                    + "to start-label";
                  }
                  description
                    "Label-range end.";
                }
                uses ns-ss-mpls-label-location;
              }
            }
          }
        }
        container ipv4 {
          description
            "Container for IPv4 Slice Selector.";
          leaf-list destination-prefix {
            type inet:ipv4-prefix;
            description
              "IPv4 Slice Selector is picked from a specified set of
               IPv4 destination prefixes.";
          }
        }
        container ipv6 {
          description
            "Container for IPv6 Slice Selector.";
          choice ss-ipv6-type {
            description
              "Choices for IPv6 Slice Selector.";
            case ipv6-destination {
              leaf-list destination-prefix {
                type inet:ipv6-prefix;
                description
                  "IPv6 Slice Selector is picked from a specified
                   set of IPv6 destination prefixes.";
              }
            }
            case ipv6-flow-label {
              container slid-flow-labels {
                description
                  "Container for a set of Slice IDs that are
                   encoded within the flow label.";
                list slid-flow-label {
                  key "slid";
                  description
                    "IPv6 Slice Selector is picked from a set of
                     Slice IDs that are encoded within the flow
                     label.";
                  leaf slid {
                    type inet:ipv6-flow-label;
                    description
                      "Slice ID encoded inside the IPv6 flow label.";
                  }
                  leaf bitmask {
                    type uint32;
                    description
                      "Bitmask to extract the encoded Slice ID from
                       the IPv6 flow label.";
                  }
                }
              }
            }
          }
        }
        leaf-list acl-ref {
          type ns-acl-ref;
          description
            "Slice Selection is done based on the specified list of
             ACLs.";
        }
      }
    }
  }

  /*
   * Grouping - Slice Resource Reservation
   */
  grouping ns-slice-resource-reservation {
    description
      "Grouping for Slice Resource Reservation.";
    container slice-resource-reservation {
      description
        "Container for Slice Resource Reservation.";
      leaf preference {
        type uint16;
        description
          "Slice control plane preference. A higher preference
           indicates a more favorable slice resource
           reservation than a lower preference.";
      }
      choice max-bw-type {
        description
          "Choice of maximum bandwidth specification.";
        case bw-value {
          leaf maximum-bandwidth {
            type uint64;
            description
              "The maximum bandwidth allocated to a network slice on
               the network resources - specified as absolute value.";
          }
        }
        case bw-percentage {
          leaf maximum-bandwidth-percent {
            type rt-types:percentage;
            description
              "The maximum bandwidth allocated to a network slice on
               the network resources - specified as percentage of
               link capacity.";
          }
        }
      }
      leaf-list shared-resource-groups {
        type uint32;
        description
          "List of shared resource groups that a network slice
           shares its allocated resources with.";
      }
      container protection {
        description
          "Container for network slice protection reservation.";
        leaf backup-slice-id {
          type uint32;
          description
            "The Slice ID that identifies the network slice used
             for backup paths that protect primary paths in a
             specific network slice.";
        }
        choice backup-bw-type {
          description
            "Choice of backup bandwidth specification.";
          case backup-bw-value {
            leaf backup-bandwidth {
              type uint64;
              description
                "The maximum bandwidth on a network resource that
                 is allocated for backup traffic - specified as
                 absolute value.";
            }
          }
          case backup-bw-percentage {
            leaf backup-bandwidth-percent {
              type rt-types:percentage;
              description
                "The maximum bandwidth on a network resource that
                 is allocated for backup traffic - specified as
                 percentage of the link capacity.";
            }
          }
        }
      }
    }
  }

  /*
   * Grouping - Slice-PHB
   */
  grouping ns-slice-phb {
    description
      "Grouping for Slice-PHB.";
    leaf slice-phb {
      type ns-phb-ref;
      description
        "Reference to a specific Slice-PHB from the list global
         Slice-PHBs.";
    }
  }

  /*
   * Grouping - Slice default profile override
   */
  grouping ns-slice-default-profile-override {
    description
      "Grouping of fields that are used to override the default
       profile of the network slice.";
    leaf slice-selector {
      type ns-ss-ref;
      description
        "Reference to a specific Slice Selector.";
    }
    uses ns-slice-phb;
  }

  /*
   * Grouping - Slice membership filter: Topology reference
   */
  grouping ns-slice-membership-topo-ref {
    description
      "Grouping for topology reference slice membership filter.";
    choice topo-ref-type {
      description
        "Choice of topology reference.";
      case algo-id {
        leaf algo-id {
          type uint8;
          description
            "Algorithm ID.";
        }
      }
      case te-topo-id {
        uses te-types:te-topology-identifier;
      }
    }
  }

  /*
   * Grouping - Slice membership filters: Custom topology
   */
  grouping ns-slice-membership-custom-topo {
    description
      "Grouping for custom topology slice membership filters.";
    leaf-list link-affinity {
      type string;
      description
        "Match-filter is a list of link affinities.";
    }
    leaf-list link-name {
      type string;
      description
        "Match-filter is a list of link names.";
    }
    leaf-list node-prefix {
      type inet:ip-prefix;
      description
        "Match-filter is a list of node IDs.";
    }
    leaf-list as {
      type inet:as-number;
      description
        "Match-filter is a list of AS numbers.";
    }
  }

  /*
   * Grouping - Slice membership filters
   */
  grouping ns-slice-membership-filters {
    description
      "Grouping for Slice Membership filters.";
    choice filter-type {
      description
        "Choice of filter type.";
      case topology-ref {
        uses ns-slice-membership-topo-ref;
      }
      case custom-topology {
        container include {
          description
            "Include policies.";
          uses ns-slice-membership-custom-topo;
        }
        container exclude {
          description
            "Exclude policies.";
          uses ns-slice-membership-custom-topo;
        }
      }
    }
  }

  /*
   * Grouping - Slice Membership
   */
  grouping ns-slice-membership {
    description
      "Grouping for 'Slice Membership'.";
    container slice-membership {
      description
        "Container for Slice Membership.";
      container filter-policies {
        description
          "Container for topology filtering policies.";
        list filter-policy {
          key "id";
          description
            "List of topology filtering policies.";
          leaf id {
            type uint16;
            description
              "A 16-bit ID that uniquely identifies the topology
               filtering policy.";
          }
          uses ns-slice-membership-filters;
          uses ns-slice-default-profile-override;
        }
      }
    }
  }

  /*
   * Grouping - Network Slice Per-Hop Behaviors (Slice-PHBs)
   */
  grouping ns-phbs {
    description
      "Grouping for Slice-PHBs.";
    container network-slice-phbs {
      description
        "Container for Slice-PHBs.";
      list network-slice-phb {
        key "id";
        description
          "List of Slice-PHBs.";
        leaf id {
          type uint16;
          description
            "A 16-bit ID that uniquely identifies the Slice-PHB.";
        }
        choice profile-type {
          description
            "Choice of PHB profile type.";
          case profile {
            description
              "Generic PHB profile available on the network
               element.";
            leaf profile {
              type string;
              description
                "Generic PHB profile identifier.";
            }
          }
          case custom-profile {
            description
              "Custom PHB profile.";
            choice guaranteed-rate-type {
              description
                "Guaranteed rate is the committed information rate
                 (CIR) of the Slice. The guaranteed rate also
                 determines the amount of excess (extra) bandwidth
                 that a group of Slices can share. Extra bandwidth
                 is allocated among the group in proportion to the
                 guaranteed rate of each Slice.";
              case rate {
                leaf guaranteed-rate {
                  type uint64;
                  description
                    "Guaranteed rate specified as absolute value.";
                }
              }
              case percentage {
                leaf guaranteed-rate-percent {
                  type rt-types:percentage;
                  description
                    "Guaranteed rate specified in percentage.";
                }
              }
            }
            choice shaping-rate-type {
              description
                "Shaping rate is the maximum bandwidth of the slice,
                 or the peak information rate (PIR) of a Slice.";
              case rate {
                leaf shaping-rate {
                  type uint64;
                  description
                    "Shaping rate specified as absolute value.";
                }
              }
              case percentage {
                leaf shaping-rate-percent {
                  type rt-types:percentage;
                  description
                    "Shaping rate specified in percentage.";
                }
              }
            }
            container classes {
              description
                "Container for classes.";
              list class {
                key class-id;
                description
                  "List of classes.";
                leaf class-id {
                  type string;
                  description
                    "A string to uniquely identify a class.";
                }
                leaf direction {
                  type identityref {
                    base s-phb-class-direction;
                  }
                  description
                    "Class direction.";
                }
                leaf priority {
                  type identityref {
                    base s-phb-class-priority;
                  }
                  description
                    "Priority of the class scheduler.  Only one Slice
                     class queue can be set as a strict-high priority
                     queue. Strict-high priority allocates the
                     scheduled bandwidth to the queue before any
                     other queue receives bandwidth. Other queues
                     receive the bandwidth that remains after the
                     strict-high queue has been serviced.";
                }
                choice guaranteed-rate-type {
                  description
                    "Guaranteed Rate is the Committed information
                     rate (CIR) of Slice class - specified as
                     absolute value or percentage.";
                  case rate {
                    leaf guaranteed-rate {
                      type uint64;
                      description
                        "Guaranteed rate specified as absolute
                         value.";
                    }
                  }
                  case percentage {
                    leaf guaranteed-rate-percent {
                      type rt-types:percentage;
                      description
                        "Guaranteed rate specified in percentage.";
                    }
                  }
                }
                leaf drop-probability {
                  type identityref {
                    base s-phb-class-drop-probability;
                  }
                  description
                    "Drop probability applied to packets exceeding
                     the CIR of the class queue.";
                }
                choice maximum-bandwidth-type {
                  description
                    "Maximum bandwidth is the Peak information
                     rate (PIR) of Slice class - specified as
                     absolute value or percentage.";
                  case rate {
                    leaf maximum-bandwidth {
                      type uint64;
                      description
                        "Maximum bandwidth specified as absolute
                         value.";
                    }
                  }
                  case percentage {
                    leaf maximum-bandwidth-percent {
                      type rt-types:percentage;
                      description
                        "Maximum bandwidth specified as percentage.";
                    }
                  }
                }
                choice delay-buffer-size-type {
                  description
                    "Size of the queue buffer as a percentage of the
                     dedicated buffer space - specified as value or
                     percentage.";
                  case value {
                    leaf delay-buffer-size {
                      type uint64;
                      description
                        "Delay buffer size.";
                    }
                  }
                  case percentage {
                    leaf delay-buffer-size-percent {
                      type rt-types:percentage;
                      description
                        "Delay buffer size specified as percentage.";
                    }
                  }
                }
              }
            }
          }
        }
      }
    }
  }

  /*
   * Grouping - Network Slice Per-Hop Definitions (Slice-PHDs)
   */
  grouping ns-entries {
    description
      "Grouping for Slice-PHDs.";
    container network-slices {
      description
        "Container for Slice-PHD entries (network-slices).";
      list network-slice {
        key "name";
        unique "id";
        description
          "List of network slices.";
        leaf name {
          type string;
          description
            "A string that uniquely identifies the network slice.";
        }
        leaf id {
          type uint32;
          description
            "A 32-bit ID that uniquely identifies the network
             slice.";
        }
        uses ns-slice-resource-reservation;
        uses ns-slice-selector;
        uses ns-slice-phb;
        uses ns-slice-membership;
      }
    }
  }

  /*
   * Top-level container - Network Slicing
   */
  container network-slicing {
    presence "Enable network slicing.";
    description
      "Top-level container for network slicing specific constructs
       on a network slicing capable node.";
    uses ns-phbs;
    uses ns-entries;
  }
}
