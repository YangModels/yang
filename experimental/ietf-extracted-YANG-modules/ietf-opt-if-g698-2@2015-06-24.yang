module ietf-opt-if-g698-2 {
     namespace "urn:ietf:params:xml:ns:yang:ietf-opt-if-g698-2";
     prefix ietf-opt-if-g698-2;

     import ietf-interfaces {
       prefix if;
     }

     organization
       "IETF NETMOD (NETCONF Data Modelling Language)
       Working Group";

     contact
       "WG Web:   <http://tools.ietf.org/wg/netmod/>
        WG List:  <mailto:netmod@ietf.org>

        WG Chair: Thomas Nadeau
                  <mailto:tnadeau@lucidvision.com>

        WG Chair: Juergen Schoenwaelder
                  <mailto:j.schoenwaelder@jacobs-university.de>

        Editor:   Dharini Hiremagalur
                  <mailto:dharinih@juniper.net>";

     description
       "This module contains a collection of YANG definitions for
        configuring Optical interfaces.

        Copyright (c) 2013 IETF Trust and the persons identified
        as authors of the code.  All rights reserved.

        Redistribution and use in source and binary forms, with or
        without modification, is permitted pursuant to, and
        subject to the license terms contained in, the Simplified
        BSD License set forth in Section 4.c of the IETF Trust's
        Legal Provisions Relating to IETF Documents
        (http://trustee.ietf.org/license-info).";

    revision "2015-06-24" {
           description
              "Revision 4.0";

           reference
              " draft-dharini-netmod-dwdm-if-yang 3.0";
    }
    revision "2015-02-24" {
           description
              "Revision 3.0";

           reference
              " draft-dharini-netmod-dwdm-if-yang 3.0";
    }
    revision "2014-11-10" {
           description
              "Revision 2.0";
           reference
              " ";
    }
    revision "2014-10-14" {
           description
              "Revision 1.0";
            reference
              " ";
    }
    revision "2014-05-10" {
           description
               "Initial revision.";
           reference
               "RFC XXXX: A YANG Data Model for Optical
                Management of an Interface for g.698.2
                support";
    }

      grouping optIfOChApplicationCode  {
             description "Application code entity.";
             leaf applicationCodeId {
                type uint8 {
                      range "1..255";
                }
                description
                      "Id for the Application code";
             }
             leaf applicationCodeType {
                type uint8 {
                      range "0..1";
             }
               description
                      "Type for the Application code
                        0 - Standard, 1 - Proprietory
                        When the Type is Proprietory, then the
                        first 6 octets of the applicationCode
                        will be the OUI (organizationally unique
                        identifier)";

             }
             leaf applicationCodeLength {
                type uint8 {
                      range "1..255";
                }
                description
                      "Number of octets in the Application code";

             }
             leaf applicationCode {
                type string {
                      length "1..255";
                }
                description "This parameter indicates the
                     transceiver application code at Ss and Rs as
                     defined in [ITU.G698.2] Chapter 5.3, that
                     is/should be used by this interface.
                     The optIfOChApplicationsCodeList has all the
                     application codes supported by this
                     interface.";

             }
      }

      grouping optIfOChApplicationCodeList {
        description "List of Application codes group.";
        leaf numberApplicationCodesSupported {
            type uint32;
            description "Number of Application codes
                         supported by this interface";
         }
        list applicationCodeList {
            key "applicationCodeId";
            description "List of the application codes";
            uses optIfOChApplicationCode;
        }
      }
     grouping optIfOChPower {
        description "Interface optical Power";
        leaf outputPower {
            type int32;
            units ".01dbm";
            description "The output power for this interface in
                          .01 dBm.";
        }

        leaf inputPower {
             type int32;
             units ".01dbm";
             config false;
             description "The current input power of this
                   interface";
        }
     }

      grouping optIfOChCentralFrequency {
        description "Interface Central Frequency";
          leaf  centralFrequency {
            type uint32;
            description "This parameter indicate This parameter
                    indicates the frequency of this interface ";

           }
     }

      notification optIfOChCentralFrequencyChange {
         description "A change of Central Frequency has been
                      detected.";
         leaf "if-name" {
             type leafref {
                 path "/if:interfaces/if:interface/if:name";
             }
             description "Interface name";
         }
         container newCentralFrequency {
                description "The new Central Frequency of the
                             interface";
                uses optIfOChCentralFrequency;
         }
      }

      notification optIfOChApplicationCodeChange {
         description "A change of Application code has been
                      detected.";
         leaf "if-name" {
             type leafref {
                 path "/if:interfaces/if:interface/if:name";
             }
             description "Interface name";
         }
         container newApplicationCode {
            description "The new application code for the
                interface";
            uses optIfOChApplicationCode;
         }
      }

      augment "/if:interfaces/if:interface" {
        description "Parameters for an optical interface";
        container optIfOChRsSs {
           description "RsSs path configuration for an interface";
           container ifCurrentApplicationCode {
                description "Current Application code of the
                             interface";
                uses optIfOChApplicationCode;
            }

            container ifSupportedApplicationCodes {
                config false;
                description "Supported Application codes of
                             the interface";
                uses optIfOChApplicationCodeList;
            }

            uses optIfOChPower;

            uses optIfOChCentralFrequency;

         }
      }
   }
