module ietf-sd-onos-service-l3vpn { 
  namespace "urn:ietf:params:xml:ns:yang:ietf-sd-onos-service-l3vpn"; 
  prefix l3vpn ; 
  /* 
  import ietf-inet-types{ 
    prefix inet;  
  } 
  import ietf-yang-types { 
    prefix yang-types; 
  } 
  */ 
  import ietf-sd-onos-service-types { 
    prefix service-types; 
  } 
  import ietf-sd-onos-common-types { 
    prefix types; 
  } 

  organization "";  
  contact ""; 

  description  
    "L3vpn configuration model in ONOS."; 

  revision "2015-12-16" { 
    reference ""; 
  } 

  container service { 
    description  
      "Root level of L3vpn service module."; 
    container l3vpn-cfg { 
      description  
        "L3vpn configuration model in ONOS."; 
      list vpn-cfg { 
        key name; 
        description  
          "vpn configuration parameter list."; 
        uses l3vpn; 
      } 
    } 
    container service-paths { 
      description  
        "The service path of the l3 vpn."; 
      list service-path{ 
        key "service-id source-ne-id source-ac-id destination-ne-id 
destination-ac-id"; 
        description  
          "The list of service path."; 
        uses service-types:service-path; 
      } 
    } 
  } 

  grouping l3vpn { 
    description  
      "The configuration module of l3 vpn."; 
    leaf name { 
      type string ; 
      mandatory true; 
      description "name of snc eline." ; 
    } 
    leaf id { 
      type uint32 ; 
      mandatory true; 
      description "ID of snc eline." ; 
    } 
    leaf user-label { 
      type string ; 
      description "user label of snc eline." ; 
    } 
    leaf parent-ncd-id { 
      type string ; 
      description "parent ncd id." ; 
    } 

    leaf admin-status { 
      type types:admin-status; 
      description "administration status." ; 
    } 
    leaf operate-status { 
      type types:operate-status; 
      description "operation status." ; 
    } 

    uses service-type-grouping; 
    container acess-information { 
      description "access information of the l3 vpn." ;                   
      list access-circuit { 
        key "id"; 
        description "list of access circuit." ; 
        uses service-types:l3-ac; 
      } 
    } 

    container protect-policy{ 
      description "L3VPN Service protect policy." ; 
      uses service-types:protect-policy; 
    } 
    container tunnel-service { 
      description "tunnel service." ; 
      uses service-types:tunnel-service; 
    }  
  } 

  grouping service-type-grouping { 
    description "Basic service type" ; 
    leaf service-topology { 
      type enumeration { 
        enum full-mesh { 
          value 1 ; 
          description "full-mesh." ; 
        } 
        enum hub-spoke { 
          value 2 ; 
          description "hub-spoke." ; 
        } 
      } 
      default full-mesh; 
      description "service topology type." ; 
    } 
  } 

  rpc create-l3vpn-instance { 
    description "Create l3vpn instance." ; 
    input { 
      container l3vpn-instance { 
        description "Create l3vpn instance." ; 
        uses l3vpn; 
      } 
    } 
  } 

  rpc delete-l3vpn-instance { 
    description "Delete l3vpn instance." ; 
    input { 
      leaf l3vpn-id { 
        type string; 
        description "vpn id." ; 
      } 
    } 
  } 

  rpc close-l3vpn { 
      input { 
          leaf l3vpn-id { 
              type string; 
        description "vpn id." ; 
          } 
          container ac-status {  
        description "Access status of the vpn." ; 
              list acs{ 
                  key "id"; 
          description "Access information." ; 
                  leaf id { 
                      type string; 
            description "Access id." ; 
                  } 
                  leaf admin-status { 
                      type types:admin-status; 
            description "Administration status." ; 
                  }                     
              } 
          } 
      } 
  }   

  rpc modify-l3vpn-instance-basic { 
    input { 
      leaf l3vpn-id { 
        type string; 
        description "vpn id." ; 
      } 
      leaf user-label { 
        type string ; 
      } 
    } 
  } 

  rpc modify-l3vpn-instance-ac-qos { 
    input { 
      leaf l3vpn-id { 
        type string; 
      } 
      container ac-qos { 
        list acs{ 
            key "id"; 
            leaf id { 
                type string; 
            } 
            container qos-policy {   
                container qos-if-cars {          
                    list qos-if-car { 
                       key "direction"; 
                       uses service-types:qos-if-car; 
                    } 
                } 
            }                     
        } 
      } 
    } 
  } 

  rpc modify-l3vpn-instance-connection { 
    input { 
      leaf l3vpn-id { 
        type string; 
      } 
      container ac-connection { 
        list acs{ 
          leaf id { 
            description "ac id." ; 
            type string ; 
          } 
          container connection { 
            description "CE to PE  connection." ; 
            uses service-types:connection; 
          } 
        } 
      } 
    } 
  } 
rpc inquire-l3vpn-instance-work-path { 
     input { 
           leaf service-id { 
             type string; 
           } 
            leaf ingress-ne-id {            
              type string ; 
            } 
            leaf destination-ne-id {                                                      
              type string ; 
            } 
            leaf ingress-ac-id {            
              type string ; 
            } 
            leaf destination-ac-id {                                                      
              type string ; 
            }  
            leaf path-layer { 
               type string ; 
            } 
            leaf path-role { 
               type string ; 
            }            
    } 
    output { 
        container service-path { 
           leaf service-id { 
             type string; 
           } 
            leaf ingress-ne-id {            
              type string ; 
            } 
            leaf destination-ne-id {                                                      
              type string ; 
            } 
            leaf ingress-ac-id {            
              type string ; 
            } 
            leaf destination-ac-id {                                                      
              type string ; 
            }  
            leaf path-layer { 
               type string ; 
            } 
            leaf path-role { 
               type string ; 
            }              
            list path-list { 
                key "ne-id"; 
                leaf ne-id { 
                   type string; 
                } 
                leaf ingress-ltp-id { 
                   type string; 
                } 
                leaf backward-peer-id { 
                   type string; 
                }  
                leaf egress-ltp-id { 
                   type string; 
                } 
                leaf forward-peer-id { 
                   type string; 
                } 
            }  
        }  
    } 
  } 
  */ 
}
