module ietf-mpls-msd {
  yang-version 1.1;
  namespace "urn:ietf:params:xml:ns:yang:ietf-mpls-msd";
  prefix mpls-msd;

  import ietf-routing {
    prefix rt;
    reference
      "RFC 8349: A YANG Data Model for Routing
                 Management (NMDA Version)";
  }

  import ietf-mpls {
    prefix mpls;
    reference "RFC 8960: A YANG Data Model for MPLS Base";
  }

  organization
    "IETF MPLS - MPLS Working Group";
  contact
    "WG Web:   <https://tools.ietf.org/wg/mpls/>
     WG List:  <mailto:mpls@ietf.org>

     Author:    Yingzhen Qu
               <mailto:yingzhen.qu@futurewei.com>
     Author:    Acee Lindem
               <mailto:acee@cisco.com>
     Author:    Stephane Litkowski
               <mailto:slitkows.ietf@gmail.com>
     Author:    Jeff Tantsura
               <mailto:jefftant.ietf@gmail.com>

    ";
  description
    "The YANG module augments the base MPLS model, and it is to
     manage different types of Maximum SID Depth (MSD).

     This YANG model conforms to the Network Management
     Datastore Architecture (NMDA) as described in RFC 8342.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  reference "RFC XXXX: YANG Data Model for Segment Routing.";

  revision 2021-08-02 {
    description
      "Initial Version";
    reference "RFC XXXX: YANG Data Model for Segment Routing.";
  }

  identity msd-base-type {
    description
      "Base identity for Maximum SID Depth (MSD) Type";
  }

  identity msd-mpls {
    base msd-base-type;
    description
      "Base MPLS Imposition MSD.";
    reference
      "RFC 8491: Singling Maximum SID Depth (MSD) using IS-IS.";
  }

  identity msd-erld {
    base msd-base-type;
    description
      "msd-erld is defined to advertise the Entropy Readable
       Label Depth (ERLD).";
    reference
      "RFC 8662: Entropy Label for Source Packet Routing in
                 Networking (SPRING) Tunnels";
  }

  augment "/rt:routing/mpls:mpls" {
    description
      "This module augments MPLS data model (RFC 8960)
       with node MSD.";
    container node-msd {
      config false;
      description
        "Maximum SID Depth (MSD) operational state.";
      list node-msds {
        leaf msd-type {
          type identityref {
            base msd-base-type;
          }
          description
            "MSD types";
        }
        leaf msd-value {
          type uint8;
          description
            "MSD value, in the range of 0-255.";
        }
        description
          "Node MSD is the smallest link MSD supported by
           the node.";
      }
    }
  }

  augment "/rt:routing/mpls:mpls/mpls:interfaces/mpls:interface" {
    description
      "This module augments MPLS data model (RFC 8960)
       with link MSD.";
    container link-msd {
      config false;
      description
        "Maximum SID Depth (MSD) interface operational state.";
      list link-msds {
        leaf msd-type {
          type identityref {
            base msd-base-type;
          }
          description
            "MSD type";
        }
        leaf msd-value {
          type uint8;
          description
            "MSD value, in the range of 0-255.";
        }
        description
          "List of link MSDs";
      }
    }
  }
}
