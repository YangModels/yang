module ietf-supa-l3vpn {
  namespace "urn:ietf:params:xml:ns:yang:ietf-supa-l3vpn";
  // replace with IANA namespace when assigned
  prefix l3vpn;
  organization "IETF";
  contact
    "Editor: Dacheng Zhang
    dacheng.zdc@alibaba-inc.com

    Adel Zaalouk
    adel.ietf@gmail.com

    Kostas Pentikousis
    k.pentikousis@eict.de
    ";

  description
    "This YANG module defines a generic service
    configuration model for L3VPN (Layer 3 Virtual
    Private Network), based on which programmers can
    develop applications to configure L3VPN instances.";
  revision 2015-02-04 {
    description
      "Initial revision.";
    reference "RFC4364, RFC7277";
  }

  list l3vpn-instance {
    key "instance-name";
    description "Indicates the name of the L3VPN instance";

    leaf instance-name {
      type string ;
      description "L3VPN instance name";
    }

    leaf service-type {
      type enumeration {
        enum full-mesh {
          value "0";
          description "full-mesh";
        }
        enum hub-spoke {
          value "1";
          description "hub-spoke";
        }
      }
      default "full-mesh";
      description "Topology type";
    }

    leaf address-family-type{
      type enumeration {
        enum ipv4uni {
          value "0";
          description "ipv4 unicast";
        }
        enum ipv6uni {
          value "1";
          description "ipv6 unicast";
        }
      }
      default "ipv4uni";
      description " Address family type: IPv4 or IPv6";
    }

    list access-interface {
      key "access-interface";
      description "Access interface ID";

      leaf access-interface {
        type if:interface-ref;
        description "Access interface ID";
      }

      leaf access-interface-address {
        type inet:ip-prefix;
        description " Access interface address, IPv4 or IPv6";
      }

      leaf role {
        type enumeration {
          enum edge-if {
            value "0";
            description "edge interface";
            }
          enum center-if {
            when "../../service-type = 'hub-spoke'";
            value "1";
            description "center interface";
          }
        }
        mandatory true;
        description
          "center-if is only available in hub-spoke mode;
          There are two scenarios: in full mesh mode,
          the role of all the access-interface is edge-if,
          while in hub-spoke mode, the role of the
          interface of hub node is ceter-if, the one
          of spoke node is edge-if";
      }

      leaf user-name {
        type string;
        mandatory true;
        description "User name for this access interface";
      }

      leaf user-password {
        type string;
        mandatory true;
        description "User password for the access interface.
        User name and password are listed here because VPN
        need the authentication, one typical way is to
        use user name and password, so that in CE dynamic
        migration case, CEs are able to access with
        authentication regardless location.";
      }

      leaf physical-node {
        type string;
        mandatory true;
        description "This is the physical node ID
        of access PE";
      }

      leaf physical-access-interface {
        type if:interface-ref;
        mandatory true;
        description " This is the Physical access
        interface of access PE.";
      }

      container protocol-id {
        description "The routing protocol between PE and CE.";

        leaf protocol-type {
          type enumeration {
            enum bgp {
              value "0";
              description "bgp";
            }
            enum ospf {
              value "1";
              description "ospf";
            }
            enum isis {
              value "2";
              description "isis";
            }
            enum rip {
              value "3";
              description "rip";
            }
            enum static {
              value "4";
              description "static";
            }
            enum eigrp {
              value "5";
              description "eigrp";
            }
          }
          default "ospf";
          description "Protocol type";
        }

        container bgp-attribute {
          when "../../protocol-type = 'bgp'"
          leaf remote-as-number {
            type string {
              length "1..11";
            }
            default "0";
            description "Valid only when protocol is BGP.";
          }

          leaf remote-peer-address {
            type string {
            }
            mandatory true;
            description "Valid only when protocol is BGP.";
          }
          description "This part defines the attribute of BGP.";
        }

        container igp-attribute {
          when "../../protocol-type = 'ospf' or 'isis'
           or 'rip' or 'static'"
          leaf protocol-id {
            type uint32 {
            }
            default "0";
            description "Valid only when protocol is IGP;
                         it can be AS number.";
          }
          description "This part defines the attribute of IGP.";
        }
      }
    }
  }
}
