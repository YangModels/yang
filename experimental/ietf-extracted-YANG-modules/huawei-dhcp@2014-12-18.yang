module huawei-dhcp {
        namespace "urn:ietf:params:xml:ns:yang:ietf-dhcp";
        prefix "dhcp";

        import ietf-inet-types {
       prefix "inet";
    }

        contact "leo.liubing@huawei.com" "loukunkun@huawei.com";
        description "The module for implementing DHCP protocol";
        revision "2014-12-18";

        container relay {

                container dhcpRelayIfCfgs {

                        list dhcpRelayIfCfg {

                                key "ifName";

                                leaf ifName {
                                    description "Specify the interface name that dhcp relay configured on";
                                        type "string";
                                        config "true";
                                }

                                leaf enable {
                                        description "Enable or disable dhcp relay function";
                                        type "boolean";
                                        default "false";
                                        config "true";
                                }

                                leaf serverGroupName {
                                        description "Server Group Name";
                                        type string;
                                        config "true";
                                }

                                leaf-list serverAddress {
                                    description "DHCP relay destination server IP address";
                                        type inet:ipv4-address;
                                        config "true";
                                }

                        }

                }

                container dhcpRelayServerGroups {

                        list dhcpRelayServerGroup {

                                key "serverGroupName";

                                 description "DHCP relay server group ";

                                 leaf serverGroupName {
                                        description "name of server group";
                                        type string;
                                        config "true";
                                }

                                leaf vpnName {
                                        description "VPN name for server group";
                                        type string;
                                        config "true";
                                }

                                leaf gateway {
                                        description "gateway for server group";
                                        type inet:ipv4-address;
                                        config "true";
                                }
                                leaf-list serverAddress {
                                    description "DHCP relay destination server IP address";
                                        type inet:ipv4-address;
                                        config "true";
                                }

                                container dhcpRelaySerGrpStats {

                                        list dhcpRelaySerGrpStats {
                                            description "DHCP relay server group packet statistics ";
                                                key "serverIpAddr";

                                                 leaf serverIpAddr {
                                                    type inet:ipv4-address;
                                                }
                                                leaf pktsReceiveFromClient {
                                                    type "uint32";
                                                        config "false";
                                                }
                                                leaf discoverPktsReceive {
                                                    type "uint32";
                                                        config "false";
                                                }
                                                leaf requestPktsReceive {
                                                    type "uint32";
                                                        config "false";
                                                }
                                                leaf releasePktsReceive {
                                                    type "uint32";
                                                        config "false";
                                                }
                                                leaf informPktsRecevie {
                                                    type "uint32";
                                                        config "false";
                                                }
                                                leaf declinePktsReceive {
                                                    type "uint32";
                                                        config "false";
                                                }
                                                leaf pktsReceiveFromServers {
                                                    type "uint32";
                                                        config "false";
                                                }
                                                leaf offerPktsReceive {
                                                    type "uint32";
                                                        config "false";
                                                }
                                                leaf ackPktsReceive {
                                                    type "uint32";
                                                        config "false";
                                                }
                                                leaf nakPktsReceive {
                                                    type "uint32";
                                                        config "false";
                                                }
                                                leaf pktsSentToServers {
                                                    type "uint32";
                                                        config "false";
                                                }
                                                leaf pktsSentToClients {
                                                    type "uint32";
                                                        config "false";
                                                }
                                                leaf unicastPktsSentToClients {
                                                    type "uint32";
                                                        config "false";
                                                }
                                                leaf broadcastPktsSentToClients {
                                                    type "uint32";
                                                        config "false";
                                                }
                                        }

                                }

                        }

                }

                container dhcpRelayStatistics {

                         leaf badPacketsRecvd {
                            type "uint32";
                                config "false";
                        }
                        leaf packetsRecvdFromClient {
                            type "uint32";
                                config "false";
                        }
                        leaf discoverPacketsRecvd {
                            type "uint32";
                                config "false";
                        }
                        leaf requestPacketsRecvd {
                            type "uint32";
                                config "false";
                        }
                        leaf informPacketsRecvd {
                            type "uint32";
                                config "false";
                        }
                        leaf declinePacketsRecvd {
                            type "uint32";
                                config "false";
                        }
                        leaf releasePacketsRecvd {
                            type "uint32";
                                config "false";
                        }
                        leaf packetsRecvdFromServers {
                            type "uint32";
                                config "false";
                        }
                        leaf offerPacketsRecvd {
                            type "uint32";
                                config "false";
                        }
                        leaf ackPacketsRecvd {
                            type "uint32";
                                config "false";
                        }
                        leaf nakPacketsRecvd {
                            type "uint32";
                                config "false";
                        }
                        leaf packetsSentToServers {
                            type "uint32";
                                config "false";
                        }
                        leaf packetsSentToClients {
                            type "uint32";
                                config "false";
                        }
                        leaf unicastPacketsSentToClients {
                            type "uint32";
                                config "false";
                        }
                        leaf broadcastPacketsSentToClients {
                            type "uint32";
                                config "false";
                        }
                        leaf releasePacketsSentToServers {
                            type "uint32";
                                config "false";
                        }
                        leaf sendRenewPacket {
                            type "uint32";
                                config "false";
                        }
                }

        }

        container server {

                container common {

                         leaf pingPacketNumber{
                                description "Ping packet number";
                                type uint8 {
                                        range "0..10";
                                }
                                config "true";
                                default "0";
                        }
                        leaf pingPacketTimeOut {
                                description "Ping packet timeout";
                                type uint16 {
                                        range "0..10000";
                                }
                                config "true";
                                default "500";
                        }
                }

                container globalIpPool {

                        list globalIpPool {

                                key "ipPoolName";

                                leaf ipPoolName {
                                        description "IP pool name";
                                        type string {
                                                length "1..64";
                                        }
                                        config "true";
                                }
                                leaf vpnInstance {
                                        description "VPN name";
                                        type string {
                                                length "1..31";
                                        }
                                        config "true";
                                }

                                container gatewayIp {
                                         leaf gatewayIp {
                                                description "Gateway IP Address";
                                                type inet:ipv4-address;
                                                config "true";
                                        }
                                        leaf gatewayMask {
                                                description "Gateway IP Address Mask";
                                                type inet:ipv4-address;
                                                config "true";
                                        }
                                }

                                container sections {

                                        list section {

                                                key "sectionIndex";

                                                 leaf sectionIndex {
                                                        description "Section Index";
                                                        type uint16 {
                                                                range "0..255";
                                                        }
                                                        config "true";

                                                }
                                                leaf sectionStartIp {
                                                        description "IP Address";
                                                        type inet:ipv4-address;
                                                        config "true";
                                                        mandatory "true";
                                                }
                                                leaf sectionEndIp {
                                                        description "IP Address";
                                                        config "true";
                                                        type inet:ipv4-address;
                                                        mandatory "false";
                                                }

                                                container ipPoolSectionStat {

                                                         leaf usedIpCount {
                                                                description "Used Ip Count";
                                                                type uint32;
                                                                config "false";
                                                        }
                                                        leaf idleIpCount {
                                                                description "Idle Ip Count";
                                                                type uint32;
                                                                config "false";
                                                        }
                                                        leaf conflictIpCount {
                                                                description "Conflict Ip Count";
                                                                type uint32;
                                                                config "false";
                                                        }
                                                        leaf totalIpCount {
                                                                description "Total Ip Count";
                                                                type uint32;
                                                                config "false";
                                                        }
                                                }

                                        }

                                }

                                container leaseTime {
                                    description "Specifies the lease time, option code is 51.";
                                         leaf day {
                                                description "Day";
                                                type uint16 {
                                                        range "0..49710";
                                                }
                                                config "true";
                                                default "1";
                                        }
                                        leaf hour {
                                                description "Hour";
                                                type uint8  {
                                                        range "0..23";
                                                }
                                                config "true";
                                                default "0";
                                        }
                                        leaf minute {
                                                description "Minute";
                                                type uint8 {
                                                        range "0..59";
                                                }
                                                config "true";
                                                default "0";
                                        }
                                }

                                leaf-list domainNameServer {
                                    description "Specifies the domain name server, option code is 5.";
                                        type inet:ipv4-address;
                                        config "true";
                                }

                                leaf domainName {
                                    description "Specifies the domain name, option code is 15.";
                                        type string {
                                                length "1..255";
                                        }
                                        config "true";
                                }

                                leaf-list NbnsServer {
                                    description "Specifies the NetBIOS name server, option code is 44.";
                                        type inet:ipv4-address;
                                        config "true";
                                }

                                leaf NbNodeType {
                                    description "Specifies the NetBIOS node type, option code is 46.";
                                        type enumeration {
                                                enum B-node {
                                                        value "1";
                                                }
                                                enum P-node {
                                                        value "2";
                                                }
                                                enum M-node {
                                                    value "4";
                                                }
                                                enum H-node {
                                                    value "8";
                                                }
                                        }
                                        config "true";
                                }

                            container UserDefOptions {

                                    list UserDefOption {
                                            description "Specifieds the user defined DHCP options";
                                            key "optionCode";
                                             leaf optionCode {
                                                    description "The option code of the user defined option";
                                                    type uint8 {
                                                            range "2 | 4..5 | 7..14 | 16..43 | 47..49 | 56 | 62..81 | 83..254";
                                                    }
                                                    config "true";
                                            }

                                            leaf-list ipAddress {
                                                description "IP address list";
                                                    type inet:ipv4-address;
                                                    config "true";
                                            }

                                            leaf optionString {
                                                description "User defined option string";
                                                    type string {
                                                        length "1..254";
                                                }
                                                    config "true";
                                            }

                                            leaf optionHex {
                                                description "User defined option HEX string";
                                                    type string {
                                                        length "2..508";
                                                }
                                                    config "true";
                                            }

                                    }
                            }

                                container ipPoolStat {

                                         leaf usedIpCount {
                                                description "Used Ip Count";
                                                type uint32;
                                                config "false";
                                        }
                                        leaf idleIpCount {
                                                description "Idle Ip Count";
                                                type uint32;
                                                config "false";
                                        }
                                        leaf conflictIpCount {
                                                description "Conflict Ip Count";
                                                type uint32;
                                                config "false";
                                        }
                                        leaf totalIpCount {
                                                description "Total Ip Count";
                                                type uint32;
                                                config "false";
                                        }
                                }

                        }

                }

                container packetStatistics {

                         leaf clientRequestCount {
                                description "Client Request Count";
                                type uint32;
                                config "false";
                        }
                        leaf discoverCount {
                                description "Discover Count";
                                type uint32;
                                config "false";
                        }
                        leaf requestCount {
                                description "Request Count";
                                type uint32;
                                config "false";
                        }
                        leaf declineCount {
                                description "Decline Count";
                                type uint32;
                                config "false";
                        }
                        leaf releaseCount {
                                description "Release Count";
                                type uint32;
                                config "false";
                        }
                        leaf informCount {
                                description "Inform Count";
                                type uint32;
                                config "false";
                        }
                        leaf serverReplyCount {
                                description "Server Reply Count";
                                type uint32;
                                config "false";
                        }
                        leaf offerCount {
                                description "Offer Count";
                                type uint32;
                                config "false";
                        }
                        leaf ackCount {
                                description "Ack Count";
                                type uint32;
                                config "false";
                        }
                        leaf nakCount {
                                description "Nak Count";
                                type uint32;
                                config "false";
                        }
                }

        }

        container client {

                container dhcpClientIf {

                        list dhcpClientIf {

                                key "ifName";

                                leaf ifName {
                                    description "Specify the interface name that dhcp client configured on";
                                        type "string";
                                        config "true";
                                }

                                leaf enable {
                                        description "Enable or disable dhcp client function";
                                        type "boolean";
                                        default "false";
                                        config "true";
                                }

                                container dhcpClientStatus {

                                    description "Specify the status of DHCP client on the interface";

                                    leaf status {
                                            description "Specify the status of DHCP client on the interface";
                                                type enumeration {
                                                    enum Init;
                                                        enum Discoverying;
                                                        enum Offered;
                                                        enum Requesting;
                                                        enum Acked;
                                                }
                                                config "false";
                                        }

                                    leaf clientIpAddr {
                                            description "Specify the IP address obtained from DHCP server on the interface";
                                                type inet:ipv4-address;
                                                config "false";
                                        }

                                        leaf-list dnsServerIpAddr {
                                        description "Specify the DNS server IP address obtained from DHCP server on the interface";
                                                type inet:ipv4-address;
                                                config "false";
                                    }

                                }

                                container dhcpClientIfStatistics {

                                        description "Specify the statistics of DHCP client send or receive packets on the interface";

                                    leaf discoverCount {
                                        description "Discover Count";
                                        type uint32;
                                        config "false";
                                }

                                        leaf requestCount {
                                            description "Request Count";
                                                type uint32;
                                                config "false";
                                        }

                                        leaf declineCount {
                                            description "Decline Count";
                                                type uint32;
                                                config "false";
                                        }

                                        leaf releaseCount {
                                            description "Release Count";
                                                type uint32;
                                                config "false";
                                        }

                                        leaf informCount {
                                            description "Inform Count";
                                                type uint32;
                                                config "false";
                                        }

                                    leaf offerCount {
                                            description "Offer Count";
                                                type uint32;
                                                config "false";
                                        }

                                        leaf ackCount {
                                            description "Ack Count";
                                                type uint32;
                                                config "false";
                                        }

                                        leaf nakCount {
                                            description "Nak Count";
                                                type uint32;
                                                config "false";
                                        }

                                }

                        }

                }

        }

}
