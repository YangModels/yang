module ietf-bulk-notification {
  yang-version 1.1;
  namespace "urn:ietf:params:xml:ns:yang:ietf-bulk-notification";
  prefix bn;

  import ietf-yang-structure-ext {
    prefix sx;
  }
  import ietf-notification-messages {
    prefix nm;
  }

  organization
    "IETF NETCONF (Network Configuration) Working Group";
  contact
    "";
  description
    "NETCONF Protocol Data Types and Protocol Operations.

     Copyright (c) 2011 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6241; see
     the RFC itself for full legal notices.";

  revision 2019-09-23 {
    description
      "Initial revision";
    reference
      "RFC XXXX: Bulk Subscription to YANG Event Notification";
  }

  sx:augment-structure "/nm:message/nm:message-header" {
     leaf group-id {
      type string;
      description
        "To identify the group to which a set of notifications belongs.";
    }
    leaf compression-algorithm {
      type string;
      description
        "The technology with which an originator compress bytestream
         contents.";
    }
    description
      "Group related informations are added to the 'message-header' of
       the ietf-notification-messages to identify the group to which a
       set of notifications belongs and compression algorithms used by
       the publisher.";
  }
}
