module ietf-lime-bfd-extension{
      namespace "urn:ietf:params:xml:ns:yang:lime-bfd-extension";
     prefix limebfd;

     import ietf-gen-oam  {
       prefix goam;
     }

     import ietf-bfd {
      prefix bfd;
     }

         import ietf-interfaces {
          prefix if;
         }

        organization
        "IETF BFD Working Group";
        contact
    "WG List:   <mailto:bfd@ietf.org>
     Editor:";

    description
    "This YANG Model extends the technology independent
    YANG model for OAM with BFD technology specifics.";

     revision 2014-08-30 {
       description
       "Initial revision.";
           reference "";
     }

      identity bfd{
       base goam:technology-types;
       description
        "bfd type";
      }

   identity technology-sub-type {
     description
     "certain implementations such as bfd can have different
         encapsulation types such as ip/udp, pw-ach and so on.
     Instead of defining separate models for each
     encapsulation, we define a technology sub-type to
     further identify different encapsulations. Technology
     sub-type is associated at the MA level";
     }

  identity technology-sub-type-sh-udp {
   base technology-sub-type;
     description
    "technology sub-type is single
        hop with IP/UDP encapsulation";
     }

   identity technology-sub-type-mh-udp {
    base technology-sub-type;
  description
  "technology sub-type is multiple
  hop with IP/UDP encapsulation";
     }

   identity technology-sub-type-sh-ach {
     base technology-sub-type;
    description
    "technology sub-type is single
        hop with PW-ACH encapsulation";
     }

   identity technology-sub-type-mh-ach {
    base technology-sub-type;
    description
    "technology sub-type is multiple hop
        with PW-ACH encapsulation";
     }

grouping tx-rx-ttl{
 description
 "bfd tx ttl";

  leaf tx-ttl{
   type uint8;
   description
   "tx ttl.";
  }
  leaf rx-ttl{
   type uint8;
   description
   "rx ttl.";
  }
}

feature bfd-authentication {
      description "BFD authentication supported";
    }

augment "/goam:domains/goam:domain/goam:MAs/goam:MA"{
    when "goam:technology = 'bfd'"
         {description
         "when goam:technology = bfd.";}
          leaf technology-sub-type {
            type identityref {
              base technology-sub-type;
            }
                        description
                        "technology sub-type such as
                        single hop udp, multiple hop udp,
                        single hop ach, multiple hop ach.";
          }
    description
        "augment the MA with bfd parameters.";
        }

augment "/goam:domains/goam:domain/goam:MAs/goam:MA"
+"/goam:MEP/goam:session"{
    when "goam:technology = 'bfd'"
         {description
         "when goam:technology = bfd.";}
 leaf admin-down {
      type boolean;
      default false;
      description
  "Is the BFD session administratively down";
               }

uses bfd:bfd-grouping-common-cfg-parms;

description
"augment the session with bfd parameters.";
}

augment "/goam:domains/goam:domain/goam:MAs/goam:MA"
+"/goam:MEP/goam:session"{
 when "technology-sub-type = 'technology-sub-type-mh-udp'
   or 'technology-sub-type-mh-ach'"{
   description
   "when technology sub type = techonlogy sub type mh udp
   or technology sub type = technology-sub-type-mh-ach.";
   }
   uses tx-rx-ttl;
   description
   "augment the session with bfd parameters.";
}

augment "/goam:domains/goam:domain/goam:MAs/goam:MA"
+"/goam:MEP/goam:session/goam:connectivity-context"{
 when "goam:technology = 'bfd'"{
  description
  "when goam:techolgoy =bfd.";}
       case connectivity-context-bfd {
        leaf local-discriminator {
         type uint32;
 description
 "local discriminator";
        }
leaf remote-discriminator{
 type uint32;

 description
 "remote-discriminator";
}
       }
           description
           "augment the connectivity-context with
           bfd parameters.";
      }

augment "/goam:domains/goam:domain/goam:MAs/goam:MA"
+"/goam:MEP/goam:session/goam:outgoing-interface"{
  when "technology-sub-type = 'technology-sub-type-sh-udp'
   or 'technology-sub-type-sh-ach'"{
  description
  "when technology-sub-type = 'technology-sub-type-sh-udp'
   or 'technology-sub-type-sh-ach.";
   }
uses bfd:bfd-grouping-common-cfg-parms;
uses bfd:bfd-grouping-echo-cfg-parms;
 description
 "augment the outgoing interface with bfd parameters.";
}
notification state-change-notification
{
  uses bfd:bfd-notification-parms;
   leaf interface {
   type if:interface-ref;
   description "Interface to which this BFD session belongs to";
   }
   leaf echo-enabled {
    type boolean;
    description "Was echo enabled for BFD";
   }
 description
 "state change notification.";
}
}
