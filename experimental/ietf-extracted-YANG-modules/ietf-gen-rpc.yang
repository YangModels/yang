module ietf-gen-rpc {
     namespace "urn:ietf:params:xml:ns:yang:ietf-gen-rpc";
     prefix goam-rpc;
   import ietf-interfaces {
   prefix if;
   }
   import ietf-inet-types {
   prefix inet;
    }
   import ietf-yang-types {
   prefix yang;
   }
  organization
  "IETF LIME (Layer Independent OAM Management
  in Multi-Layer Environment) Working Group";
  contact
  "wangzitao@huawei.com";
   description
   "This YANG module defines the generic
   notification and rpc command for multi-layer
   OAM management to be used
   within IETF in a protocol independent manner.";
   revision 2014-12-16 {
   description
   "Initial revision.";
   reference "RFC XXXX: A YANG Data Model
   for Layer independent OAM management";
   }

/*features*/
feature connectivity-verification {
   description
"This feature indicates that the server supports
executing connectivity verification OAM command
and returning a response. Servers that do not
advertise this feature will not support executing
connectivity verification command or rpc model
for connectivity verification command.";
 }

/*identities*/
     identity technology-types {
       description
         "this is the base identity of technology types which are
          vpls, nvo3, TRILL, ipv4, ipv6, mpls, etc";
     }
  identity defect-types {
       description
         "foo";
     }

     identity ipv4 {
       base technology-types;
       description
         "technology of ipv4";
     }

     identity ipv6 {
       base technology-types;
       description
         "technology of ipv6";
     }

     identity command-sub-type {
       description
         "defines different rpc command subtypes,
         e.g.,rfc792 IP ping ,rfc4379 LSP ping,
         rfc6905 trill OAM, this is optional for most cases";
     }

     identity name-format {
       description
         "This defines the name format,
        IEEE 8021Q CFM defines varying
         styles of names. It is expected
        name format as an identity ref
         to be extended with new types.";
     }

     identity name-format-null {
       base name-format;
       description
         "defines name format as null";
     }

     identity identifier-format {
       description
         "identifier-format identity can be augmented to define other
        format identifiers used in MEPD-ID etc";
     }

     identity identifier-format-integer {
       base identifier-format;
       description
         "defines identifier-format to be integer";
     }

/*typedefs*/
     typedef MEP-direction {
       type enumeration {
         enum "Up" {
           value 0;
     description
     "MEP direction up.";
         }
         enum "Down" {
           value 1;
     description
     "MEP direction down.";
         }
       }
    description
         "Describes the direction of MEP.";

     }

     typedef MEP-name {
       type string;
       description
         "Generic administrative name for a MEP";
     }

     typedef Interval {
       type uint32;
       units "milliseconds";
       default "1000";
       description
         "Interval between packets in milliseconds.
          0 means no packets are sent.";
     }

     typedef ecmp-choices {
       type enumeration {
         enum "ecmp-use-platform-hash" {
           value 0;
   description
     "use platform hash.";
         }
         enum "ecmp-use-round-robin" {
           value 1;
    description
     "use round robin.";
         }
       }
    description
    "describes the algorithm of ecmp";
     }

     typedef MD-name-string {
       type string;
    default "";
       description
         "Generic administrative name for an MD";
     }

     typedef MA-name-string {
       type string;
    default "";
       description
         "Generic administrative name for an MA";

     }

     typedef oam-counter32 {
       type yang:zero-based-counter32;
       description
         "defines 32 bit counter for OAM";
     }

     typedef MD-level {
       type uint32 {
         range "0..255";
       }
       description
         "Maintenance Domain level.  The level may be restricted in
          certain protocols (eg to 0-7)";
     }

/*groupings*/
    grouping topology {
    choice topology {
      case topo-null {
        description
          "this is a placeholder when no topology is needed";
        leaf topo-null {
           type empty;
           description
     "there is no topology define, it will be defined
     in technology specific model.";
        }
      }
description
"describes the topology choice";
    }
description
"This grouping describes the topology";
}

    grouping error-message {
    choice error {
      case error-null {
        description
          "this is a placeholder when no error status is needed";
        leaf error-null {
           type empty;
           description
             "there is no error define, it will be defined in
    technology specific model.";
        }
      }
 description
 "describes the error message";
    }
 description
 "this grouping describes the error message";
}

     grouping mp-address {
       choice mp-address {
         case mac-address {
           leaf mac-address {
             type yang:mac-address;
     description
     "mac address";
           }
         }
         case ipv4-address {
           leaf ipv4-address {
             type inet:ipv4-address;
     description
     "ipv4 address";
           }
         }
         case ipv6-address {
           leaf ipv6-address {
             type inet:ipv6-address;
     description
     "ipv6 address";
           }
         }
   description
    "describes the mp-address";
       }
  description
  "describes the mp-address";
     }

     grouping maintenance-domain-id {
       //status current;
       description
         "Grouping containing leaves sufficient to identify an MD";
       leaf technology {
         type identityref {
           base technology-types;
         }
   //status current;
         mandatory true;
         description
           "Defines the technology";
       }
       leaf MD-name-string {
         //status current;
         type MD-name-string;
         mandatory true;
   description
         "Defines the generic administrative
          maintenance domain name";
       }
     }
     grouping MD-name {
       leaf MD-name-format {
         type identityref {
           base name-format;
         }
  description
         "Defines the md name format";
       }
       choice MD-name {
         case MD-name-null {
           leaf MD-name-null {
             when "../../../MD-name-format = name-format-null"{
             description
             "describe condition met by MD-name-format";
             }
             type empty;
     description
      "there is no MD NAME define, it will be defined in
       technology specific model.";
           }
         }
  description
         "Defines the MD-name choice";
       }
  description
       "Defines the MD-name grouping";
     }
     grouping ma-identifier {
       description
         "Grouping containing leaves sufficient to identify an MA";
       leaf MA-name-string {
         type MA-name-string;
   description
   "define the MA name";
       }
     }
     grouping MA-name {
       leaf MA-name-format {
         type identityref {
           base name-format;
         }
    description
    "define the MA name format";
       }
       choice MA-name {
         case MA-name-null {
           leaf MA-name-null {
             when "../../../MA-name-format = name-format-null"{
             description
             "describe condition met by MA-name-format";
             }
             type empty;
     description
     "there is no MA-name-format define,
      it will be defined in technology specific model";
           }
         }
   description
   "define the MA NAME";
       }
  description
   "define the MA name grouping";
     }

     grouping MEP-ID {
       choice MEP-ID {
         default "MEP-ID-int";
         case MEP-ID-int {
           leaf MEP-ID-int {
             type int32;
     description
     "define the MEP id int";
           }
         }
   description
    "define the MEP ID";
       }
       leaf MEP-ID-format {
         type identityref {
           base identifier-format;
         }
          description
    "define the MEP ID format";
       }
   description
   "define the MEP ID grouping";
     }
     grouping MEP {
      // status current;
       description
         "Defines elements within the MEP";
       leaf mep-name {
         type MEP-name;
    mandatory true;
         //status current;
          description
           "Generic administrative name of the MEP";
       }
       uses MEP-ID;
       uses mp-address;
       uses connectivity-context;
       leaf Interface {
         type if:interface-ref;
         description
           "Interface name as defined by ietf-interfaces";
       }
       uses topology;

     }
      grouping session-type {
     leaf session-type{
             type enumeration {
               enum proactive {
                 description
                   "The current session is 'proactive'.";
               }
               enum on-demand {
                 description
                   "The current session is on-demand.";
               }
             }
             description
         "This object indicates whether the current
       session is defined to be proactive or on-demand.";
           }
     description
     "define the session type grouping";
   }

grouping monitor-stats {
       description
         "grouping for monitoring statistics, this will be augmented
          by others who use this component";
       choice monitor-stats {
         default "monitor-null";
         case monitor-null {
           description
             "this is a place holder when
            no monitoring statistics is needed";
           leaf monitor-null {
             type empty;
             description
              "there is no monitoring statistics to be defined";
           }
         }
 description
 "define the monitor stats";
       }
     }
     grouping MIP {
       description
         "defines MIP";
       leaf interface {
         type if:interface-ref;
  description
  "define the interface";
       }
     }

     grouping related-oam-layer {
       leaf offset {
         type int32 {
           range "-255..255";
         }
         description
           "defines offset (in MD levels) to a related OAM layer
            +1 is the layer immediately above
            -1 is the layer immediately below";
       }
       uses maintenance-domain-id;
       uses ma-identifier;
   description
   "define the related oam layer";
     }

     grouping interface-status {
       description
         "collection of interface related status";
       leaf admin-status {
         type leafref {
           path "/if:interfaces-state/if:interface/if:admin-status";
         }
   config false;
          description
           "oper status from ietf-interface module";
       }
       leaf oper-status {
         type leafref {
           path "/if:interfaces-state/if:interface/if:oper-status";
         }
         config false;
         description
           "oper status from ietf-interface module";
       }
     }

     grouping connectivity-context {
       description
         "Grouping defining the connectivity context for an MA; for
          example, a VRF for IP, or an LSP for MPLS.  This will be
          augmented by each protocol who use this component";
       choice connectivity-context {
         default "context-null";
         case context-null {
           description
             "this is a place holder when no context is needed";
           leaf context-null {
             type empty;
             description
               "there is no context define";
           }
         }
    description
    "define the connectivity-context";
       }
     }

     grouping priority {
       description
         "Priority used in transmitted packets; for example, in the
          TOS/DSCP field in IP or the Traffic Class field in MPLS";
       leaf priority {
         type uint8;
    description
    "define the priority which be used in
    transmitted packets.";
       }
     }

     grouping flow-entropy {
       description
         "defines the grouping statement for flow-entropy";
       choice flow-entropy {
         default "flow-entropy-null";
         case flow-entropy-null {
           description
             "this is a place holder when no flow entropy is needed";
           leaf flow-entropy-null {
             type empty;
             description
               "there is no flow entropy defined";
           }
         }
   description
   "define the flow entropy";
       }
     }

     notification defect-condition-notification {
       description
         "When defect condition is met this notificiation is sent";
      uses maintenance-domain-id {
      description
      "defines the MD (Maintenance Domain) identifier,
     which is the Generic MD-name-string
     and the technology.";
       }
       uses ma-identifier;
       leaf mep-name {
         type MEP-name;
         description
           "Indicate which MEP is seeing the error";
       }
       container remote-mepid {
         uses MEP-ID;
         description
           "Who is seeing the error (if known)
     if unknown make it 0.";
       }
leaf defect-type{
         type identityref {
           base defect-types;
         }
description
"The currently active defects on the specific MEP.";}
       uses error-message {
         description
           "Error message to indicate more details.";
       }
     }

     rpc continuity-check {
       description
         "Generates continuity check and return response";
       input {
         uses maintenance-domain-id {
           description
          "defines the MD (Maintenance Domain) identifier,
           which is the generic MD-name-string
           and the technology.";
         }

         uses ma-identifier {
           description
             "identfies the Maintenance association";
         }
         uses flow-entropy;
         uses priority;
         leaf ttl {
           type uint8;
            default "255";
       description
    "define the ttl";
         }
         uses session-type;
         leaf ecmp-choice {
           type ecmp-choices;
           description
             "0 means use the specified interface
              1 means use round robin";
         }
         leaf sub-type {
           type identityref {
             base command-sub-type;
           }
           description
             "defines different command types";
         }
         list outgoing-interfaces {
           key "interface";
      description
   "list of outgoing interface";
           leaf interface {
             type if:interface-ref;
     description
     "define the interface";
           }
         }
         leaf source-mep {
           type MEP-name;
      description
  "define the source mep";
         }
         container destination-mp {
    description
    "this container collect a set of parameters
     of destination mep";
           uses mp-address;
           uses MEP-ID {
             description
    "Only applicable if the destination is a MEP";
           }
         }
         leaf count {
           type uint32;
           default "3";
           description

             "Number of ping echo request message to send";
         }
         leaf interval {
           type Interval;
           description
             "Interval between echo requests";
         }
         leaf packet-size {
           type uint32 {
             range "64..10000";
           }
           default "64";
           description
             "Size of ping echo request packets, in octets";
         }
       }
       output {
         uses monitor-stats {
           description
             "Stats of continuity check is same as
           that of monitor sessions";
         }
       }
     }
     rpc connectivity-verification {
      if-feature connectivity-verification;
       description
         "Generates connectivity verification and return response";
       input {
         uses maintenance-domain-id {
           description
           "defines the MD (Maintenance Domain) identifier,
            which is the generic MD-name-string and
            the technology.";
         }

         uses ma-identifier {
           description
             "identfies the Maintenance association";
         }
         uses flow-entropy;
         uses priority;
         leaf ttl {
           type uint8;
           default "255";
    description
  "define the ttl leaf";
         }
         uses session-type;
         leaf ecmp-choice {
           type ecmp-choices;
           description
             "0 means use the specified interface
              1 means use round robin";
         }
         leaf sub-type {
           type identityref {
             base command-sub-type;
           }
           description
             "defines different command types";
         }
         list outgoing-interfaces {
           key "interface";
      description
      "a list of outgoing interface";
           leaf interface {
             type if:interface-ref;
              description
     "define the interface";
           }
         }
         leaf source-mep {
           type MEP-name;
      description
   "define the source mep";
         }
         container destination-mp {
    description
    "this container collect a set of
    destination mp parameters";
           uses mp-address;
           uses MEP-ID {
             description
    "Only applicable if the destination is a MEP";
           }
         }
         leaf count {
           type uint32;
           default "3";
           description

             "Number of ping echo request message to send";
         }
         leaf interval {
           type Interval;
           description
             "Interval between echo requests";
         }
         leaf packet-size {
           type uint32 {
             range "64..10000";
           }
           default "64";
           description
             "Size of ping echo request packets, in octets";
         }
       }
       output {
         uses monitor-stats {
           description
             "Stats of connectivity verification is
            same as that of monitor sessions";
         }
       }
     }
     rpc path-discovery {
       description
         "Generates path discovery and return response.
          Starts with TTL of one and increment by one at each hop.
          Untill destination reached or TTL reach max valune";
       input {
         uses maintenance-domain-id {
           description
           "defines the MD (Maintenance Domain) identifier,
            which is the generic MD-name-string and
            the technology.";
         }
         uses ma-identifier {
           description
             "identfies the Maintenance association";
         }
         uses flow-entropy;
         uses priority;
         leaf ttl {
           type uint8;
           default "255";
      description
   "define the ttl";
         }
         leaf command-sub-type {
           type identityref {
             base command-sub-type;
           }
           description
             "defines different command types";
         }
         uses session-type;
         leaf ecmp-choice {
           type ecmp-choices;
           description
             "0 means use the specified interface
              1 means use round robin";
         }
         list outgoing-interfaces {
           key "interface";
     description
     "list of outgoing interface";
           leaf interface {
             type if:interface-ref;
     description
     "define the interface";
           }
         }
         leaf source-mep {
           type MEP-name;
      description
    "define the source mep";
         }
         container destination-mp {
    description
    "this container collect a set of
    destination mp";
           uses mp-address;
           uses MEP-ID {
             description
      "Only applicable if the destination is a MEP";
           }
         }
         leaf count {
           type uint32;
           default "1";
          description
          "Number of traceroute probes to send.
           In protocols where a separate message is sent at each TTL,
           this is the number of packets to send at each TTL.";
         }
         leaf interval {
           type Interval;
           description
             "Interval between echo requests";
         }
       }
       output {
         list response {
           key "response-index";
      description
   "a list of path discovery response";
           leaf response-index {
             type uint8;
     description
               "Arbitrary index for the response.
               In protocols which guarantee there is only
                a single response at each TTL
                (e.g., IP Traceroute), the TTL can be used
                as the response index.";
           }
           leaf ttl {
             type uint8;
     description
     "define the ttl leaf";
           }
           container destination-mp {
             description
    "MP from which the response has been received";
             uses mp-address;
             uses MEP-ID {
               description
                 "Only applicable if the destination is a MEP";
             }
           }
           uses monitor-stats {
             description
               "If count is 1,
      there is a single delay value reported.";
           }
         }
       }
     }
   }
