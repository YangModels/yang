module ietf-network-inventory {
  yang-version 1.1;
  namespace "urn:ietf:params:xml:ns:yang:ietf-digital-asset-map";
  prefix nw-inv;

  import ietf-yang-schema-mount {
    prefix yangmnt;
    reference
      "RFC 8528: YANG Schema Mount";
  }
  import ietf-network {
    prefix nw;
    reference
      "RFC 8345: A YANG Data Model for Network Topologies";
  }
  import ietf-inet-types {
    prefix inet;
    reference
      "RFC 6991: Common YANG Data Types";
  }
  import ietf-yang-types {
    prefix yang;
    reference
      "RFC 6991: Common YANG Data Types";
  }
  import iana-hardware {
    prefix ianahw;
    reference
      "RFC 8348: A YANG Data Model for Hardware Management";
  }
  import ietf-geo-location {
    prefix geo;
    reference
      "RFC 9179: A YANG Grouping for Geographic Locations";
  }

  organization
    "IETF OPSAWG (Operations and Management Area Working Group)";
  contact
    "WG Web:   <https://datatracker.ietf.org/wg/opsawg/>
     WG List:  <mailto:opsawg@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module defines XXX.

     Copyright (c) 2022 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2022-10-24 {
    description
      "Initial revision.";
    reference
      "RFC XXXX: A Network Inventory Management Model for
       Enterprise Networks ";
  }

  identity inventory-software-type {
    description
      "Base identity of the software type.";
  }

  identity os-software {
    base inventory-software-type;
    description
      "OS software type.";
  }

  identity firmware {
    base inventory-software-type;
    description
      "Firmware type.";
  }

  identity endpoint-type {
    description
      "Base identity for endpoint type.";
  }

  identity server {
    base endpoint-type;
    description
      "Identity for computing server device.";
  }

  identity vm {
    base endpoint-type;
    description
      "Identity for VM node.";
  }

  identity iot_device {
    base endpoint-type;
    description
      "Identity for IoT device.";
  }

  identity cell-phone {
    base endpoint-type;
    description
      "Identity for mobile phone.";
  }

  identity node-type {
    description
      "Base identity for node device type.";
  }

  identity hub {
    base node-type;
    description
      "Identity for hub device.";
  }

  identity switch {
    base node-type;
    description
      "Identity for switch device.";
  }

  identity router {
    base node-type;
    description
      "Identity for router device.";
  }

  identity gateway {
    base node-type;
    description
      "Identity for gateway device.";
  }
  identity security {
    base node-type;
    description
      "Identity for access-point device.";
  }

  identity virtual-gateway {
    base node-type;
    description
      "Identity for virtual gateway device.";
  }

  identity virtual-router {
    base node-type;
    description
      "Identity for virtual router device.";
  }

  identity virtual-switch {
    base node-type;
    description
      "Identity for virtual switch device.";
  }

  identity virtual-security {
    base node-type;
    description
      "Identity for virtual security device.";
  }

  identity access-point {
    base node-type;
    description
      "Identity for access-point device.";
  }

  typedef software-class {
    type string;
    description
      "Software name for the software component.";
  }

  typedef component-class {
    type union {
      type identityref {
        base ianahw:hardware-class;
      }
      type software-class;
    }
    description
      "Definition for the type of hardware or software
       component class.";
  }

  /* Groupings */

  grouping system-config {
    description
      "Grouping for node system configuration.";

    container system-config {
    description
      "Container for system configuration mount-point,
          e.g. ietf-hardware, ietf-interface, etc.";
      anydata root {
        yangmnt:mount-point "root";
        description
          "Mount-point to system configuration, which is applied to
           a network device or a security device.";
      }
    }

  }

  grouping software-component {
    description
      "Grouping for software components.";
    container software-component {
      description
        "The software components within the device.";
      list software-instance {
        key "software-type version";
        description
          "The list of software instances contained within the
           device.";
        leaf software-type {
          type identityref {
            base inventory-software-type;
          }
          config false;
          description
            "The type of software.";
        }
        leaf version {
          type string;
          config false;
          description
            "The current version of the software in the device.";
        }
        leaf last-changed {
          type yang:date-and-time;
          config false;
          description
            "The date and time the current version last changed.";
        }
        uses license-info;
      }
    }
  }

  grouping license-info {
    description
      "Grouping for license information.";
    container licenses {
      description
        "All license items.";
      list license {
        key "name";
        description
          "License item.";
        leaf name {
          type string {
            length "1..31";
          }
          description
            "License item name.";
        }
        leaf license-description {
          type string {
            length "1..255";
          }
          config false;
          description
            "The description of a license item.";
        }
        leaf license-filename {
          type string {
            length "5..127";
          }
          config false;
          description
            "The name of a license file.";
        }
        leaf active-state {
          type string {
            length "1..49";
          }
          config false;
          description
            "To indicate the license activating state of the system,
             the value can be 'normal' or 'default'.";
        }
        leaf esn {
          type string {
            length "1..2047";
          }
          config false;
          description
            "The License ESN.";
        }
        leaf license-status {
          type string {
            length "1..49";
          }
          config false;
          description
            "The status of a license item.";
        }
        leaf issue-date {
          type yang:date-and-time;
          config false;
          description
            "The issued date of a license item.";
        }
        leaf expired-date {
          type string {
            length "1..71";
          }
          config false;
          description
            "The expired date of a license item.";
        }
        leaf type {
          type string {
            length "1..49";
          }
          config false;
          description
            "The type of a license item.";
        }
      }
    }
  }

  // grouping license-info
  // Device Management Information
  /* Main blocks */

  augment "/nw:networks/nw:network/nw:node" {
    description
      "Augment used to define attach the node configuration";
    leaf node-type {
      type identityref {
        base node-type;
        description
          "Node type.";
      }
    }
    container device-configs {
      description
        "Device hardware and interface configuration.";
      uses system-config;
    }
    uses software-component;
    uses geo:geo-location;
    container endpoints {
      description
        "This container provides a list of network endpoints
         for management purposes.";
      list endpoint {
        key "endpoint-id";
        description
          "The key of the endpoint list.";
        leaf endpoint-id {
          type string;
          description
            "Endpoint identifier.";
        }
        leaf endpoint-type {
          type identityref {
            base endpoint-type;
            description
              "Endpoint type.";
          }
        }
        leaf endpoint-ip-address {
          type inet:host;
          description
            "The IP address or DNS domain name of the device.";
        }
        leaf endpoint-mac-address {
          type yang:mac-address;
          description
            "The MAC address of the device.";
        }
        container hardware-components {
          description
            "Endpoint hardware information.";
          list hardware-component {
            key "name";
            description
              "An entry in this list represents a component.";
            leaf name {
              type string;
              description
                "The component name.";
            }
            leaf class {
              type component-class;
              mandatory true;
              description
                "An indication of the general hardware type of the
                 component.";
            }
            leaf parent {
              type leafref {
                path "../../hardware-component/name";
                require-instance false;
              }
              description
                "The name of the component that physically contains
                 this component.
                 If this leaf is not instantiated, it indicates that
                 this component is not contained in any other
                 component.
                 In the event that a physical component is contained
                 by more than one physical component, this node
                 contains the name of one of these components.
                 An implementation should use the same name
                 every time this node is instantiated.";
            }
            leaf serial-num {
              type string;
              config false;
              description
                "The vendor-specific serial number string for the
                 component.
                 The preferred value is the serial number string
                 acctually printed on the component itself
                 (if present).";
            }
            leaf mfg-name {
              type string;
              config false;
              description
                "The name of the manufacturer of this physical
                 component.
                 The preferred value is the manufacturer name
                 string actually printed on the component
                 itself (if present).";
            }
            leaf model-name {
              type string;
              config false;
              description
                "The vendor-specific model name identifier string
                 associated with this physical component.
                 The preferred value is the customer-visible part
                 number, which may be printed on the component itself.
                 If the model name string associated with the
                 physical component is unknown to the server,
                 then this node is not instantiated.";
            }
          }
        }
        uses software-component;
        list user {
          key "user-id";
          description
            "The user information.";
          leaf user-id {
            type string;
            description
              "The identifier of the user";
          }
        }
        list application {
          key "application-id";
          description
            "The application information.";
          leaf application-id {
            type string;
            description
              "The identifier of the application";
          }
        }
      }
    }
  }
}
