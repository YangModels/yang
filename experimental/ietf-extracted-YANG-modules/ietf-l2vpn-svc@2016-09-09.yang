module ietf-l2vpn-svc {

   namespace "urn:ietf:params:xml:ns:yang:ietf-l2vpn-svc";

   prefix "l2svc";

   import ietf-inet-types {
     prefix inet;
   }

   import ietf-yang-types {
        prefix yang;
   }

   organization
     "IETF L2SM Working Group.";

   contact
     "WG List: l3sm@ietf.org
      Editor: Bin_Wen@comcast.com";

   description
     "The YANG module defines a generic service configuration
      model for Layer 2 VPN services common across all of the
      vendor implementations.";

   revision 2016-09-09{
     description
       "Initial revision.";
     reference
       "draft-wen-l2sm-l2vpn-service-model-01.txt
        A YANG Data Model for L2VPN Service Delivery.";
   }

   /* Features */

   feature oam-3ah {
     description
       "Enables support of oam 802.3ah";
   }

   feature Micro-BFD {
     description
       "Enables support of Micro-BFD";
   }

   feature bfd {
     description
       "Enables support of bfd";
   }

   feature signaling-option {
     description
       "Enable support of signaling option";
   }

   feature site-diversity {
     description
       "Enables support of site diversity constraints";
   }

   feature encryption {
       description
         "Enables support of encryption";
     }

   /* Typedefs */

   typedef ccm-priority-type {
     type uint8 {
     range "0..7";
     }
     description
     "A 3 bit priority value to be used in the VLAN tag, if present
      in the transmitted frame.";
    }
   typedef control-mode {
     type enumeration{
       enum peer{
         description
           "Peer mode";
     }
     enum tunnel {
       description
         "Tunnel mode";
     }
     enum discard {
       description
         "Discard mode";
     }
    }
    description
      "Defining a type of the control mode";
   }

   /* Identities */

   identity color-id {
     description
      "Identity of color id";
   }

   identity color-id-evc {
     base color-id;
     description
       "Identity of color id base on EVC";
   }

   identity color-id-evc-cvlan {
     base color-id;
     description
      "Identity of color id base on EVC and CVLAN ";
   }

   identity cos-id {
     description
       "Identity of class of service id";
   }

   identity cos-id-evc {
     base cos-id;
     description
       "Identity of cos id based on EVC";
   }
   identity cos-id-ovc-ep {
     base cos-id;
     description
       "Identity of cos id based on OVC End Point";
   }

   identity cos-id-evc-pcp {
     base cos-id;
     description
       "Identity of cos id based on EVC and PCP";
   }

   identity cos-id-evc-dscp {
     base cos-id;
     description
       "Identity of cos id based on EVC and DSCP";
   }

   identity performance-tier-option {
     description
       "Identity of performance tier option.";
   }

   identity metro {
     base performance-tier-option;
     description
       "Identity of metro";
   }

   identity regional {
     base performance-tier-option;
     description
       "Identity of regional";
   }

   identity continental {
     base performance-tier-option;
     description
      "Identity of continental";
   }

   identity global {
     base performance-tier-option;
     description
       "Identity of global";
   }

   identity policing {
     description
       "Identity of policing type";
   }

   identity one-rate-two-color {
     base policing;
     description
       "Identity of one-rate, two-color (1R2C)";
   }

   identity two-rate-three-color {
     base policing;
     description
       "Identity of two-rate, three-color (2R3C)";
   }

   identity BUM-type {
     description
       "Identity of BUM type";
   }

   identity broadcast {
     base BUM-type;
     description
       "Identity of broadcast";
   }

   identity unicast {
     base BUM-type;
     description
       "Identity of unicast";
   }

   identity multicast {
     base BUM-type;
     description
       "Identity of multicast";
   }

   identity loop-prevention-type{
     description
       "Identity of loop prevention";
   }

   identity shut {
     base loop-prevention-type;
     description
       "Identity of shut protection";
   }

   identity trap {
     base loop-prevention-type;
     description
       "Identity of trap protection";
   }

   identity lacp-state {
     description
       "Identity of lacp state";
   }

   identity lacp-on {
     base lacp-state;
     description
       "Identity of lacp on";
   }

   identity lacp-off {
     base lacp-state;
     description
       "Identity of lacp off";
   }

   identity lacp-mode {
     description
       "Identity of lacp mode";
   }

   identity lacp-passive {
     base lacp-mode;
     description
       "Identity of lacp passive";
   }

   identity lacp-active {
     base lacp-mode;
     description
       "Identity of lacp active";
   }

   identity lacp-speed {
     description
       "Identity of lacp speed";
   }

   identity lacp-fast {
     base lacp-speed;
     description
       "Identity of lacp fast";
   }

   identity lacp-slow {
     base lacp-speed;
     description
       "Identity of lacp slow";
   }

   identity vpn-signaling-type {
      description
        "Identity of vpn signaling types";
   }

   identity vrf {
     base vpn-signaling-type;
     description
       "Virtual routing and forwarding (VRF).";
   }

   identity vfi {
     base vpn-signaling-type;
     description
       "Virtual forwarder interface";
   }

   identity evi {
     base vpn-signaling-type;
     description
       "Ethernet virtual interconnect.";
   }

   identity l2vpn-type {
     description
       "Layer 2 VPN types";
   }

   identity vpws {
     base l2vpn-type;
     description
       "Virtual Private Wire Service";
   }

   identity vpls {
     base l2vpn-type;
     description
       "Virtual Private LAN Service";
   }

   identity evpn {
     base l2vpn-type;
     description
       "Ethernet VPN";
   }

   identity management {
     description
       "Base identity for site management scheme.";
   }

   identity co-managed {
     base management;
     description
       "Base identity for comanaged site.";
   }

   identity customer-managed {
     base management;
     description
       "Base identity for customer managed site.";
   }

   identity provider-managed {
     base management;
     description
       "Base identity for provider managed site.";
   }

   identity address-family {
     description
       "Base identity for an address family.";
   }

   identity ipv4 {
     base address-family;
     description
       "Identity for IPv4 address family.";
   }

   identity ipv6 {
     base address-family;
     description
       "Identity for IPv6 address family.";
   }
   identity vpn-topology {
     description
       "Base identity for VPN topology.";
   }

   identity any-to-any {
     base vpn-topology;
     description
       "Identity for any to any VPN topology.";
   }

   identity hub-spoke {
     base vpn-topology;
     description
       "Identity for Hub'n'Spoke VPN topology.";
   }

   identity hub-spoke-disjoint {
     base vpn-topology;
     description
       "Identity for Hub'n'Spoke VPN topology
        where Hubs cannot talk between each other.";
   }

   identity site-role {
     description
       "Base identity for site type.";
   }

   identity any-to-any-role {
     base site-role;
     description
       "Site in an any to any IPVPN.";
   }

   identity spoke-role {
     base site-role;
     description
       "Spoke Site in a Hub & Spoke IPVPN.";
   }

   identity hub-role {
     base site-role;
     description
       "Hub Site in a Hub & Spoke IPVPN.";
   }

   identity pm-type {
     description
       "Performance monitor type";
   }

   identity loss {
     base pm-type;
     description
       "Loss measurement";
   }

   identity delay {
     base pm-type;
     description
       "Delay measurement";
   }

   identity fault-alarm-defect-type {
     description
       "Indicating the alarm priority defect";
   }

   identity remote-rdi {
     base fault-alarm-defect-type;
     description
       "Indicates the aggregate health of the remote MEPs.";
   }

   identity remote-mac-error {
     base fault-alarm-defect-type;
     description
       "Indicates that one or more of the remote MEPs is
        reporting a failure in its Port Status TLV or
        Interface Status TLV.";
   }

   identity remote-invalid-ccm {
     base fault-alarm-defect-type;
     description
       "Indicates that at least one of the Remote MEP
        state machines is not receiving valid CCMs
        from its remote MEP.";
    }

    identity invalid-ccm {
      base fault-alarm-defect-type;
      description
        "Indicates that one or more invalid CCMs has been
         received and that 3.5 times that CCMs transmission
         interval has not yet expired.";
    }

    identity cross-connect-ccm {
      base fault-alarm-defect-type;
      description
        "Indicates that one or more cross connect CCMs has been
         received and that 3.5 times of at least one of those
         CCMs transmission interval has not yet expired.";
    }

   /* Groupings */

   grouping customer-info-grouping {
     list customer-info {
       key "customer-account-number customer-name";
       leaf customer-account-number {
         type uint32;
         description
           "Customer account number";
       }
       leaf customer-name {
         type string;
         description
           "Customer name";
       }
       container customer-operation-center {
         leaf customer-noc-street-address {
           type string;
           description
             "Customer NOC street Address.";
         }
         container customer-noc-phone-number {
           leaf main-phone-num {
             type uint32;
             description
               "Main phone number.";
           }
           leaf extension-options {
             type uint32;
             description
               "Extension or options";
           }

           description
             "Configuration of customer noc phone number";
         }
         description
           "Configuration of customer operation center";
       }
       description
         "List of customer information";
     }
     description
       "Grouping for customer information";
   }

   grouping site-management {
     container management {
       leaf site-name {
         type string;
         description
           "Site name";
       }
       leaf address {
         type inet:ip-address;
         description
         "Address";
       }
       leaf ce-device-info {
         type string;
         description
           "CE device info";
       }
       leaf type {
         type identityref {
           base management;
         }
         description
           "Management type of the connection.";
       }
       leaf management-transport {
         type identityref {
           base address-family;
         }
         description
           "Transport protocol used for management.";
       }
       description
         "Management configuration";
     }
     description
       "Management parameters for the site.";
   }

   grouping customer-location-info {
     container location {
       leaf address {
         type string;
         description
           "Address (number and street) of the site.";
       }
       leaf zip-code {
         type string;
         description
           "ZIP code of the site.";
       }
       leaf state {
         type string;
         description
           "State of the site. This leaf can also be used to
           describe a region for country who does not have
           states.";
       }
       leaf city {
         type string;
         description
           "City of the site.";
       }
       leaf country-code {
         type string;
         description
           "Country of the site.";
       }
       description
         "Location of the site.";
     }
     description
       "This grouping defines customer location parameters";
    }

    grouping site-diversity {
      container site-diversity {
        if-feature site-diversity;
        container groups {
          list group {
            key group-id;
            leaf group-id {
              type string;
              description
                "Group-id the site is belonging to";
              }
            description
              "List of group-id";
          }
          description
            "Groups the site is belonging to.
             All site network accesses will inherit those group
             values.";
        }
        description
          "Diversity constraint type.";
      }
      description
        "This grouping defines site diversity parameters";
    }

    grouping site-service{
      leaf svlan-id-ethernet-tag {
        type string;
         description
           "SVLAN-ID/Ethernet Tag configurations";
      }
      leaf cvlan-id-to-evc-map {
        type string;
        description
          "List of CVLAN-ID to EVC Map configurations";
      }
      leaf service-level-mac-limit {
        type string;
        description
          "Service-level MAC-limit (E-LAN only)";
      }
      description
        "This grouping defines site service parameters";
    }

    grouping service-protection{
      container service-protection {
        container protection-model {
          description
            "Container of protection model configurations";
        }
        container peer-evc-id {
          description
            "Container of peer evc id configurations";
        }
        description
          "Container of End-to-end Service Protection
          configurations";
      }
      description
        "Grouping for service protection";
    }

    grouping ethernet-service-type {
      choice ethernet-svc-type {
        case e-line {
          leaf epl {
            type boolean;
            description
              "Ethernet private line";
          }
          leaf evpl {
            type boolean;
            description
              "Ethernet virtual private line";
          }
          description
            "Case of e-line";
        }

        case e-lan {
          leaf ep-lan {
            type boolean;
            description
              "Ethernet private LAN";
          }
          leaf evp-lan {
            type boolean;
            description
              "Ethernet virtual private LAN";
          }
          description
            "Case of e-lan";
        }
        case e-access {
          leaf access-epl {
            type boolean;
            description
              "Access Ethernet virtual private line";
          }
          leaf access-evpl {
            type boolean;
            description
              "Access Ethernet virtual private line";
          }
          description
            "Case of e-access.";
        }
        description
          "Choice of Ethernet service type";
      }
      description
        "Grouping for Ethernet service type.";
    }

    grouping signaling-option-grouping {
      list signaling-option {
        key "name type";
        leaf name {
          type string;
          description
            "VRF/VFI/EVI Name";
        }
        leaf type {
          type identityref {
            base vpn-signaling-type;
          }
          description
            "VPN signaling types";
        }
        container mp-bgp-l2vpn {
            leaf vpn-id {
              type string;
              description
                "Identifies the target VPN";
            }
            leaf type {
              type identityref {
                base l2vpn-type;
              }
              description
                "L2VPN types";
            }
          description
          "Container for MP BGP l2VPN";
        }

        container mp-bgp-evpn {
            leaf vpn-id {
              type string;
              description
                "Identifies the target VPN";
            }
            leaf type {
              type identityref {
                base l2vpn-type;
              }
              description
                "L2VPN types";
            }
          description
          "Container for MP BGP l2VPN";
        }

        container t-ldp-pwe {
          list PE-EG-list {
            key "service-ip-lo-addr vc-id";
            leaf service-ip-lo-addr {
              type inet:ip-address;
              description
                "Service ip lo address";
            }
            leaf vc-id {
              type string;
              description
              "VC id";
            }
            description
              "List of PE/EG";
          }
          description
            "Container of T-LDP PWE configurations";
        }

        container pwe-encapsulation-type {
          leaf ethernet {
            type boolean;
            description
              "Ethernet";
          }
          leaf vlan {
            type boolean;
            description
              "VLAN";
          }
          description
          "Container of PWE Encapsulation Type configurations";
        }

        container pwe-mtu {
          leaf allow-mtu-mismatch {
            type boolean;
            description
              "Allow MTU mismatch";
          }
          description
          "Container of PWE MTU configurations";
        }

        container control-word {
          description
            "Container of control word configurations";
        }

        description
          "List of VPN Signaling Option.";
      }

      description
        "Grouping for signaling option";
    }

   grouping load-balance-grouping {
     leaf fat-pw {
       type boolean;
       description
         "Fat label is applied to Pseudowires across MPLS
         network";
     }
     leaf entropy-label {
       type boolean;
       description
         "Entropy label is applied to IP forwarding,
          L2VPN or L3VPN across MPLS network";
     }
     description
       "Grouping for load balance ";
   }

   grouping intra-mkt-grouping {
     list intra-mkt {
       key "metro-mkt-id mkt-name";
       leaf metro-mkt-id {
         type uint32;
         description
           "Metro MKT ID";
       }
       leaf mkt-name {
         type string;
         description
           "MKT Name";
       }
       description
         "List of intra-MKT";
     }
     description
       "Grouping for intra-MKT";
   }

   grouping inter-mkt-service {
     leaf inter-mkt-service{
       type boolean;
       description
         "Indicate whether service is inter market service.";
     }
     description
       "Grouping for inter-MKT service";
   }

   grouping evc-id-grouping {
     leaf evc-id {
       type boolean;
       description
         "Ethernet Virtual Connection identifier";
     }
     description
       "Grouping for EVC-ID";
   }

   grouping svc-type-grouping {
     container svc-type {
       container evc {
         leaf evc-id {
           type boolean;
           description
             "Indicate whether the Ethernet virtual connection
              id support.";
         }
         leaf max-number-of-pe {
         type uint32;
         description
           "Maximum number of PEs supported per EVC.";
         }
         leaf max-number-of-site {
           type uint32;
           description
             "Maximum number of sites supported per EVC.";
         }
         description
           "Container for Ethernet virtual connection.";
       }
       container ovc {
         leaf on-net-ovc-id {
           type boolean;
           description
             "Indicate whether the on net OVC id support.";
         }
         leaf off-net-ov-id {
           type boolean;
           description
             "Indicate whether the off net OVC id support.";
         }
         description
           "Container for OVC";
       }
       description
         "Container for service types.";
     }
     description
       "Grouping of service types.";
   }

   grouping cfm-802-grouping {

     leaf MAID {
       type string;
       description
         "MA ID";
     }

     leaf mep-id {
      type uint32;
      description
        "Local MEP ID";
     }

     leaf mep-level {
       type uint32;
       description
         "MEP level";
     }

     leaf mep-up-down {
       type enumeration {
         enum up {
           description
             "MEP up";
         }
         enum down {
           description
             "MEP down";
         }
       }
       description
         "MEP up/down";
     }

     leaf remote-mep-id {
       type uint32;
       description
         "Remote MEP ID";
     }

     leaf cos-for-cfm-pdus {
       type uint32;
       description
         "COS for CFM PDUs";
     }

     leaf ccm-interval {
       type uint32;
       description
         "CCM interval";
     }

     leaf ccm-holdtime {
       type uint32;
       description
         "CCM hold time";
     }

     leaf alarm-priority-defect {
       type identityref {
         base fault-alarm-defect-type;
       }
       description
        "The lowest priority defect that is
         allowed to generate a Fault Alarm.
         The non-existence of this leaf means
         that no defects are to be reported";
     }

     leaf ccm-p-bits-pri {
       type ccm-priority-type;
       description
         "The priority parameter for CCMs transmitted by the MEP";
     }

     description
       "Grouping for 802.1ag CFM attribute";
   }

   grouping y-1731{
     list y-1731 {
       key MAID;

       leaf MAID {
         type string;
         description
           "MA ID ";
       }

       leaf mep-id {
         type uint32;
         description
           "Local MEP ID";
       }

       leaf type {
         type identityref {
           base pm-type;
         }
         description
           "Performance monitor types";
       }

       leaf remote-mep-id {
         type uint32;
         description
           "Remote MEP ID";
       }

       leaf message-period {
         type uint32;
         description
           "Defines the interval between OAM messages. The message
            period is expressed in milliseconds";
       }

       leaf measurement-interval{
         type uint32;
         description
           "Specifies the measurement interval for statistics. The
            measurement interval is expressed in seconds";
       }

       leaf cos {
         type uint32;
         description
           "Class of service";
       }

       leaf loss-measurement {
         type boolean;
         description
           "Whether enable loss measurement";
       }

       leaf synthethic-loss-measurement {
         type boolean;
         description
           "Indicate whether enable synthetic loss measurement";
       }

       container delay-measurement {
         leaf enable-dm {
           type boolean;
           description
             "Whether to enable delay measurement";
         }
         leaf two-way {
           type boolean;
           description
             "Whether delay measurement is two-way (true) of one-
             way (false)";
         }
         description
           "Container for delay measurement";
       }

       leaf frame-size{
         type uint32;
         description
           "Frame size";
       }

       leaf session-type {
         type enumeration {
           enum proactive {
             description
               "Proactive mode";
           }
           enum on-demand {
             description
               "On demand mode";
           }
         }
         description
           "Session type";
       }

       description
         "List for y-1731.";
     }
     description
       "Grouping for y.1731";
   }

   grouping enni-site-info-grouping {
     container site-info {
       leaf site-name {
         type string;
         description
           "Site name";
       }
       leaf address {
         type inet:ip-address;
         description
           "Address";
       }
       leaf Edge-Gateway-Device-Info {
         type string;
         description
           "Edge Gateway Device Info ";
       }
       description
         "Container of site info configurations";
     }
     description
       "Grouping for site information";
   }

   grouping site-security {
     container security {
       description
         "Security parameters";
     }
     description
       "This grouping defines security parameters for a site";
   }
   grouping lacp-grouping {

     container LACP {
       leaf LACP-state {
         type identityref {
           base lacp-state;
         }
         description
           "LACP on/off";
       }
       leaf LACP-mode {
         type identityref {
           base lacp-mode;
         }
         description
           "LACP mode";
       }
       leaf LACP-speed {
         type identityref {
           base lacp-speed;
         }
         description
           "LACP speed";
       }
       leaf mini-link {
         type uint32;
         description
           "Mini link";
       }
       leaf system-priority {
         type uint16;
         description
           "Indicates the LACP priority for the system.
            The range is from 0 to 65535.
            The default is 32768.";
       }

       container Micro-BFD {
         if-feature Micro-BFD;
         leaf Micro-BFD-on-off {
           type enumeration {
             enum on {
               description
                 "Micro-bfd on";
             }
             enum off {
               description
                 "Micro-bfd off";
             }
           }
           description
             "Micro BFD ON/OFF";
         }
         leaf bfd-interval {
           type uint32;
           description
             "BFD interval";
         }
         leaf bfd-hold-timer {
           type uint32;
           description
             "BFD hold timer";
         }
         description
           "Container of Micro-BFD configurations";
       }

       container bfd {
         if-feature bfd;
         leaf bfd-enabled {
           type boolean;
           description
             "BFD activation";
         }
         choice holdtime {
           case profile {
             leaf profile-name {
               type string;
               description
                 "Service provider well
                  known profile.";
             }
             description
               "Service provider well
                known profile.";
           }
           case fixed {
             leaf fixed-value {
               type uint32;
               units msec;
               description
                 "Expected holdtime
                  expressed in msec.";
             }
           }
           description
             "Choice for holdtime flavor.";
         }
         description
           "Container for BFD.";
       }

       container Member-link-list {
         list member-link {
           key "name";
           leaf name {
             type string;
             description
               "Member link name";
           }
           leaf port-speed {
             type uint32;
             description
               "Port speed";
           }
           leaf auto-neg {
             type string;
             description
               "Auto neg";
           }
           leaf mtu {
             type uint32;
             description
               "MTU";
           }
           container oam-802.3AH-link{
             if-feature oam-3ah;
             leaf enable {
               type boolean;
               description
                 "Indicate whether support oam 802.3 ah
                  link";
             }
             description
               "Container for oam 802.3 ah link.";
           }
           description
             "Member link";
         }
         description
           "Container of Member link list";
       }

       leaf flow-control {
         type string;
         description
           "Flow control";
       }

       leaf encapsulation-type {
         type enumeration {
           enum VLAN {
             description
               "VLAN";
           }
           enum ether {
             description
               "Ethernet";
           }
         }
         description
           "Encapsulation type";
       }

       leaf ethertype {
         type string;
         description
           "Ether type";
       }

       leaf lldp {
         type boolean;
          description
            "LLDP";
        }

        description
          "LACP";
      }

      description
        "Grouping for lacp";
   }

   grouping phy-interface-grouping {
     container phy-interface {
       leaf port-number {
         type uint32;
         description
           "Port number";
       }
       leaf port-speed {
         type uint32;
         description
           "Port speed";
       }
       leaf auto-neg {
         type string;
         description
           "Auto neg";
       }
       leaf phy-mtu {
         type uint32;
         description
           "PHY MTU";
       }
       leaf flow-control {
         type string;
         description
           "Flow control";
       }
       leaf encapsulation-type {
         type enumeration {
           enum VLAN {
             description
               "VLAN";
           }
           enum Ethernet {
             description
               "Ethernet";
           }
         }
         description
           "Encapsulation-type";
       }
       leaf ethertype {
         type string;
         description
           "Ethertype";
       }
       leaf lldp {
         type boolean;
         description
           "LLDP";
       }
       container oam-802.3AH-link{
         if-feature oam-3ah;
         leaf enable {
           type boolean;
           description
             "Indicate whether support oam 802.3 ah
              link";
          }
          description
            "Container for oam 802.3 ah link.";
       }
       leaf uni-loop-prevention{
         type boolean;
         description
           "If this leaf set to truth that the port automatically
            goes down when a physical loopback is detect.";
       }

       description
         "Container of PHY Interface Attributes configurations";
     }
     description
       "Grouping for phy interface.";
   }

   grouping lag-interface-grouping{
     container LAG-interface {
       list LAG-interface {
         key "LAG-interface-number";
         leaf LAG-interface-number {
           type uint32;
           description
             "LAG interface number";
         }
         uses lacp-grouping;
         description
           "List of LAG interfaces";
       }
       description
         "Container of LAG interface attributes configuration";
     }
    description
      "Grouping for LAG interface";
   }

   grouping bearer-grouping {
     container bearer {
       uses phy-interface-grouping;
       uses lag-interface-grouping;

       leaf interface-description {
         type string;
         description
           "Interface description";
       }
       leaf sub-if-id {
         type uint32;
         description
           "Sub-if id";
       }

       description
         "Container for bearer";
     }
     description
     "Grouping for bearer.";
   }

   grouping ethernet-connection-grouping {
     container ethernet-connection {
       container vlan {
         leaf svlan-id-ethernet-tag {
           type string;
           description
             "SVLAN-ID/Ethernet Tag configurations";
         }
         description
           "Abstract container for VLAN";
       }
       description
         "Container for Ethernet connection";
     }
     description
       "Grouping for Ethernet connection";
   }

   grouping evc-mtu-grouping {
     leaf evc-mtu {
       type uint32;
       description
         "EVC MTU";
     }
     description
       "Grouping for evc mtu";
   }

   grouping mac-addr-limit-grouping {
     container mac-addr-limit {
       leaf exceeding-option {
         type uint32;
         description
           "Exceeding option";
       }
       description
         "Container of MAC-Addr limit configurations";
     }
     description
       "Grouping for mac address limit";
   }

   grouping s-vlan-grouping {
     container S-vlan {
       leaf c-vlan2evc-mapping {
         type string;
         description
           "C-VLAN to EVC mapping";
       }
       description
         "Container of S-VLAN configurations";
     }
     description
       "Grouping for s-vlan";
   }

   grouping multihoming-grouping {
     container multihoming {
       list multihoming {
         key "ESI";
         leaf ESI {
           type string;
           description
             "Ethernet segment id";
         }
         choice redundancy-mode {
           case single-active {
             leaf single-active {
               type boolean;
               description
                 "Single active";
             }
             description
               "Single active case";
           }
           case all-active {
             leaf all-active {
               type boolean;
               description
                 "All active";
             }
             description
               "All active case";
           }
           description
             "Redundancy mode choice";
         }
         description
           "List of multihomings";
       }
       description
         "Container of multihoming optional configurations";
     }
     description
       "Grouping for multihoming";
   }

   grouping l2cp-grouping {
     container L2CP-control {
       leaf stp-rstp-mstp {
         type control-mode;
         description
           "STP/RSTP/MSTP";
       }
       leaf pause {
         type control-mode;
         description
           "Pause";
       }
       leaf lacp-lamp {
         type control-mode;
         description
           "LACP/LAMP";
       }
       leaf link-oam {
         type control-mode;
         description
           "Link OAM";
       }
       leaf esmc {
         type control-mode;
         description
           "ESMC";
       }
       leaf l2cp-802.1x {
         type control-mode;
         description
           "802.x";
       }
       leaf e-lmi {
         type control-mode;
         description
           "E-LMI";
       }
       leaf lldp {
         type boolean;
         description
           "LLDP";
       }
       leaf ptp-peer-delay {
         type control-mode;
         description
           "PTP peer delay";
       }
       leaf garp-mrp {
         type control-mode;
         description
           "GARP/MARP";
       }
       leaf provider-bridge-group {
         type yang:mac-address;
         description
           "Provider bridge group reserved MAC address
            01-80-C2-00-00-08";
       }
       leaf provider-bridge-mvrp {
         type yang:mac-address;
         description
           "Provider bridge MVRP reserved MAC address
            01-80-C2-00-00-0D";
       }
       description
         "Container of L2CP control configurations";
      }
      description
        "Grouping for l2cp control";
   }

   grouping service-level-grouping {
     container service-level {
       leaf cos-identifier {
         type identityref {
           base cos-id;
         }
         description
           "COS Identifier [ EVC | EVC + PCP ]";
       }
       leaf color-identifier {
         type identityref {
           base color-id;
         }
         description
           "Color Identifier [ EVC | EVC + CVLAN ]";
       }
       leaf ingress-bw-profile-per-evc {
         type string;
         description
           "Ingress Bandwidth Profile per EVC";
       }
       leaf ingress-bw-profile-per-cos-id {
         type string;
         description
           "Ingress Bandwidth Profile per COS Identifier";
       }
       leaf egress-bw-profile-per-evc {
         type string;
         description
           "Egress Bandwidth Profile per EVC";
       }
       leaf egress-bw-profile-per-cos-id {
         type string;
         description
           "Egress Bandwidth Profile per COS Identifier";
       }
       leaf byte-offset {
         type uint16;
         description
           "For not including extra VLAN tags in the QoS
           calculation";
       }
       leaf policing {
         type identityref {
           base policing;
         }
         description
           "The policing can be either one-rate,
            two-color (1R2C) or two-rate, three-color (2R3C)";
       }
       leaf performance-tier-option {
         type identityref {
           base performance-tier-option;
         }
         description
          "Performance tier option";
       }
       leaf COS {
         type uint32;
         description
           "Class of Service";
       }
       description
       "Container of service level configurations.";
     }
     description
       "Grouping for service level.";
   }

   grouping B-U-M-strom-control-grouping {
     container B-U-M-strom-control {
       leaf BUM-overall-rate {
       type uint32;
       description
         "overall rate for BUM";
     }
     list BUM-rate-per-type {
       key "type";
       leaf type {
         type identityref {
           base BUM-type;
         }
         description
           "BUM type";
       }
       leaf rate {
         type uint32;
         description
           "Rate for BUM";
       }
       description
         "List of rate per type";
       }
       description
         "Container of B-U-M-strom-control configurations";
     }
     description
       "Grouping for B-U-M-strom-control";
   }

   grouping mac-loop-prevention-grouping {
     container mac-loop-prevention {
       leaf frequency {
         type uint32;
         description
           "Frequency";
       }
       leaf protection-type {
         type identityref {
           base loop-prevention-type;
         }
         description
           "Protection type";
       }
       leaf number-retries {
         type uint32;
         description
           "Number of retries";
       }
       description
         "Container of MAC loop prevention.";
     }
     description
       "Grouping for MAC loop prevention";
   }

   grouping ethernet-svc-oam-grouping {
     container Ethernet-Service-OAM {
       leaf MD-name {
         type string;
         description
           "Maintenance domain name";
       }
       leaf MD-level {
         type uint8;
         description
           "Maintenance domain level";
       }
       container cfm-802.1-ag {
         list n2-uni-c {
           key "MAID";
           uses cfm-802-grouping;
           description
             "List of UNI-N to UNI-C";
         }
         list n2-uni-n {
           key "MAID";
           uses cfm-802-grouping;
           description
            "List of UNI-N to UNI-N";
         }
         description
           "Container of 802.1ag CFM configurations.";
       }
       uses y-1731;
       description
         "Container for Ethernet service OAM.";
     }
     description
       "Grouping for Ethernet service OAM.";
   }

   grouping enni-management {
     container management {
       leaf site-name {
         type string;
         description
           "Site name";
       }
       leaf address {
         type inet:ip-address;
         description
           "Address";
       }
       leaf Edge-Gateway-Device-Info {
         type string;
         description
           "Edge Gateway Device Information.";
       }
       leaf type {
         type identityref {
           base management;
         }
         description
           "Management type of the connection.";
       }
       leaf management-transport {
         type identityref {
           base address-family;
         }
         description
           "Transport protocol used for management.";
       }
       description
         "Management configuration.";
     }
     description
       "Grouping for ENNI site management.";
   }

   grouping fate-sharing-group {
     container groups {
       leaf fate-sharing-group-size {
         type uint16;
         description
           "Fate sharing group size.";
       }
       list group {
         key group-id;
         leaf group-id {
           type string;
           description
             "Group-id the site network access
              is belonging to";
         }
         description
           "List of group-id";
       }
       description
         "Groups the fate sharing group member
          is belonging to";
     }
     description
       "Grouping for Fate sharing group.";
   }

   /* MAIN L2VPN SERVICE */

   container l2vpn-svc {

     /* CUSTOMER */

     container customer-info {
       uses customer-info-grouping;
       description
         "Container of customer information configurations.";
     }

     /* SERVICE */

     container vpn-services {
       list vpn-svc {
         key "svc-id";
         leaf svc-id {
           type string;
           description
             "Defining a service id.";
         }
         uses svc-type-grouping;
         container ethernet-svc-type {
           uses ethernet-service-type;
           description
             "Container of Ethernet service type";
         }
         container metro-network-id {
           uses inter-mkt-service;
           uses intra-mkt-grouping;
           description
             "Container of Metro-Network ID configurations";
         }
         container signaling-option {
           uses signaling-option-grouping;
           description
             "Container for signaling option";
         }
         container load-balance-options {
           uses load-balance-grouping;
           description
             "container for load balance options";
         }
         uses site-service;
         uses service-protection;
         description
           "List of vpn-svc";
       }
       description
         "Container of vpn-services configurations";
     }

     /* SITE */

     container site {
       container uni-sites {
         list uni-site {
           key "site-id";
           leaf site-id {
             type string;
             description
               "Container of site id";
           }
           uses site-management;
           uses customer-location-info;
           uses site-diversity;
           uses site-security;
           container signaling-option {
             if-feature signaling-option;
             uses signaling-option-grouping;
             description
               "Container for signaling option";
           }

           container load-balance-options {
             uses load-balance-grouping;
               leaf vxlan-source-port {
                 type string;
                 description
                   "Vxlan source port";
               }
             description
               "Container for load balance options";
           }

           container uni-ports {
             list uni-port {
               key "uni-id";
               leaf uni-id {
                 type string;
                 description
                   "UNI id";
               }

               uses fate-sharing-group;
               uses bearer-grouping;
               uses ethernet-connection-grouping;
               uses evc-mtu-grouping;
               uses mac-addr-limit-grouping;
               uses s-vlan-grouping;
               uses multihoming-grouping;
               uses l2cp-grouping;

               container service {
                 uses site-service;
                 uses service-level-grouping;
                 description
                   "Container for site service.";
               }

               uses B-U-M-strom-control-grouping;
               uses mac-loop-prevention-grouping;
               uses ethernet-svc-oam-grouping;
               uses site-security;

               description
                 "List of UNI ports";
             }
             description
               "Container of UNI port configurations";
           }
           description
             "List of UNI sites";
         }
         description
           "Container of UNI site configurations";
       }

       container enni-sites {
         list enni-site {
           key "site-id";
           leaf site-id {
             type string;
             description
               "Container of site id";
           }

           uses customer-location-info;
           uses site-diversity;
           uses enni-management;
           uses site-security;
           uses service-protection;

           container signaling-option {
             if-feature signaling-option;
             uses signaling-option-grouping;
             description
               "Container for signaling option";
           }

           container load-balance-options {
             uses load-balance-grouping;
               leaf vxlan-source-port {
                 type string;
                 description
                   "Vxlan source port";
               }
             description
               "Container for load balance options";
           }

           container enni-ports {
             list enni-port {
               key "enni-id";
               leaf enni-id {
                 type string;
                 description
                   "ENNI id";
               }
               leaf remote-carrier-name{
                 type string;
                    description
                      "Remote carrier name";
               }

               uses bearer-grouping;
               uses ethernet-connection-grouping;
               uses evc-mtu-grouping;
               uses mac-addr-limit-grouping;
               uses s-vlan-grouping;
               uses multihoming-grouping;
               uses l2cp-grouping;

               container service{
                 uses site-service;
                 uses service-level-grouping;
                 description
                   "Container for site service.";
               }

               uses B-U-M-strom-control-grouping;
               uses mac-loop-prevention-grouping;
               uses ethernet-svc-oam-grouping;
               uses site-security;

               description
                 "List of ENNI ports";
             }
             description
               "Container of ENNI port configurations";
           }
           description
             "List of ENNI sites";
         }
         description
           "Container of ENNI site configurations";
       }
       description
         "Container for site configurations";
     }
     description
       "Container of l2vpn-svc configurations";
   }
}
