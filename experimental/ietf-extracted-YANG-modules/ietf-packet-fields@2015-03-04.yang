module ietf-packet-fields {
  yang-version 1;

  namespace "urn:ietf:params:xml:ns:yang:ietf-packet-fields";

  prefix packet-fields;

  import ietf-inet-types {
    prefix "inet";

  }

  import ietf-yang-types {
    prefix "yang";
  }

  organization
  "IETF NETMOD (NETCONF Data Modeling Language) Working Group";

  contact
    "WG Web: http://tools.ietf.org/wg/netmod/
    WG List: netmod@ietf.org

    WG Chair: Juergen Schoenwaelder
    j.schoenwaelder@jacobs-university.de

    WG Chair: Tom Nadeau
    tnadeau@lucidvision.com

    Editor: Dean Bogdanovic
    deanb@juniper.net

    Editor: Kiran Agrahara Sreenivasa
    kkoushik@brocade.com

    Editor: Lisa Huang
    yihuan@cisco.com

    Editor: Dana Blair

    dblair@cisco.com";

  description
    "This YANG module defines groupings that used by ietf-acl
    but not limited to acl.

    Copyright (c) 2015 IETF Trust and the persons identified as
    the document authors.  All rights reserved.

    Redistribution and use in source and binary forms, with or
    without modification, is permitted pursuant to, and subject
    to the license terms contained in, the Simplified BSD
    License set forth in Section 4.c of the IETF Trust's Legal
    Provisions Relating to IETF Documents
    (http://trustee.ietf.org/license-info).

    This version of this YANG module is part of RFC XXXX; see
    the RFC itself for full legal notices.";

    // RFC Ed.: replace XXXX with actual RFC number and remove this
    // note.

  revision 2015-03-04 {
    description "Initial version of packet fields used by
      access-lists";
    reference
      "RFC XXXX: Network Access Control List (ACL)
      YANG Data  Model";
  }

  grouping access-control-list-transport-header-fields {
    description "Transport header fields";

    container source-port-range {
      description "inclusive range of source ports";
      leaf lower-port {
        type inet:port-number;
        mandatory true;
        description "Lower boundary.";
      }
      leaf upper-port {
        type inet:port-number;
        description "Upper boundary. If exist, upper port must be greater or
        equal to lower port.";
      }
    }

    container destination-port-range {
      description "inclusive range of destination ports";
      leaf lower-port {
        type inet:port-number;
        mandatory true;
        description "Lower boundary.";
      }
      leaf upper-port {
        type inet:port-number;
        description "Upper boundary.";
      }
    }
  }

  grouping access-control-list-ip-header-fields {
    description "Header fields common to ipv4 and ipv6";

    uses access-control-list-transport-header-fields;

    leaf dscp {
      type inet:dscp;

      description "Value of dscp.";
    }

    leaf protocol {
      type uint8;
      description "Internet Protocol number.";
    }

  }

  grouping access-control-list-ipv4-header-fields {
    description "fields in IPv4 header";

    leaf destination-ipv4-network {
      type inet:ipv4-prefix;
      description "One or more ip addresses.";
    }

    leaf source-ipv4-network {
      type inet:ipv4-prefix;
      description "One or more ip addresses.";
    }

  }

  grouping access-control-list-ipv6-header-fields {
    description "fields in IPv6 header";

    leaf destination-ipv6-network {
      type inet:ipv6-prefix;
      description "One or more ip addresses.";
    }

    leaf source-ipv6-network {
      type inet:ipv6-prefix;
      description "One or more ip addresses.";
    }

    leaf flow-label {
      type inet:ipv6-flow-label;
      description "Flow label.";
    }

  }

  grouping access-control-list-eth-header-fields {

    description "fields in ethernet header";

    leaf destination-mac-address {
      type yang:mac-address;
      description "Mac addresses.";
    }

    leaf destination-mac-address-mask {
      type yang:mac-address;
      description "Mac addresses mask.";
    }

    leaf source-mac-address {
      type yang:mac-address;
      description "Mac addresses.";
    }

    leaf source-mac-address-mask {
      type yang:mac-address;
      description "Mac addresses mask.";
    }
  }

  grouping timerange {
    description "Time range contains time
    segments to allow access-control-list to be
    active/inactive when the system time
    is within the time segments.";

    container absolute {
      description
        "Absolute time and date that
        the associated function starts
        going into effect.";

      leaf start {
        type yang:date-and-time;
        description
        "Start time and date";
      }
      leaf end {
        type yang:date-and-time;
        description "Absolute end time and date";
      }
      leaf active {
        type boolean;
        default "true";
        description

          "Specify the associated function

          active or inactive state when
          starts going into effect";
      }
    } // container absolute
  } //grouping timerange

  grouping metadata {
    description "Fields associated with a packet but not in
      the header";

    leaf input-interface {
      type string;
      description "Packet was received on this interface";
    }
    uses timerange;
  }
}
