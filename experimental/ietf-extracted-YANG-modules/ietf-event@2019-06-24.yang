module ietf-event {
  yang-version 1.1;
  namespace "urn:ietf:params:xml:ns:yang:ietf-event";
  prefix evt;

  import ietf-yang-types {
    prefix yang;
  }
  import ietf-event-trigger {
    prefix trig;
  }

  organization
    "IETF xxx Working Group";
  contact
    "Zitao Wang: wangzitao@huawei.com
     Qin Wu: bill.wu@huawei.com";
  description
    "This module defines a model for the service topology.";

  revision 2019-06-24 {
    description
      "Initial revision.";
    reference
      "foo";
  }

  identity event-type {
    description
      "Base identity for event type";
  }

  identity frequency {
    description
      "Base identity for frequency";
  }

  identity periodic {
    base frequency;
    description
      "Identity for periodic trigger";
  }

  identity scheduling {
    base frequency;
    description
      "Identity for scheduling trigger";
  }

  identity logging {
    description
      "Base identity for logging action";
  }

  identity logging-notification {
    base logging;
    description
      "Logging for event notification";
  }

  identity logging-set {
    base logging;
    description
      "Logging for reset values";
  }

  typedef logging-type {
    type identityref {
      base logging;
    }
    description
      "Logging types";
  }

  typedef group-type {
    type string;
    description
      "Group type";
  }

  grouping start-end-grouping {
    description
      "A grouping that provides start and end times for
       Event objects.";
    leaf start {
      type yang:date-and-time;
      description
        "The date and time when the Event object
         starts to create triggers.";
    }
    leaf end {
      type yang:date-and-time;
      description
        "The date and time when the Event object
         stops to create triggers.
         It is generally a good idea to always configure
         an end time and to refresh the end time as needed
         to ensure that agents that lose connectivity to
         their Controller do not continue executing Schedules
         forever.";
    }
  }

  container events {
    list event {
      key "event-name type";
      leaf event-name {
        type string;
        description
          "Event name";
      }
      leaf type {
        type identityref {
          base event-type;
        }
        description
          "Type of event";
      }
      leaf event-description {
        type string;
        description
          "Event description";
      }
      leaf group-id {
        type group-type;
        description
          "Group Identifier";
      }
      leaf-list target {
        type trig:target;
        description
          "targeted objects";
      }
      leaf clear {
        type boolean;
        default "false";
        description
          "A flag indicate whether the event be closed";
      }
      list trigger {
        key "name";
        leaf name {
          type string;
          description
            "Trigger name";
        }
        leaf trigger-description {
          type string;
          description
            "Trigger description";
        }
        leaf call-event {
          type leafref {
            path "../../event-name";
          }
          description
            "This leaf call sub-event.";
        }
        container frequency {
          leaf type {
            type identityref {
              base frequency;
            }
            description
              "Type of trigger frequency";
          }
          container periodic {
            when "derived-from-or-self(../type, 'periodic')";
            description
              "A periodic timing object triggers periodically
               according to a regular interval.";
            leaf interval {
              type uint32 {
                range "1..max";
              }
              units "seconds";
              mandatory true;
              description
                "The number of seconds between two triggers
                 generated by this periodic timing object.";
            }
            uses start-end-grouping;
          }
          container scheduling {
            when "derived-from-or-self(../type, 'scheduling')";
            description
              "A scheduling timing object triggers.";
            leaf-list month {
              type string;
              description
                "A set of months at which this scheduling timing
                 will trigger.";
            }
            leaf-list day-of-month {
              type uint8 {
                range "0..59";
              }
              description
                "A set of days of the month at which this
                 scheduling timing will trigger.";
            }
            leaf-list day-of-week {
              type uint8 {
                range "0..59";
              }
              description
                "A set of weekdays at which this scheduling timing
                 will trigger.";
            }
            leaf-list hour {
              type uint8 {
                range "0..59";
              }
              description
                "A set of hours at which the scheduling timing will
                 trigger.";
            }
            leaf-list minute {
              type uint8 {
                range "0..59";
              }
              description
                "A set of minutes at which this scheduling timing
                 will trigger.";
            }
            leaf-list second {
              type uint8 {
                range "0..59";
              }
              description
                "A set of seconds at which this calendar timing
                 will trigger.";
            }
            uses start-end-grouping;
          }
          description
            "Container for frequency";
        }
        uses trig:trigger-grouping;
        description
          "List for trigger";
      }
      container actions {
        leaf target {
          type trig:target;
          description
            "Report the target objects";
        }
        anydata value {
          description
            "Inline set content.";
        }
        leaf logging {
          type logging-type;
          description
            "Specifies the log action";
        }
        description
          "Container for Actions";
      }
      description
        "List for Events";
    }
    description
      "YANG data module for defining event triggers and actions for
       network management purposes";
  }
}
