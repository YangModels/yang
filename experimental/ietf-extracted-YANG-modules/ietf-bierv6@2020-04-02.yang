module ietf-bierv6 {
  yang-version 1.1;
  namespace "urn:ietf:params:xml:ns:yang:ietf-bierv6";
  prefix "bierv6";

  import ietf-routing {
  prefix "rt";
  }

  import ietf-inet-types {
    prefix "inet";
  }

  import ietf-bier {
    prefix "bier";
  }

  import ietf-srv6-base {
    prefix "srv6";
  }

  organization
    "IETF BIER(Bit Indexed Explicit Replication ) Working Group";

  contact
    "WG List:  <mailto:bier@ietf.org>

     WG Chair: Tony Przygienda
               <mailto:tonysietf@gmail.com>

     WG Chair: Greg Shepherd
               <mailto:gjshep@gmail.com>

     Editor:   Xuesong Geng
                <mailto:gengxuesong@huawei.com>

               Feng Zheng
                <mailto:habby.zheng@huawei.com>

               Jingrong Xie
                <mailto:xiejingrong@huawei.com>";

               Zhuangzhuang Qin
                <mailto:qinzhuangzhuang@chinaunicom.cn>";

  description
    "The YANG Module defines configuration model for Bierv6";
  revision 2020-04-02 {
    description
      "Initial vision";
    reference
    "RFC XXX: YANG Data Model for Bierv6";
  }

  typedef bierv6-address-len {
    type uint8 {
      range "32 .. 96";
    }
    description
      "This type defines a Bierv6-address-len with range constraints";
  }

  typedef bierv6-status-type {
    type enumeration {
     enum up { value 1; description "State is Up"; }
     enum down { description "State is Down"; }
    }
    description
      "Status type";
  }

  //Identifications

  identity bierv6 {
    base "bier:bier-encapsulation";
  description
    "This identity represents bierv6 encapsulation";
  }

  identity ipv6-address-block {
    description
      "A dedicated group of Ipv6 addresses";
  }

  identity bierv6-address-block {
    base "ipv6-address-block";
    description
      "Ipv6 address block for bierv6";
  }

  identity bierv6-srv6-locator {
    base "ipv6-address-block";
    description
     "SRv6 locators for bierv6";
  }

  //Groupings
  grouping end-bier-address-state {
    description "end.bier address state ";
    leaf operational-status {
      type bierv6-status-type;
      config false;
      description
        "Indicates whether bierv6 ipv6 address state is UP";
    }

    leaf is-in-address-conflict {
      type boolean;
      config false;
        description
          "Indicates whether locator address conflicts with
         some other IPv6 address on the box";
    }
  }

  grouping bierv6-ipv6-block-state {
    description "SRv6 grouping Locastateor ";
    leaf operational-status {
      type bierv6-status-type;
      config false;
      description
       "Indicates whether bierv6 ipv6 address state is UP";
    }

    leaf is-in-address-conflict {
     type boolean;
      config false;
      description
        "Indicates whether locator address conflicts with
         some other IPv6 address on the box";
    }
  }

  grouping bierv6-address-blocks {
    description
      "ipv6 address block for bierv6";
    container bierv6-address-blocks {
      description
        "ipv6 address block for bierv6";
      list bierv6-address-block {
        key "name";
        description
          "Configure a bierv6 ipv6 address";
        leaf name {
          type string;
          description "Bierv6 ipv6 address name";
        }
        leaf enable {
          type boolean;
          default false;
          description "Enable a Bierv6 ipv6 address";
        }
        leaf is-default {
          type boolean;
          mandatory true;
          description "Indicates if the Bierv6 ipv6 address is a default address";
        }
        container prefix {
          description "Specify Bierv6 ipv6 address prefix value";
          leaf address {
            type inet:ipv6-address;
            mandatory true;
            description "IPv6 address";
          }
          leaf length {
            type bierv6-address-len;
            mandatory true;
            description "Bierv6 ipv6 address (prefix) length";
          }
        }
        uses bierv6-ipv6-block-state;
      }
    }
  }

  grouping end-bier {
    description
      "end.bier";
    choice end-bier-address {
      description
        "Two kinds of possible bier address";
      case bierv6-address-block {
        leaf bierv6-block-name {
          type leafref {
            path "/rt:routing/bier:bier/bierv6:bierv6/bierv6:bierv6-address-blocks/bierv6:bierv6-address-block/bierv6:name";
          }
          description
            "bierv6-block-name";
        }
        leaf offset {
          type inet:ipv6-address-no-zone;
          description
            "bierv6 ipv6 address block offset";
        }
      }

      case bierv6-srv6-locator {
        leaf srv6-locator-name {
          type leafref {
            path "/rt:routing/srv6:srv6/srv6:locators/srv6:locator/srv6:name";
          }
          description
            "SRv6 locator name";
        }
        leaf opcode {
          type inet:ipv6-address-no-zone;
          description
            "SRv6 function opcode.";
        }
      }
    }
    uses end-bier-address-state;
  }

  augment "/rt:routing/bier:bier" {
    container bierv6{
      description
        "bier global configuration.";
      uses bierv6-address-blocks;
    }
  }

  augment "/rt:routing/bier:bier/bier:sub-domain" {
    when "../encapsulation/encapsulation-type='bierv6'";
    container bierv6{
      uses end-bier;
      description
        "end.bier configuration";
    }
  }
}
