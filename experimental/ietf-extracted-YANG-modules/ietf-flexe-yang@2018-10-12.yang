module ietf-flexe-yang {
  yang-version 1;
  namespace "urn:ietf:params:xml:ns:yang:ietf-flexe-yang";
  prefix "flexe";
  import ietf-routing-types {
    prefix rt-types;
  }
  organization
    "Internet Engineering Task Force (IETF) CCAMP WG";
  contact
    "WG List: <mailto:ccamp@ietf.org>
  ID-draft editor:
    Xiaobing Niu (niu.xiaobing@zte.com.cn);
    Qilei Wang (wang.qilei@zte.com.cn); ";
  description
    "This module defines a YANG data model for FlexE.";
  revision 2018-10-12 {
    description
      "Initial version.";
    reference
          "draft-xiaobn-flexe-yang-mod-00.txt";
  }

  /* typedefs */
  typedef calendar-slot-granularity {
    type enumeration {
      enum csg-5G {
        value 1;
        description "Calendar slot with a 5G granularity";
      }
      enum csg-25G {
        value 2;
        description "Calendar slot with a 25G granularity";
      }
    }
    description
      "Defines a type representing the granularity of a calendar slot.";
  }

  typedef flexe-client-signal-rate {
    type enumeration {
      enum flexe-client-signal-10Gbps{
        value 1;
        description
          "FlexE Client signal rate of 10Gbps";
      }
      enum flexe-client-signal-40Gbps{
        value 2;
        description
          "FlexE Client signal rate of 40Gbps";
      }
      enum flexe-client-signal-25mGbps{
        value 3;
        description
          "FlexE Client signal rate of m*25Gbps";
      }
    }
    description
      "Defines FlexE Client signal rate, including 10, 40, m*25Gbps.";
  }
  typedef flexe-phy-type {
    type enumeration {
      enum flexe-phy-100GBASE-R {
        value 1;
        description "100GBASE-R PHY";
      }
      enum flexe-phy-200GBASE-R {
        value 2;
        description "200GBASE-R PHY";
      }
      enum flexe-phy-400GBASE-R {
        value 3;
        description "400GBASE-R PHY";
      }
    }
    description
      "Defines types of PHYs in a FlexE group";
  }
  typedef calendar-AorB {
    type enumeration {
      enum calendar-A {
        value 0 ;
        description
          "Set the A calendar configuration.";
      }
      enum calendar-B {
        value 1 ;
        description
          "Set the B calendar configuration.";
      }
    }
    description
      "Calendar configuration A or B";
  }
  /* interface states: OK, SF, SD */
  typedef intf-state {
    type enumeration {
      enum ok {
        value 0 ;
        description
          "The interface state of the FlexE Group is OK.";
      }
      enum sf {
        value 1 ;
        description
          "The interface state of the FlexE Group is SF."      ;
      }
      enum sd {
        value 2 ;
        description
          "The interface state of the FlexE Group is SD.";
      }
    }
    description
      "Interface state of port group.";
  }
  /* grouping */
  grouping flexe-client-bandwidth{
    leaf signal-type{
      type flexe-client-signal-rate;
      description
        "Client signal types: 10, 40, m*25 Gbps.";
    }
    leaf mac-rate {
      type rt-types:bandwidth-ieee-float32;
        description
          "Bandwidth of clients.";
    }
    description
      "The bandwidth of a FlexE client.";
  }

  /* Configuration of FlexE */
  container flexe-configuration{
    description
      "FlexE configuration, including configuration of FlexE groups and FlexE clients.";
    container flexe-groups {
      description
        "Container for the FlexE Group";
      list flexe-group {
        key group-name;
        description
          "List of FlexE Group";
        leaf group-name {
          type string ;
          description
            "The name of a FlexE Group";
        }
        container group-attributes {
          description
            "The attributes of a FlexE Group";
          leaf group-number {
            type uint32 {
              range 1..1048574 ;
            }
            description
              "The FlexE Group number is selected from the range 1~0xFFFFE.
               The value of 0x00000 and 0xFFFFF may not be used to designate
               a FlexE Group.";
          }
          leaf calendar-slot-granularity{
            type calendar-slot-granularity;
              description
                "The granularity of calendar slot is 5G or 25G";
              reference
                "OIF FlexE IA 2.0";
          }
          leaf flexe-phy-type{
            type flexe-phy-type;
            description
              "Types of PHYs, such as 100/200/400GBASE-R";
            reference
              "OIF FlexE IA 2.0";
          }
          container bonded-phys {
            description
              "PHYs bonded to form a FlexE Group";
            list flexe-phys {
              key phy-number-in-group;
              description
                "One of bonded PHYs in a FlexE Group";
              leaf phy-number-in-group{
                type uint8 ;
                description
                  "Refer to the clause 6.1 in FlexE IA 2.0.
                   For 100GBASE-R, the FlxeE PHY number and the 100G FlexE instance
                   number are the same and in the range [1-254];
                   For 200GBASE-R, each PHY number is in the range [1-126].
                   For 400GBASE-R, each PHY number is in the range [1-62].";
              }
              leaf local-phy-number{
                type uint16 ;
                description
                  "Local PHY number related to the PHY number
                   in a FlexE group.( with uint16 while not uint8 )";
              }
            }
          }

          container flexe-instances {
            description
              "FlexE instances in a FlexE Group";
            list flexe-instance {
              key flexe-instance-number;
              description
                "List of a FlexE instance in a FlexE Group";
              leaf flexe-instance-number{
                type uint8 ;
                description
                  "Logical FlexE instance number";
                reference
                  "Clause 6.1 FlexE Group in FlexE IA 2.0.
                   For 100G, instance num=PHY num;
                   For 200G, 8-bit instance num consists of the PHY num in the upper
                   seven bits, and 0 or 1 in the lower order bit.
                   For 400G, 8-bit instance num consists of the PHY num in the upper
                   six bits, and 0,1,2, or 3 in the two lower order bits.  ";
              }
            }
            list uneqipped-flexe-instance {
              key flexe-instance-number;
              description
                "Unquipped FlexE instance in a FlexE Group";
              leaf flexe-instance-number{
                type uint8 ;
                description
                  "Clause 6.1 FlexE Group in FlexE IA 2.0";
              }
            }
          }
          leaf rx-calendar {
            type calendar-AorB;
            description
              "Calendar configuration in the receive direction";
          }
          leaf tx-calendar {
            type calendar-AorB;
            description
              "Calendar configuration in the transmit direction";
          }
          leaf tx-calendar-neg {
            type enumeration {
              enum manual {
                value 1 ;
                description
                  "Manually configured";
              }
              enum protocol-force {
                value 2 ;
                description
                  "Protocol forced";
              }
              enum protocol-normal {
                value 3 ;
                description
                  "Protocol normal";
              }
            }
            description
              "TX calendar negotiation methods";
          }
          leaf reply-ca-mode {
            type enumeration {
              enum never {
                value 1 ;
                description
                  "never reply CA (Configuration Ack)";
              }
              enum immediately {
                value 2 ;
                description
                  "immediately reply CA (Configuration Ack)";
              }
              enum ask-controller {
                value 3 ;
                description
                  "Ask controller for more control";
              }
            }
            description
              "Reply CA mode";
          }
        }
      }
    }
    container flexe-clients {
      description
        "FlexE clients information";
      list flexe-client {
        key client-name ;
        description
          "Attributes of FlexE client" ;
        leaf client-name {
          type string ;
          description
            "FlexE client name";
        }
        container client-attribute {
          description
            "Attributes for specific client.";
          leaf client-number {
            type uint32 {
              range 1..65534 ;
            }
            description
              "Client number in the range of 1~0xFFFF";
          }
          container bandwidth {
            description "Client bandwidth";
            uses flexe-client-bandwidth;
          }
        }
        container used-flexe-resources {
          description
            "Used FlexE resources to carry the FlexE client";
          list used-rsc {
            key "calendar flexe-group" ;
            description
              "List of used resources";
            leaf calendar {
              type calendar-AorB;
              description
                "Calendar configuration";
            }
            leaf flexe-group {
              type string ;
              description
                "FlexE Group";
            }
            leaf flexe-instance {
              type uint8 ;
              description
                "FlexE Instance";
            }
          }
        }
      }
    }     /* end of FlexE client */
  }

  /* states of FlexE Group */
  container flexe-group-state {
    config false ;
    description "State info." ;
    container port-group {
      description "Port group state information.";
      list port-group {
        key port-group-id ;
        description "The state information of port-group.";
        leaf port-group-id {
          type uint32 {
            range 1..65536 {
              description "Port group id.";
            }
          }
          description "Port group id of port group.";
        }
        leaf intf-state {
          type intf-state ;
          description "Port state of port group.";
        }
      }
    }
  }
}
