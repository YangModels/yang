module service-node {

  namespace "urn:cisco:params:xml:ns:yang:sfc-sn";

  prefix sfc-sn;

  import ietf-inet-types { prefix inet; }
  import ietf-yang-types { prefix yang; }
  import service-function {prefix sfc-sf; }

  organization "Cisco Systems, Inc.";
  contact "Reinaldo Penno <repenno@cisco.com>";

  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
      "Revision based on Opendaylight project feedback";
  }
    // Service Nodes

  typedef service-node-ref {
      type leafref {
          path "/sfc-sn:service-nodes/sfc-sn:service-node/sfc-sn:name";
      }
      description
          "This type is used by data models that need to reference
           configured service functions.";
  }

  grouping service-node-grouping {
      leaf name {
        type string;
        description
             "The name of the service node.";
      }

      leaf ip-mgmt-address {
        type inet:ip-address;
      }
      leaf-list service-function {
        type sfc-sf:service-function-ref;
        description
            "A list of service functions resident in this service node";
      }
  }

  container service-nodes {
    description
        "Physical or virtual element that hosts one or
        more service functions and has one or more network locators
        associated with it for reachability and service delivery.";
    list service-node {
      key "name";
      uses service-node-grouping;
    }
  }

    // Remote procedure calls (for testing)

    rpc put-service-node {
        input {
            uses service-node-grouping;
    }
  }
}
