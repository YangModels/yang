module ietf-te {

    namespace "urn:ietf:params:xml:ns:yang:ietf-te";

    /* Replace with IANA when assigned */
    prefix "te";

    /* Import TE generic types */
    import ietf-te-types {
        prefix ietf-te-types;
    }

    /* Import TE packet specific types */
    import ietf-te-psc-types {
        prefix ietf-te-psc-types;
    }

    import ietf-interfaces {
        prefix if;
    }

    import ietf-inet-types {
        prefix inet;
    }

    organization
        "IETF TEAS Working Group";

    contact
        "Fill me";

    description
        "YANG data module for TE configuration,
         state, RPC and notifications.";

    revision 2015-03-22 {
        description
            "Initial revision.";
        reference "TBD";
    }

    grouping interface-attributes {
        description "Interface TE properties grouping.";
        leaf te-metric {
            type ietf-te-types:te-metric;
            description "Interface TE link metric.";
        }
        uses ietf-te-types:interface-affinities;
        uses ietf-te-types:interface-srlgs;
        uses ietf-te-psc-types:bandwidth-psc-reservable;
    }

    /* TE interface flooding parameters */
    grouping flooding-parameters {
        description "Interface TE flooding properties.";
        container thresholds {
            description "Flooding threshold values in percentages.";
            choice type {
                description
                    "Describes the flooding threshold step method";
                case equal-steps {
                    choice equal-step-type {
                        description
                            "Describes whether up and down equal step
                             size are same or different";
                        case up-down-different-step {
                            leaf up-step {
                                type uint8 {
                                    range "0..100";
                                }
                                description
                                    "Set single percentage threshold
                                    for increasing resource
                                    allocation";
                            }
                            leaf down-step {
                                type uint8 {
                                    range "0..100";
                                }
                                description
                                    "Set single percentage threshold
                                    for decreasing resource
                                    allocation";
                            }
                        }
                        case up-down-same-step {
                            leaf step {
                                type uint8 {
                                    range "0..100";
                                }
                                description
                                    "Set single percentage threshold
                                    for increasing and decreasing
                                    resource allocation";
                            }
                        }
                    }
                }
                case unequal-steps {
                    list up-steps {
                        key "value";
                        description
                            "Set nultuple percentage thresholds for
                            increasing resource allocation";
                        leaf value {
                            type uint8 {
                                range "0..100";
                            }
                            description
                                "Percentage value";
                        }
                    }
                    list down-steps {
                        key "value";
                        description
                            "Set nultuple percentage thresholds for
                            decreasing resource allocation";
                        leaf value {
                             type uint8 {
                                  range "0..100";
                             }
                             description
                                "Percentage value";
                        }
                    }
                }
            }
        }
    }

    grouping auto-backup {
        description
            "Auto-tunnel backup properties grouping.";
        container auto-backup {
            presence "Enable auto-tunnel backup feature.";
            description "Container for auto-backup features";
            leaf method {
                type identityref {
                    base ietf-te-psc-types:backup-type;
                }
                description
                    "Describes whether facility backup or 1-for-1
                    backup should be used";
            }
            leaf protection {
                type identityref {
                    base ietf-te-psc-types:backup-protection-type;
                }
                default
                    ietf-te-psc-types:backup-protection-node-link;
                description
                    "Describes whether the backup should offer
                    protection against link, node, or either";
            }
            leaf path-computation {
                type identityref {
                    base ietf-te-types:path-computation-srlg-type;
                }
                description
                    "FRR backup computation type";
            }
        }
    }

    grouping fast-reroute-backups {
        description
            "FRR backup tunnels";
        container fast-reroute-backups {
            if-feature ietf-te-types:frr-te;
            description
                "FRR backup tunnel container";
            container backup-capacity {
                description
                    "Limits the aggregate amount of primary
                     protected LSP bandwidth that this backup
                     tunnel may protect";
                leaf capacity {
                    type uint32;
                    description
                        "Maximum bandwidth this facility backup
                        is allowed to protect";
                }
                leaf type {
                    type uint32;
                    description
                        "Type of primary LSP bandwidth that the
                         backup is allowed to protect.";
                }
            }
            choice type {
                description
                    "FRR backup tunnel type";
                case static-tunnel {
                    leaf name {
                        type leafref {
                            path "/te/tunnels/tunnel/name";
                        }
                        description
                            "Static FRR backup tunnel name";
                    }
                    list static-backups {
                        key "backup-tunnel";
                        description
                            "List of static backup tunnels that
                            protect the TE interface.";
                        leaf backup-tunnel {
                            type leafref {
                                path "/te/tunnels/tunnel
                                [name = current()/../../name]/type";
                            }
                            description "FRR Backup tunnel";
                        }
                    }
                }
                case auto-tunnel {
                    uses auto-backup;
                }
            }
        }
    }

    grouping path-constraints {
        description
            "Grouping of possible TE path constraints";
        container path-constraints {
            description
                "Path contraints container";
            uses ietf-te-types:tunnel-path-selection;
        }
    }

    grouping tunnel-path-properties {
        description
            "Tunnel path properties grouping";
        container path-properties {
            description
                "Defines a TE tunnel path properties";
            leaf path-named-constraint {
                if-feature ietf-te-types:named-path-constraints;
                type leafref {
                    path "/te/globals/path-named-constraints/name";
                }
                description
                    "Reference to a globally defined named path
                     constraint set";
            }
            uses path-constraints;
            choice type {
                description
                    "Describes the path type";
                case dynamic {
                    leaf dynamic {
                        type empty;
                        description
                            "A CSPF dynamically computed path";
                    }
                }
                case explicit {
                    leaf explicit-path-name {
                        type leafref {
                            path "/te/globals/explicit-paths/name";
                        }
                        description
                            "Reference to a globally defined
                             explicit-path";
                    }
                }
            }

            leaf no-cspf {
                type empty;
                description
                    "Indicates no CSPF is to be attempted on this
                     path.";
            }
            leaf lockdown {
                type empty;
                description
                    "Indicates no reoptimization to be attempted for
                     this path.";
            }
        }
    }

    container te {
        presence "Enable TE feature.";
        description
            "TE global container.";

        /*** End of Groupings ***/
        container globals {
            description
                "Configuration data model for Global System-wide
                 Traffic Engineering.";

            list interface-named-admin-groups {
                if-feature ietf-te-types:extended-admin-groups;
                if-feature ietf-te-types:named-extended-admin-groups;
                key "name";
                description
                    "List of named TE admin-groups";
                leaf name {
                    type string;
                    description
                        "A string name that uniquely identifies a TE
                         interface named admin-group";
                }
                leaf group {
                    type ietf-te-types:admin-groups;
                    description
                        "An SRLG value";
                }
            }

            list interface-named-srlgs {
                if-feature ietf-te-types:named-srlg-groups;
                key "name";
                description
                    "A list of named SRLG groups";
                leaf name {
                    type string;
                    description
                        "A string name that uniquely identifies a TE
                         interface named srlg";
                }
                leaf group {
                    type ietf-te-types:srlg;
                    description
                        "An SRLG value";
                }
            }

            list explicit-paths {
                key "name";
                description
                    "A list of explicit paths";
                leaf name {
                    type string;
                    description
                        "A string name that uniquely identifies an
                         explicit path";
                }
                list explicit-route-objects {
                    key "index";
                    description
                        "List of explicit route objects";
                    leaf index {
                        type uint8 {
                             range "0..255";
                        }
                        description
                            "Index of this explicit route object";
                    }
                    uses ietf-te-types:explicit-route-object;
                    leaf explicit-route-usage {
                        type identityref {
                            base ietf-te-types:route-usage-type;
                        }
                        description
                            "An IP hop action.";
                    }
                }
            }

            list path-named-constraints {
                if-feature ietf-te-types:named-path-constraints;
                key "name";
                description
                    "A list of named path constraints";
                leaf name {
                    type string;
                    description
                        "A string name that uniquely identifies a
                         path constraint set";
                }
                uses path-constraints;
            }
        }

        /* TE Interface Configuration Data */
        container interfaces {
            description
                "Configuration data model for TE interfaces.";

            list interface {
                key "interface";
                description "TE interfaces.";
                leaf interface {
                     type if:interface-ref;
                     description
                        "TE interface name.";
                }

                list named-admin-groups {
                    if-feature ietf-te-types:extended-admin-groups;
                    if-feature
                        ietf-te-types:named-extended-admin-groups;
                    key named-admin-group;
                    description
                        "A list of named admin-group entries";
                    leaf named-admin-group {
                        type leafref {
                            path "/te/globals/" +
                                "interface-named-admin-groups/name";
                        }
                        description
                            "A named admin-group entry";
                    }
                }

                list named-srlgs {
                    if-feature ietf-te-types:named-srlg-groups;
                    key named-srlg;
                    description
                        "A list of named SRLG entries";
                    leaf named-srlg {
                        type leafref {
                            path "/te/globals/" +
                                "interface-named-srlgs/name";
                        }
                        description
                            "A named SRLG entry";
                    }
                }

                uses ietf-te-types:interface-switching-cap;
                uses interface-attributes;
                /* Link IGP flooding properties */
                uses flooding-parameters;
                uses fast-reroute-backups;
            }
        }

        /* TE Tunnel Configuration Data */
        container tunnels {
            description
                "Configuration, operational, notification and RPC
                 data model for TE tunnels.";

            list tunnel {
                key "name type";
                unique "identifier";
                description "TE tunnel.";
                leaf name {
                    type string;
                    description "TE tunnel name.";
                }
                leaf type {
                    type identityref {
                        base ietf-te-types:tunnel-type;
                    }
                    description "TE tunnel type.";
                }
                leaf identifier {
                    type uint16;
                    description
                        "TE tunnel Identifier.";
                }
                leaf description {
                    type string;
                    description
                        "TE tunnel description.";
                }
                leaf admin-status {
                    type identityref {
                        base ietf-te-types:state-type;
                    }
                    default ietf-te-types:state-up;
                    description "TE tunnel administrative state.";
                }
                uses ietf-te-psc-types:tunnel-routing-properties;
                uses ietf-te-psc-types:tunnel-forwarding-properties;
                uses ietf-te-types:tunnel-bidir-assoc-properties;
                choice path-type {
                    description
                        "Describes the path type";
                    case p2p {
                        leaf destination {
                            type inet:ip-address;
                            description
                                "P2P tunnel destination address";
                        }
                        /* P2P list of path(s) */
                        list primary-paths {
                            key "preference";
                            description
                                "List of primary paths for this
                                 tunnel.";
                            leaf preference {
                                 type uint8 {
                                      range "1..255";
                                 }
                                 description
                                    "Specifies a preference for
                                     this path. The lower the
                                     number higher the
                                     preference";
                            }
                            uses tunnel-path-properties;
                            list seondary-paths {
                                key "preference";
                                description
                                    "List of secondary paths for this
                                     tunnel.";
                                leaf preference {
                                     type uint8 {
                                          range "1..255";
                                     }
                                     description
                                        "Specifies a preference for
                                         this path. The lower the
                                         number higher the
                                         preference";
                                }
                                uses tunnel-path-properties;
                            }
                        }
                    }
                    case p2mp {
                        if-feature ietf-te-types:p2mp-te;
                        list p2mp-paths {
                            key "destination";
                            description
                                "List of destinations and their
                                 paths.";
                            leaf destination {
                                type inet:ip-address;
                                description
                                    "P2MP destination leaf address";
                            }
                            list primary-paths {
                                key "preference";
                                description
                                    "List of primary paths";
                                leaf preference {
                                     type uint8 {
                                          range "1..255";
                                     }
                                     description
                                        "Specifies a preference for
                                         this path. The lower the
                                         number higher the
                                         preference";
                                }
                                uses tunnel-path-properties;
                                list seondary-paths {
                                    key "preference";
                                    description
                                        "List of secondary paths";
                                    leaf preference {
                                        type uint8 {
                                            range "1..255";
                                        }
                                        description
                                            "Specifies a preference
                                             for this path. The lower
                                             the number higher
                                             the preference";
                                    }
                                    uses tunnel-path-properties;
                                }
                            }
                        }
                    }
                }
            }
        }
        /* MPLS-TE Global Operational Data */
        container global-state {
            config "false";
            description
                "State for global TE data";
        }

        /* TE Interfaces State Data */
        container interface-state {
            config "false";
            description
                "Operational data model for TE interfaces.";
        }

        /* TE Tunnel State Data */
        container tunnels-state {
            config "false";
            description "MPLS-TE tunnel operational state data.";
        }
    }

    /* TE Global RPCs/execution Data */
    rpc globals-rpc {
        description
            "Execution data for TE global.";
    }

    /* TE interfaces RPCs/execution Data */
    rpc interfaces-rpc {
        description
            "Execution data for TE interfaces.";
    }

    /* TE Tunnel RPCs/execution Data */
    rpc tunnels-rpc {
        description
            "TE tunnels RPC nodes";
    }

    /* TE Global Notification Data */
    notification globals-notif {
        description
            "Notification messages for Global TE.";
    }

    /* TE Interfaces Notification Data */
    notification interfaces-notif {
        description
            "Notification messages for TE interfaces.";
    }

    /* TE Tunnel Notification Data */
    notification tunnels-notif {
        description
            "Notification messages for TE tunnels.";
    }
}
