module ietf-syncphy {
  yang-version 1.1;
  namespace "urn:ietf:params:xml:ns:yang:ietf-syncphy";
  prefix "syncphy";

  import ietf-interfaces {
    prefix if;
    reference
      "RFC8343: A YANG Data Model for Interface Management";
  }

  organization "IETF CCAMP Working Group";
  contact
      "WG Web:   http://tools.ietf.org/wg/ccamp/
       WG List:  <mailto:ccamp@ietf.org>
       Author:   Yuanlong Jiang
                 <mailto:jiangyuanlong@huawei.com>
       Author:   Jingfei Lv
                 <mailto:lvjingfei@huawei.com>
       Author:   Liuyan Han
                 <mailto:hanliuyan@chinamobile.com>";
  description
    "This YANG module defines a data model for the configuration
     and management of Sync PHY.";

  revision "2020-07-09" {
    description "Initial version";
    reference "draft-jiang-ccamp-syncphy-yang: YANG Data Model for
               Sync PHY";
  }

  typedef sync-network-option-enumeration {
    type enumeration {
      enum "OptionUnknown" {
        value "1";
      }
      enum "Option1" {
        value "2";
      }
      enum "Option2Gen1" {
        value "3";
      }
      enum "Option2Gen2" {
        value "4";
      }
      enum "Option3" {
        value "5";
      }
      enum "OptionInvalid" {
        value "6";
      }
    }
    description
      "The Network synchronization networking options.
       Values for this enumeration are specified
       in G.781.";
    reference
      "ITU-T G.781-2017: 5.3.1";
  }

  typedef quality-level-enumeration {
    type enumeration {
      enum "QualityLevelNULL" {
        value "1";
      }
      enum "QualityLevelDNU" {
        value "2";
      }
      enum "QualityLevelDUS" {
        value "3";
      }
      enum "QualityLeveleEEC" {
        value "4";
      }
      enum "QualityLevelePRTC" {
        value "5";
      }
      enum "QualityLevelFAILED" {
        value "6";
      }
      enum "QualityLevelINV0" {
        value "7";
      }
      enum "QualityLevelINV1" {
        value "8";
      }
      enum "QualityLevelINV2" {
        value "9";
      }
      enum "QualityLevelINV3" {
        value "10";
      }
      enum "QualityLevelINV4" {
        value "11";
      }
      enum "QualityLevelINV5" {
        value "12";
      }
      enum "QualityLevelINV6" {
        value "13";
      }
      enum "QualityLevelINV7" {
        value "14";
      }
      enum "QualityLevelINV8" {
        value "15";
      }
      enum "QualityLevelINV9" {
        value "16";
      }
      enum "QualityLevelINV10" {
        value "17";
      }
      enum "QualityLevelINV11" {
        value "18";
      }
      enum "QualityLevelINV12" {
        value "19";
      }
      enum "QualityLevelINV13" {
        value "20";
      }
      enum "QualityLevelINV14" {
        value "21";
      }
      enum "QualityLevelINV15" {
        value "22";
      }
      enum "QualityLevelNSUPP" {
        value "23";
      }
      enum "QualityLevelPRC" {
        value "24";
      }
      enum "QualityLevelPROV" {
        value "25";
      }
      enum "QualityLevelPRS" {
        value "26";
      }
      enum "QualityLevelPRTC" {
        value "27";
      }
      enum "QualityLevelSEC" {
        value "28";
      }
      enum "QualityLevelSMC" {
        value "29";
      }
      enum "QualityLevelSSUA" {
        value "30";
      }
      enum "QualityLevelSSUB" {
        value "31";
      }
      enum "QualityLevelST2" {
        value "32";
      }
      enum "QualityLevelST3" {
        value "33";
      }
      enum "QualityLevelST3E" {
        value "34";
      }
      enum "QualityLevelST4" {
        value "35";
      }
      enum "QualityLevelSTU" {
        value "36";
      }
      enum "QualityLevelTNC" {
        value "37";
      }
      enum "QualityLevelUNC" {
        value "38";
      }
      enum "QualityLevelUNK" {
        value "39";
      }
    }
    description
      "Clock source QL (quality level) as defined in ITU-T G.781.";
    reference
      "ITU-T standard G.781 section 5.4";
  }
  typedef port-type-enumeration {
    type enumeration {
      enum "IfTypeE1" {
        value "1";
      }
      enum "IfTypeT1" {
        value "2";
      }
      enum "IfType2Mhz" {
        value "3";
      }
      enum "IfType2Mbit" {
        value "4";
      }
      enum "IfTypeSDH" {
        value "5";
      }
      enum "IfTypeSONET" {
        value "6";
      }
      enum "IfTypeEthernet" {
        value "7";
      }
      enum "IfTypeOTN" {
        value "8";
      }
    }
    description
      "Sync clock source Interface type.
       Values for this enumeration are specified
       in G.781.";
    reference
      "ITU-T G.781-2017: 5.3.1";
  }
  typedef run-mode-enumeration {
    type enumeration {
      enum "ModeFreeRun" {
        value "1";
      }
      enum "ModeHoldover" {
        value "2";
      }
      enum "ModeLocked" {
        value "3";
      }
    }
    description
      "The clock operation mode.
       Values for this enumeration are specified in G.781.";
    reference
      "ITU-T G.781-2017: 6.3.1";
  }
  container sync-phy {
    description
      "The sync-phy contains all attributes of Sync-PHY,
       optional attributes can be augmented to this node.";
    container sync-node {
      description
        "The sync-node contains all the node-level Sync-PHY
         management attributes for an equipment.";
      leaf sync-network-option {
        type sync-network-option-enumeration;
        description
          "The Network synchronization networking options.
           Values for this enumeration are specified
           in G.781.";
        reference
          "ITU-T G.781-2017: 5.3.1";
      }
      leaf local-quality-level {
        type quality-level-enumeration;
        config false;
        description
          "The local QL retrieved.";
      }
      leaf quality-level-enabled {
        type boolean;
        description
           "Whether QL is enabled or not.";
      }
      leaf revertive-enabled {
        type boolean;
        description
           "Whether revertive mode is enabled or not.";
      }
      leaf wtr-time {
        type uint8 {
          range "0..12";
      }
        default "5";
        description
           "The WTR time in the unit of minute for selection
            processes in common.";
      }
      leaf holdoff-time {
        type uint16 {
          range "300..1800";
      }
        description
          "The Holdoff time in the unit of ms for selection
           processes in common.";
      }
    }
    list port-list {
      key "name";
      description
        "List of one or more PHY ports in the device (see G.871).
         Each item of port-list represents port-level management
         information for a physical port.";

      leaf name {
        type if:interface-ref;
        description
           "The interface name of the physical port.";
      }
      leaf port-type {
        type port-type-enumeration;
        description
           "The interface type of the physical port.";
      }
      leaf sync-enabled {
        type boolean;
        description
           "Whether sync mechanism is enabled or not.";
      }
      leaf ql-overwrite-enabled {
        type boolean;
        description
           "Whether QL overwrite is enabled or not, if not enabled,
            it means QL will pass through.";
      }
      leaf ql-overwrite-val {
        type quality-level-enumeration;
        description
           "The quality level used if overwrite mode is enabled.";
      }
      leaf ql-in {
        type quality-level-enumeration;
        description
           "After overwrite or pass through, the final QL fed into
            the clock.";
      }
      leaf ql-out {
        type quality-level-enumeration;
        description
           "The output QL for the physical port.";
      }
      leaf ssm-transmit-enabled {
        type boolean;
        description
           "Whether SSM transmit is enabled or not.";
      }
    }
    container system-clock {
      description
        "The system-clock contains all attributes on management of
         the system clock in an equipment.";

      list port-list {
        key "name";
        description
             "List of one or more source clock PHY ports for the
              system clock (see G.871).
           Each port-list item represents management information
           on a clock source physical port used in the system
           clock.";
        leaf name {
          type if:interface-ref;
          description
            "The interface name of the clock source physical port.";
        }
        leaf priority {
          type uint32;
          description
            "The source priority of the physical port.";
        }
      }
      leaf selected-source {
        type if:interface-ref;
        description
           "The selected source clock physical port.";
      }
      leaf run-mode {
        type run-mode-enumeration;
        description
           "The run mode of the system clock.";
      }
    }
    container station-clock {
      description
        "The station-clock contains all attributes on management of
         the station clock in an equipment.";
      list port-list {
        key "name";
        description
             "List of one or more source clock PHY ports for the
              station clock (see G.871).
           Each port-list item represents management information
           on a clock source physical port used in the station
           clock.";
        leaf name {
          type if:interface-ref;
          description
           "The interface name of the clock source physical port.";
        }
        leaf priority {
          type uint32;
          description
            "The source priority of the physical port.";
        }
      }
      leaf ql-min {
        type uint8;
        description
          "The minimum QL of the system clock.";
      }
      leaf selected-source {
        type if:interface-ref;
        description
           "The current selected source of the station clock by
            automatic process.";
      }
      leaf out-source {
        type if:interface-ref;
        description
           "The final output source for the station clock.";
      }
    }
  }
}
