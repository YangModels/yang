module service-function {

  namespace "urn:TBD:params:xml:ns:yang:sfc-sf";

  prefix sfc-sf;

  import ietf-inet-types { prefix inet; }
  import ietf-yang-types { prefix yang; }

  organization "Cisco Systems, Inc.";
  contact "Reinaldo Penno <repenno@cisco.com>";

  description
    "This module contains a collection of YANG definitions for
     managing service function.
     It follows closely the constructs of
     http://tools.ietf.org/html/draft-ietf-netmod-interfaces-cfg-12

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-06-05 {
    description
    "Changes based on Opendaylight Testing.";
  }

  // Service Function

  // Service Function Type definitions

  identity service-function-type-indentity {
    description
      "Base identity from which specific service function types are
      derived.";
  }

  identity firewall {
    base "service-function-type-indentity";
    description "Firewall";
  }

  identity dpi {
    base "service-function-type-indentity";
    description "Deep Packet Inspection";
  }

  identity napt44 {
    base "service-function-type-indentity";
    description "Network Address and Port Translation 44";
  }

  typedef service-function-type {
    type identityref {
      base "service-function-type-indentity";
    }
  }

  typedef service-function-ref {
    type leafref {
      path "/sfc-sf:service-functions/sfc-sf:service-function/sfc-sf:name";
    }
    description
      "This type is used by data models that need to reference
       configured service functions.";
  }

  container service-functions {
    description
      "A network or application based packet
      treatment, application, compute or storage resource, used
      singularly or in concert with other service functions within a
      service chain to enable a service offered by an operator.

      A non-exhaustive list of Service Functions includes: firewalls,
      WAN and application acceleration, Deep Packet Inspection (DPI),
      server load balancers, NAT44 [RFC3022], NAT64 [RFC6146], HOST_ID
      injection, HTTP Header Enrichment functions, TCP optimizer, etc.";

    list service-function {
      key "name";
      leaf name {
        type string;
        description
            "The name of the service function.";
      }
      leaf type {
        type service-function-type;
        mandatory true;
      }
      leaf ip-mgmt-address {
        type inet:ip-address;
      }
    }
  }
}
