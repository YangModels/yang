module ietf-wang-i2nsf-extension-nsf-facing-interface {
  yang-version 1.1;
  namespace
    "urn:ietf:params:xml:ns:yang:wang-i2nsf-extension-
     nsf-facing-interface";
  prefix i2nsf-exnfi;
  import ietf-inet-types {
    prefix inet;
    reference "RFC 6991";
  }
  organization
    "IETF I2NSF (Interface to Network Security Functions)
     Working Group";
  contact
    "WG Web: <https://datatracker.ietf.org/wg/i2nsf>
     WG List: <mailto:i2nsf@ietf.org>
     Author: Weilin Wang
     <mailto:21111026@bjtu.edu.cn>
     Author: Qi Guo
     <mailto:20120044@bjtu.edu.cn>
    Author: Shuangxing Deng
    <mailto:21120038@bjtu.edu.cn>";
 description
   "This module is a YANG module for the extension of I2NSF
    NSF-Facing Interface.
    The key words 'MUST', 'MUST NOT', 'REQUIRED', 'SHALL',
    'SHALL NOT', 'SHOULD', 'SHOULD NOT', 'RECOMMENDED',
    'NOT RECOMMENDED', 'MAY', and 'OPTIONAL' in this
    document are to be interpreted as described in BCP 14
    (RFC 2119) (RFC 8174) when, and only when, they appear
    in all capitals, as shown here.
    Copyright (c) 2022 IETF Trust and the persons identified as
    authors of the code. All rights reserved.
    Redistribution and use in source and binary forms, with or
    without modification, is permitted pursuant to, and subject
    to the license terms contained in, the Revised BSD License
    set forth in Section 4.c of the IETF Trust's
    Legal Provisions Relating to IETF Documents
    (https://trustee.ietf.org/license-info).
    This version of this YANG module is part of RFC XXXX
    (https://www.rfc-editor.org/info/rfcXXXX); see the RFC itself
    for full legal notices.";
 revision "2023-03-21"{
   description "Initial revision.";
   reference
     "RFC XXXX: Extension of I2NSF NSF-Facing Interface
      YANG Data Model";
 }
 list i2nsf-security-policy {
   key policy-name;
   description
     "The container for the security policy.";
   leaf policy-name {
     type string;
     description
       "The name of the security policy.";
   }
   container path-configuration-rule {
     description
       "The container for path configuration rule.";
     leaf path-id {
       type string;
       description
         "Identify the different service function paths.";
     }
     container classifiers {
       description
         "The container for classifiers in the service
           function chain (SFC).";
       list classifier {
         key classifier-name;
         description
            "The container for the classifier.";
         leaf classifier-name {
            type string;
            description
              "Use the name to identity the classifier.";
         }
         leaf classifier-ip {
            type inet:ip-address-no-zone;
            description
              "The IPv4 or IPv6 address of the classifier.";
         }
       }
     }
     container nsfs {
       description
         "The container for the nsfs in the
           service function chain (SFC).";
       list nsf {
         key nsf-name;
         description
            "The container for the NSF.";
         leaf nsf-name {
            type string;
            description
              "Use the name to identify the NSF.";
         }
         leaf sequence-number {
            type uint64;
            description
              "Identifies the sequence of the NSF in the
               service function path.";
         }
         container ip-address {
            description
              "The IPv4 or IPv6 address of the NSF and
               the corresponding service function 
               forwarder (SFF).";
            leaf nsf-ip {
              description
                  "The IPv4 or IPv6 address of the NSF.";
                   type inet:ip-address-no-zone;
             }
             leaf sff-ip {
                description
                    "The IPv4 or IPv6 address of the
                      corresponding SFF.";
                 type inet:ip-address-no-zone;
              }
             }
           }
        }
    }
  }
}
