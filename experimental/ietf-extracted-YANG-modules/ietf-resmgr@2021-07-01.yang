module ietf-resmgr {
  yang-version 1.1;
  namespace "urn:ietf:params:xml:ns:yang:ietf-resmgr";
  prefix rrm;

  import ietf-inet-types {
    prefix inet;
    reference
      "RFC6991: Common YANG Data Types";
  }
  import ietf-topology-filter {
    prefix topo-filt;
    reference
      "I-D.bestbar-teas-yang-topology-filter";
  }
  import ietf-routing {
    prefix rt;
    reference
      "RFC8349: A YANG Data Model for Routing Management";
  }

  organization
    "IETF Traffic Engineering Architecture and Signaling (TEAS)
     Working Group.";
  contact
    "WG Web:   <http://tools.ietf.org/wg/teas/>
     WG List:  <mailto:teas@ietf.org>

     Editor:   Tarek Saad
               <mailto:tsaad@juniper.net>

     Editor:   Vishnu Pavan Beeram
               <mailto:vbeeram@juniper.net>";
  description
    "YANG data module for configuration, state, and RPCs of
     a Resource Reservation Manager.
     The model fully conforms to the Network Management
     Datastore Architecture (NMDA).

     Copyright (c) 2019 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  // RFC Ed.: replace XXXX with actual RFC number and remove this
  // note.
  // RFC Ed.: update the date below with the date of RFC publication
  // and remove this note.

  revision 2021-07-01 {
    description
      "Initial revision";
    reference
      "RFC XXXX: A YANG data model for the Resource Reservation
       Manager.";
  }

  identity path-admission-method {
    description
      "Base identity for path admission method.";
  }

  identity path-admission-local {
    base path-admission-method;
    description
      "Indicates path admission is managed local RRM.";
  }

  identity path-admission-external {
    base path-admission-method;
    description
      "Indicates path admission is managed by external RRM.";
  }

  identity path-reservation-style {
    description
      "Base identity for reservation style.";
  }

  identity path-reservation-fixed-filter {
    base path-reservation-style;
    description
      "Fixed-Filter (FF) Style.";
    reference
      "RFC2205";
  }

  identity path-reservation-shared-explicit {
    base path-reservation-style;
    description
      "Shared Explicit (SE) Style.";
    reference
      "RFC2205";
  }

  grouping path-key {
    description
      "Grouping for leafs that identify a specific path.";
    leaf client-id {
      type string;
      description
        "A client identifier";
    }
    leaf source {
      type inet:ip-address;
      description
        "The path source address.";
    }
    leaf destination {
      type inet:ip-address;
      description
        "The path destination address.";
    }
    leaf context {
      type string;
      description
        "The path context set by the tunnel manager. For
         example, this can be the SR Candidate Path name";
    }
    leaf tunnel-id {
      type uint32;
      description
        "The tunnel ID that is shared for multiple path-instances
         belonging to the tunnel.";
    }
    leaf path-instance-id {
      type uint32;
      description
        "The path instance identifier. Multiple path instances may
         be instantiated for the same tunnel.";
    }
    leaf multipath-id {
      type uint32;
      description
        "An identifier that uniquely distinguishes the path within
         a set of multiple paths for a path instance.";
    }
  }

  grouping link-key {
    description
      "A grouping for a link key descriptor";
    leaf local-id {
      type inet:ip-address;
      description
        "Link local identifier.";
    }
    leaf remote-id {
      type inet:ip-address;
      description
        "Link remote identifier.";
    }
    leaf local-domain-id {
      type uint32;
      description
        "The local domain identifier.";
    }
    leaf remote-domain-id {
      type uint32;
      description
        "The remote domain identifier.";
    }
  }

  grouping node-key {
    description
      "Node properties.";
    leaf node-id {
      type inet:ip-address;
      description
        "The node identifier.";
    }
  }

  container resmgr {
    description
      "A container that holds all RRM information.";

    container external-rrms {
      description
        "A container for the list of external RRMs.";

      list external-rrm {
        key "external-rrm-id";
        description
          "An entry in the list of external RRMs.";

        leaf external-rrm-id {
          type inet:ip-address;
          description
            "The IP address of the external RRM managing network
             resources.";
        }
        leaf external-rrm-role {
          type enumeration {
            enum redundancy-active {
              description
                "External RRM in active role.";
            }
            enum redundancy-stanby {
              description
                "External RRM in standby role.";
            }
          }
          description
            "The redundancy role of the external RRM managing the
             network resources.";
        }
        container topology-filter {
          description
            "A container for the set of topology filters that
             describe network resources managed by the RRM.";
          leaf filter {
            type leafref {
              path "/rt:routing/topo-filt:topology-filters/"
                   + "topo-filt:topology-filter/topo-filt:name";
            }
            description
              "A filter that describes the set of network resources
               managed by the RRM.";
          }
          leaf filter-set {
            type leafref {
              path "/rt:routing/topo-filt:topology-filter-sets/"
                   + "topo-filt:topology-filter-set/topo-filt:name";
            }
            description
              "A filter set that describes the network resources
               managed by the RRM.";
          }
        }
      }
    }

    container domains {
      description
        "A container for the list of managed domains.";
      list domain {
        key "domain-id";
        description
          "Represents a domain in the network.";
        leaf domain-id {
          type uint32;
          description
            "The domain identifier.";
        }
        container nodes {
          description
            "A container for the list of managed nodes.";
          list node {
            key "node-id";
            description
              "Represents a node entry in a domain.";
            uses node-key;
            // Node attributes
            container links {
              description
                "A container for the list of managed links.";
              list link {
                key "local-id remote-id";
                description
                  "A resource reservation managed link entry.";
                uses link-key;
                // Static Link attributes
                leaf total-bw {
                  type uint64;
                  description
                    "Link total bandwidth (capacity) of this link.";
                }
                leaf max-reservable-bw {
                  type uint64;
                  description
                    "The maximum reservable bandwidth of this link.";
                }
                leaf max-link-bw {
                  type uint64;
                  description
                    "The maximum bandwidth of this link.";
                }
                leaf link-name {
                  type string;
                  description
                    "The symbolic name of this link (e.g. FQDN).";
                }
                list available-bw {
                  key "priority";
                  config false;
                  description
                    "A list of available bandwidth (by priority).";
                  leaf priority {
                    type uint8;
                    description
                      "The reservation priority.";
                  }
                  leaf val {
                    type uint64;
                    description
                      "Available bandwidth value at specific
                       priority.";
                  }
                }
                leaf admission-method {
                  type identityref {
                    base path-admission-method;
                  }
                  default "path-admission-local";
                  description
                    "The path admission method. By default, it is
                     locally managed by the RRM.";
                }
                container external-rrm {
                  when "derived-from-or-self(../admission-method, "
                     + "'path-admission-external')" {
                    description
                      "The external RRM where the path admission is
                       managed.";
                  }
                  description
                    "The container that holds information about
                     RRM external server managing path admission.";
                  leaf resmgr-server-address {
                    type inet:ip-address;
                    description
                      "The IP address of the RRM server externally
                       managing link resources.";
                  }
                }
                // Admitted paths
                container paths {
                  description
                    "A container for the list of admitted paths on a
                     link.";
                  list path {
                    key "client-id tunnel-id path-instance-id"
                      + " multipath-id source destination";
                    description
                      "A list of paths admitted on a link.";
                    uses path-key;
                    leaf admission-timestamp {
                      type uint64;
                      description
                        "The admission timestamp.";
                    }
                    leaf admission-bw {
                      type uint64;
                      description
                        "The admitted bandwidth on this link.";
                    }
                    leaf admission-priority {
                      type uint8;
                      description
                        "The admission priority for this path.";
                    }
                    leaf admission-reservation-style {
                      type identityref {
                        base path-reservation-style;
                      }
                      default "path-reservation-shared-explicit";
                      description
                        "The path admssion bandwidth reservation
                         style.";
                    }
                  }
                }
              }
            }
          }
        }
      }
    }
  }

  rpc path-admit {
    description
      "Input arguments for the RPC to admit/release a path on a
       specific set of resource links.";
    input {
      leaf action {
        type enumeration {
          enum add {
            description
              "Operation add.";
          }
          enum delete {
            description
              "Operation delete.";
          }
        }
        description
          "Admit/release RPC.";
      }
      container path-info {
        description
          "A container that includes information about the admitted
           path.";
        uses path-key;
        leaf admission-priority {
          type uint8;
          description
            "The admission priority for this path.";
        }
        container nodes {
          description
            "A container for the list of nodes that the path is being
             admitted on.";
          list node {
            key "node-id";
            description
              "A node that holds resources for the admitted path.";
            uses node-key;
            leaf node-name {
              type string;
              description
                "The symbolic name of this node (e.g. FQDN).";
            }
            // Node attributes
            container links {
              description
                "A container for the list of links used by the
                 admitted path.";
              list link {
                key "local-id remote-id";
                description
                  "A link that is used by the admitted path.";
                uses link-key;
                leaf admission-bw {
                  type uint64;
                  description
                    "The admitted bandwidth on this link.";
                }
              }
            }
          }
        }
      }
    }
    output {
      leaf result {
        type enumeration {
          enum unknown {
            description
              "The RPC result is unknown.";
          }
          enum successful {
            description
              "The RPC result is successful.";
          }
          enum rejected {
            description
              "The RPC result is rejected.";
          }
          enum in-progress {
            description
              "The RPC result is in-progress.";
          }
        }
        description
          "Result of admission RPC.";
      }
    }
  }

  rpc topology-update {
    description
      "Input arguments for the RPC to update the topological
       elements managed by the Resource Reservation Manager.";
    input {
      leaf topology-element-type {
        type enumeration {
          enum link {
            description
              "Topology element link type.";
          }
          enum node {
            description
              "Topology element node type.";
          }
        }
        description
          "Type of topology element.";
      }
      leaf action {
        type enumeration {
          enum add {
            description
              "Operation add.";
          }
          enum delete {
            description
              "Operation delete.";
          }
        }
        description
          "Add/delete topology element.";
      }
      container topology-elemnt-info {
        description
          "A container for the network element information.";
        choice element-type {
          mandatory true;
          description
            "The network element type.";
          case ne-link {
            uses link-key;
          }
          case ne-node {
            uses node-key;
          }
        }
      }
    }
  }
}
