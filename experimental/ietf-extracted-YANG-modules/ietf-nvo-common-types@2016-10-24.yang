module ietf-nvo-common-types {
    namespace "urn:ietf:params:xml:ns:yang:ietf-nvo-common-types" ;
    prefix CommonTypes ;
    import ietf-yang-types {
        prefix yang;
    }

    organization "" ;
    contact "";
    description "ietf-nvo-common-types";
    revision 2016-10-24 {
        reference "draft-chen-opsawg-composite-vpn-dm-00";
    }

    typedef AdminStatus {
        type enumeration {
            enum active {
                description "Active status";
            }
            enum inactive {
                description "Inactive status";
            }
            enum partial {
                description "Partial status";
            }
        }
        description "AdminStatus";
    }

    typedef OperStatus {
        type enumeration {
            enum up {
                description "Up status";
            }
            enum down {
                description "Down status";
            }
            enum degrade {
                description "Degrade status";
            }
        }
        description "OperStatus";
    }

    typedef SyncStatus {
        type enumeration {
            enum SYNC {
                description "Sync status";
            }
            enum OUT-SYNC {
                description "Out sync status";
            }
        }
        description "SyncStatus";
    }

    typedef Topology {
        type enumeration {
            enum full-mesh {
                description "full-mesh";
            }
            enum point_to_multipoint {
                description "point_to_multipoint";
            }
            enum point_to_point {
                description "point_to_point";
            }
            enum complex {
                description "complex";
            }
        }
        description "Topology";
    }

    typedef Technology {
        type enumeration {
            enum mpls {
                description "mpls";
            }
            enum rosen_multivpn {
                description "rosen_multivpn";
            }
            enum ng_multivpn {
                description "ng_multivpn";
            }
            enum vxlan_overlay_l3vpn {
                description "vxlan_overlay_l3vpn";
            }
            enum eth_oversdh {
                description "eth_oversdh";
            }
        }
        description "Technology";
    }

    typedef TopoNodeRole {
        type enumeration {
            enum other {
                description "other";
            }
            enum hub {
                description "hub";
            }
            enum spoke {
                description "spoke";
            }
        }
        description "TopoNodeRole";
    }

    typedef TpType{
        type enumeration {
            enum nop {
                description "nop";
            }
            enum PTP {
                description "PTP";
            }
            enum CTP {
                description "CTP";
            }
            enum TRUNK {
                description "TRUNK";
            }
            enum LoopBack {
                description "LoopBack";
            }
            enum TPPool {
                description "TPPool";
            }
        }
        description "TpType";
    }

    typedef LayerRate{
        type enumeration {
            enum LR_UNKNOW {
                description "LR_UNKNOW";
            }
            enum LR_IP {
                description "LR_IP";
            }
            enum LR_ETHERNET {
                description "LR_ETHERNET";
            }
            enum LR_VXLAN {
                description "LR_VXLAN";
            }
        }
        description "LayerRate";
    }

    typedef EthernetEncapType {
        type enumeration {
            enum DEFAULT {
                description "DEFAULT";
            }
            enum DOT1Q {
                description "DOT1Q";
            }
            enum QINQ {
                description "QINQ";
            }
            enum UNTAG {
                description "UNTAG";
            }
        }
        description "EthernetEncapType";
    }
    typedef EthernetAction {
        type enumeration {
            enum nop {
                description "nop";
            }
            enum UNTAG {
                description "UNTAG";
            }
            enum STACKING {
                description "STACKING";
            }
        }
        description "EthernetAction";
    }

    typedef RouteProtocolType {
        type enumeration {
            enum staticRouting {
                description "staticRouting";
            }
            enum bgp {
                description "bgp";
            }
            enum rip {
                description "rip";
            }
            enum ospf {
                description "ospf";
            }
            enum isis {
                description "isis";
            }
        }
        description "RouteProtocolType";
    }

    typedef QosPriorityType {
        type enumeration {
            enum nop {
                description "nop";
            }
            enum 802dot1p {
                description "802dot1p";
            }
            enum dscp {
                description "dscp";
            }
            enum mplsExp {
                description "mplsExp";
            }
            enum cos {
                description "cos";
            }
            enum ipPrecedence {
                description "ipPrecedence";
            }
        }
        description "QosPriorityType";
    }

    typedef ColorType {
        type enumeration {
            enum nop {
                description "nop";
            }
            enum green {
                description "green";
            }
            enum yellow {
                description "yellow";
            }
            enum red {
                description "red";
            }
        }
        description "ColorType";
    }

    grouping nvStringList{
        description "nvStringList Grouping.";

        list nvstringList {
            key "name";
            uses CommonTypes:nvstring;
            description "nvStringList";
        }
    }

    grouping nvstring {
        description "nvstring Grouping.";
        leaf name {
            type string;
            description "string name ";
        }
        leaf value {
            type string;
            description "string value";
        }
    }

    typedef FlowClassifierType {
        type enumeration {
            enum nop {
                description "nop";
            }
            enum 802dot1p {
                description "802dot1p";
            }
            enum dscp {
                description "dscp";
            }
            enum cos {
                description "cos";
            }
            enum mpls-exp {
                description "mpls-exp";
            }
            enum sourceIP {
                description "sourceIP";
            }
            enum destinationIP {
                description "destinationIP";
            }
        }
        description "FlowClassifierType";
    }

    grouping ObjectIdentifiers {
        description "ObjectIdentifiers Grouping.";

        list ObjectIdentifiers {
            key "obejctId";
            uses CommonTypes:ObjectIdentifier;
            description "ObjectIdentifiers";
        }
    }

    grouping ObjectIdentifier {
        description "ObjectIdentifier Grouping.";

        leaf objectType {
            type CommonTypes:ObjectType;
            description "objectType";
        }

        leaf obejctId {
            type yang:uuid;
            description "obejctId";
        }

        leaf roleLable {
            type string {length "0..200";}
            description "here is the route role";
        }
    }

    typedef ObjectType {
        type enumeration {
            enum nop {
                description "nop";
            }
            enum SEG-VPN {
                description "SEG-VPN";
            }
            enum TP {
                description "TP";
            }
            enum TPL {
                description "TPL";
            }
            enum NE {
                description "NE";
            }
            enum BUSINESSTYPE {
                description "BUSINESSTYPE";
            }
            enum COMPOSED-VPN {
                description "COMPOSED-VPN";
            }
            enum SUBNETWORK {
                description "SUBNETWORK";
            }
        }
        description "ObjectType";
    }

    typedef EdgePointRole {
        type enumeration {
            enum nop {
                description "nop";
            }
            enum PE {
                description "PE";
            }
            enum P {
                description "P";
            }
            enum UNI {
                description "UNI";
            }
            enum NNI {
                description "NNI";
            }
            enum AsbTP {
                description "AsbTP";
            }
        }
        description "EdgePointRole";
    }

    typedef DomainRole {
        type enumeration {
            enum nop {
                description "nop";
            }
            enum external {
                description "external";
            }
            enum internal {
                description "internal";
            }
            enum asb {
                description "asb";
            }
        }
        description "DomainRole";
    }

    grouping CommandResult {
        description "this is the common result which is send back by
        server by RPC response";
        leaf resultCode {
            type int32;
            description "resultCode";
        }
        leaf-list successResourceList {
            type yang:uuid;
            description "successResourceList";
        }
        list failedResourceList {
            uses CommonTypes:FailedNode;
            description "failedResourceList";
        }
        leaf errorReason {
            type string {length "0..200";}
            description "errorReason";
        }
    }

    grouping FailedNode {
        description "fail reason for each object.";
        leaf resourceId {
            type yang:uuid;
            description "failed object.";
        }
        leaf errorReason {
            type string {length "0..200"; }
            description "errorReason";
        }
    }

    grouping SLA {
        description "SLA";
        leaf latency {
            type uint32;
            description "delay,unit:ms.";
        }
    }

    typedef ConnectionDirection {
        type enumeration {
            enum CD-UNI {
                description "CD-UNI";
            }
            enum CD-BI {
                description "CD-BI";
            }
        }
        description "ConnectionDirection";
    }

    typedef ObjectDirection {
        type enumeration {
            enum IN {
                description "IN";
            }
            enum OUT {
                description "OUT";
            }
            enum BI-DIRECTION {
                description "BI-DIRECTION";
            }
        }
        description "ObjectDirection";
    }

    typedef DiversityType {
        type enumeration {
            enum NOP {
                description "NOP";
            }
            enum PE-DIFF {
                description "PE-DIFF";
            }
            enum MAIN-TP-DIFF {
                description "MAIN-TP-DIFF";
            }
        }
        description "DiversityType";
    }
}
