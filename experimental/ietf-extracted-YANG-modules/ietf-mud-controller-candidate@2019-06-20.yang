module ietf-mud-controller-candidate {
  yang-version 1.1;
  namespace "urn:ietf:params:xml:ns:yang:ietf-mud-controller-candidate";
  prefix mud-cc;

  import ietf-mud {
    prefix "mud";
  }

  import ietf-inet-types {
    prefix "inet";
  }

  organization
    "IETF OPSAWG (Ops Area) Working Group";
  contact
    "WG Web: http://tools.ietf.org/wg/opsawg/
     WG List: opsawg@ietf.org
     Author: Eliot Lear
     lear@cisco.com
    ";
  description

    "This YANG module augments the ietf-mud model to provide for two
     optional lists to indicate that this device type may be used as
     a controller for other MUD-enabled devices.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
       (https://trustee.ietf.org/license-info).

     This version of this YANG module is part of RFC XXXX
     (https://www.rfc-editor.org/info/rfcXXXX); see the RFC itself
      for full legal notices.

     The key words 'MUST', 'MUST NOT', 'REQUIRED', 'SHALL', 'SHALL
     NOT', 'SHOULD', 'SHOULD NOT', 'RECOMMENDED', 'NOT RECOMMENDED',
    'MAY', and 'OPTIONAL' in this document are to be interpreted as
     described in BCP 14 (RFC 2119) (RFC 8174) when, and only when,
    they appear in all capitals, as shown here.
";

  revision 2019-06-20 {
    description
      "Initial proposed standard.";
    reference "RFC XXXX: QoS for MUD Specification";
  }

  grouping mud-controller-candidates {
    description
      "Controller candidate grouping";
    container controller-candidates {
      description
        "Lists of controller candidates.";
      leaf-list urls {
        type inet:uri;
        description
          "a list of mud urls this device is designed to control.
           Each entry may end with a * to indicate a wildcard that
           matches zero or more of characters from that point.  A
           wildcard MUST NOT appear in the authority section of the
           URL.";
        }
        leaf-list classes {
          type inet:uri;
          description
            "A list of URIs that are used as classes in MUD files,
             indicating that this device can serve as a controller
             in those classes.";
        }
      }
    }

  augment "/mud:mud" {
    uses mud-controller-candidates;
    description
      "add controller candidate list";
  }
}
