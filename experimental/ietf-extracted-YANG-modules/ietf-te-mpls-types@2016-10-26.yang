module ietf-te-mpls-types {

  namespace "urn:ietf:params:xml:ns:yang:ietf-te-mpls-types";

  /* Replace with IANA when assigned */
  prefix "te-mpls-types";

  import ietf-inet-types {
    prefix inet;
  }

  import ietf-mpls {
    prefix mpls;
  }

  organization
    "IETF TEAS Working Group";

  contact "Fill me";

  description
    "This module contains a collection of generally
    useful TE specific YANG data type defintions.";

  revision "2016-10-26" {
    description "Latest revision of TE MPLS types";
    reference "RFC3209";
  }

  identity backup-protection-type {
    description
      "Base identity for backup protection type";
  }

  identity backup-protection-link {
    base backup-protection-type;
    description
      "backup provides link protection only";
  }
  identity backup-protection-node-link {
    base backup-protection-type;
    description
      "backup offers node (preferred) or link protection";
  }

  identity bc-model-type {
    description
      "Base identity for Diffserv-TE bandwidth constraint
      model type";
  }

  identity bc-model-rdm {
    base bc-model-type;
    description
      "Russian Doll bandwidth constraint model type.";
  }

  identity bc-model-mam {
    base bc-model-type;
    description
      "Maximum Allocation bandwidth constraint
      model type.";
  }

  identity bc-model-mar {
    base bc-model-type;
    description
      "Maximum Allocation with Reservation
      bandwidth constraint model type.";
  }

  grouping bandwidth-constraint-values {
    description
      "Packet bandwidth contraints values";
    choice value-type {
      description
        "Value representation";
      case percentages {
        container perc-values {
          uses bandwidth-mpls-constraints;
          description
            "Percentage values";
        }
      }
      case absolutes {
        container abs-values {
          uses bandwidth-mpls-constraints;
          description
            "Absolute values";
        }
      }
    }
  }

  grouping bandwidth-mpls-reservable {
    description
      "Packet reservable bandwidth";
    choice bandwidth-value {
      description "Reservable bandwidth configuraiton choice";
      case absolute {
        leaf absolute-value {
          type uint32;
          description "Absolute value of the bandwidth";
        }
      }
      case precentage {
        leaf percent-value {
          type uint32 {
            range "0..4294967295";
          }
          description "Percentage reservable bandwidth";
        }
        description
          "The maximum reservable bandwidth on the
          interface";
      }
    }
    choice bc-model-type {
      description
        "Reservable bandwidth percentage capacity
        values.";
      case bc-model-rdm {
        container bc-model-rdm {
          description
            "Russian Doll Model Bandwidth Constraints.";
          uses bandwidth-mpls-constraints;
        }
      }
      case bc-model-mam {
        container bc-model-mam {
          uses bandwidth-mpls-constraints;
          description
            "Maximum Allocation Model Bandwidth
            Constraints.";
        }
      }
      case bc-model-mar {
        container bc-model-mar {
          uses bandwidth-mpls-constraints;
          description
            "Maximum Allocation with Reservation Model
            Bandwidth Constraints.";
        }
      }
    }
  }

  typedef bfd-type {
    type enumeration {
      enum classical {
        description "BFD classical session type.";
      }
      enum seamless {
        description "BFD seamless session type.";
      }
    }
    default "classical";
    description
      "Type of BFD session";
  }

  typedef bfd-encap-mode-type {
    type enumeration {
      enum gal {
        description
          "BFD with GAL mode";
      }
      enum ip {
        description
          "BFD with IP mode";
      }
    }
    default ip;
    description
      "Possible BFD transport modes when running over TE
      LSPs.";
  }

  grouping bandwidth-mpls-constraints {
    description "Bandwidth constraints.";
    container bandwidth-mpls-constraints {
      description
        "Holds the bandwidth contraints properties";
      leaf maximum-reservable {
        type uint32 {
          range "0..4294967295";
        }
        description
          "The maximum reservable bandwidth on the
          interface";
      }
      leaf-list bc-value {
        type uint32 {
          range "0..4294967295";
        }
        max-elements 8;
        description
          "The bandwidth contraint type";
      }
    }
  }

  grouping tunnel-forwarding-properties {
    description "Properties for using tunnel in forwarding.";
    container forwarding {
      description
        "Tunnel forwarding properties container";
      leaf binding-label {
        type mpls:mpls-label;
        description "MPLS tunnel binding label";
      }
      leaf load-share {
        type uint32 {
          range "1..4294967295";
        }
        description "ECMP tunnel forwarding
          load-share factor.";
      }
      choice policy-type {
        description
          "Tunnel policy type";
        container class {
          description
            "Tunnel forwarding per class properties";
          leaf class {
            type uint8 {
              range "1..7";
            }
            description
              "The class associated with this tunnel";
          }
        }
        container group {
          description
            "Tunnel frowarding per group properties";
          leaf-list classes {
            type uint8 {
              range "1..7";
            }
            description
              "The forwarding class";
          }
        }
      }
    }
  }

  grouping tunnel-routing-properties {
    description
      "TE tunnel routing properties";
    choice routing-choice {
      description
        "Announces the tunnel to IGP as either
        autoroute or forwarding adjacency.";
      case autoroute {
        container autoroute-announce {
          presence "Enable autoroute announce.";
          description
            "Announce the TE tunnel as autoroute to
            IGP for use as IGP shortcut.";
          leaf-list routing-afs {
            type inet:ip-version;
            description
              "Address families";
          }
          choice metric-type {
            description
              "Type of metric to use when announcing
              the tunnel as shortcut";
            leaf metric {
              type uint32 {
                range "1..2147483647";
              }
              description
                "Describes the metric to use when
                announcing the tunnel as shortcut";
            }
            leaf relative-metric {
              type int32 {
                range "-10..10";
              }
              description
                "Relative TE metric to use when
                announcing the tunnel as shortcut";
            }
            leaf absolute-metric {
              type uint32 {
                range "1..2147483647";
              }
              description
                "Absolute TE metric to use when
                announcing the tunnel as shortcut";
            }
          }
        }
      }
      case forwarding-adjacency {
        container forwarding-adjacency {
          presence "Enable forwarding adjacency
            on the tunnel.";
          description
            "Announce the TE tunnel
            as forwarding adjacency.";
          leaf holdtime {
            type uint32 {
              range "0..4294967295";
            }
            description
              "Holdtime in seconds after
              tunnel becomes UP.";
          }
          leaf-list routing-afs {
            type inet:ip-version;
            description
              "Address families";
          }
        }
      }
    }
  }
}
