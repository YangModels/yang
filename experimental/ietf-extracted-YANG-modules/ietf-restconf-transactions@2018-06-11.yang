module ietf-restconf-transactions {

  namespace
    "urn:ietf:params:xml:ns:yang:ietf-restconf-transactions";

  prefix rct;

  organization
    "IETF NETCONF (Network Configuration) Working Group";

  contact
    "WG Web:   <https://tools.ietf.org/wg/netconf/>
     WG List:  <mailto:netconf@ietf.org>

     WG Chair: Kent Watsen
               <mailto:kwatsen@juniper.net>

     WG Chair: Mahesh Jethanandani
               <mailto:mjethanandani@gmail.com>

     Editor:   Ladislav Lhotka
               <mailto:lhotka@nic.cz>";
  description
    "This module defines operations that implement transactions in
     the RESTCONF protocol.

     Copyright (c) 2018 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     The key words 'MUST', 'MUST NOT', 'REQUIRED', 'SHALL', 'SHALL
     NOT', 'SHOULD', 'SHOULD NOT', 'RECOMMENDED', 'MAY', and
     'OPTIONAL' in the module text are to be interpreted as described
     in RFC 2119 (https://tools.ietf.org/html/rfc2119).

     This version of this YANG module is part of RFC XXXX
     (https://tools.ietf.org/html/rfcXXXX); see the RFC itself for
     full legal notices.";

  revision 2018-06-11 {
    description
      "Initial revision.";
    reference
      "RFC XXXX: RESTCONF with Transactions";
  }

  /* Operations */

  rpc commit {
    description
      "Atomically merge the contents of client's staging datastore
       into the intended datastore.

       If a merge conflict occurs that cannot be automatically
       resolved, the server SHALL send an error report with
       error-app-tag set to 'merge-conflict' and error-info
       indicating the reason for the conflict.";
  }

  rpc reset {
    description
      "Reset the client's staging datastore so that its contents is
       identical to the contents of the intended repository.";
  }
}
