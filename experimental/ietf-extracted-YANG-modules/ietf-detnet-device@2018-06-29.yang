module ietf-detnet-device {
  namespace "urn:ietf:params:xml:ns:yang:ietf-detnet-device";
  prefix "detnet-device";

  organization "IETF DetNet Working Group";
  contact
    "WG Web:   <http://tools.ietf.org/wg/detnet/>
     WG List:  <mailto: detnet@ietf.org>
     WG Chair: Lou Berger
               <mailto:lberger@labn.net>
     Editor:  Xuesong Geng
              <mailto:gengxuesong@huawei.com>
     Editor:  Mach Chen
              <mailto:mach.chen@huawei.com>
     Editor:  Zhenqiang Li
              <lizhenqiang@chinamobile.com>
     Eidtor:  Reshad Rahman
              <rrahman@cisco.com>";
     description
       "This YAGN module describes the parameters needed
        for DetNet configuration in device";
  revision "2018-06-29" {
    description
      "Latest revision for ietf-detnet-device";
    reference
      "RFC XXXX: YANG Data Model for ietf-detnet-device";
  }

  grouping detnet-device-parameters {
    description
      "Parameters of queuing, bandwidth on device.";
    leaf PEF-enabled {
      type boolean;
      description
        "A Packet Elimination Function (PEF) eliminates duplicate
         copies of packets to prevent excess packets flooding the
         network or duplicate packets being sent out of the DetNet
         domain.  PEF can be implemented by an edge node, a relay
         node, or an end system.";
    }
    leaf PRF-enabled {
      type boolean;
      description
        "A Packet Replication Function (PRF) replicates DetNet flow
         packets and forwards them to one or more next hops in the
         DetNet domain.  The number of packet copies sent to each next
         hop is a DetNet flow specific parameter at the node doing the
         replication.  PRF can be implemented by an edge node, a relay
         node, or an end system.";
    }
    leaf POF-enabled {
      type boolean;
      description
        "A Packet Ordering Function (POF) re-orders packets within a
         DetNet flow that are received out of order.  This function
         can be implemented by an edge node, a relay node, or an end
         system.";
    }

    container detnet-interfaces {
      description
        "A list of interfaces that are DetNet enabled.";
    //Edior notes: This is heavily related to the YANG models
    //defined in IEEE Qcw project.
    }
  }

  container detnet-device-config {
    description
      "DetNet device configurations.";
    uses detnet-device-parameters;
  }

  container detnet-device-states {
    config false;
    description
      "DetNet device states.";
    uses detnet-device-parameters;
  }
}
