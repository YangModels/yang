module ietf-notification-capabilities {
  yang-version 1.1;
  namespace
    "urn:ietf:params:xml:ns:yang:ietf-notification-capabilities";
  prefix inc;

  import ietf-yang-push    {
    prefix yp;
    description
      "The module ietf-yang-push is REQUIRED to be
        implemented.";
  }

  import ietf-system-capabilities {
    prefix sysc;
    description
      "The module ietf-system-capabilities is REQUIRED to be
        implemented.";
  }

  organization
    "IETF NETCONF (Network Configuration) Working Group";
  contact
    "WG Web:   <https://datatracker.ietf.org/wg/netconf/>
     WG List:  <mailto:netconf@ietf.org>

     Editor:   Balazs Lengyel
               <mailto:balazs.lengyel@ericsson.com>";
  description
    "This module specifies YANG-Push related publisher capabilities.

     The module contains
     - specification of which data nodes support on-change or periodic
     notifications.
     - capabilities related to the throughput of notification data the
     publisher can support. (Note that for a specific subscription
     the publisher MAY still allow only longer periods or smaller
     updates depending on e.g., actual load conditions.)

     Capability values can be specified on system/publisher level,
     datastore level or for specific data nodes (and their contained
     sub-tree) of a specific datastore, as defined in the
     ietf-system-capabilities module.

     If, different data nodes covered by a single subscription
     have different values for a specific capability, then using values
     that are only acceptable for some of these data nodes, but not for
     others, may result in the rejection of the subscription.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX
     (https://www.rfc-editor.org/info/rfcXXXX); see the RFC itself
     for full legal notices.";

  revision 2020-01-02 {
    description
      "Initial version";
    reference
      "RFC XXX: YANG-Push Notification Capabilities";
  }

  grouping subscription-capabilities {
    description  "Capabilities related to YANG-Push subscriptions
      and notifications";

    container subscription-capabilities {
      description "Capabilities related to YANG-Push subscriptions
        and notifications";

      typedef notification-support {
        type enumeration {
          enum no-notifications-supported {
            description "The publisher is not capable of sending any
              notifications for the relevant scope and subscription
              type." ;
          }
          enum notifications-for-config-changes-supported {
            description "The publisher is capable of sending
              notifications for config=true nodes, but not
              for config=false nodes for the relevant scope
              and subscription type." ;
          }
          enum notifications-for-state-changes-supported {
            description "The publisher is capable of sending
              notifications for config=false nodes, but not
              for config=true nodes for the relevant scope
              and subscription type." ;
          }
          enum notifications-for-all-changes-supported {
            description "The publisher is capable of sending
              notifications for both config=false and config=true
              nodes for the relevant scope and subscription type." ;
          }
        }
        description "Type for defining whether on-change or
          periodic notifications are supported for no, only config=true,
          only config=false or all data nodes.";
      }

      choice update-period {
        description "Supported update period value or values for
          periodic subscriptions.";
        leaf minimum-update-period {
          type uint32;
          units "centiseconds";
          description "Indicates the minimal update period that is
            supported for a periodic subscription.
            A periodic subscription to the selected data nodes must
            specify a value that is at least as large or greater than
            this";
          reference
            "The period leaf in RFC 8641 ietf-yang-push YANG module";
        }

        leaf-list supported-update-period {
          type uint32;
          units "centiseconds";
          description "Supported update period values for a
            periodic subscription.
            A periodic subscription to the selected data nodes must
            specify one of the values in the list; other values
            are not supported.";
          reference
            "The period leaf in RFC 8641 ietf-yang-push YANG module";
        }
      }

      leaf max-objects-per-update {
        type uint32 {
              range "1..max";
        }
        description
          "Maximum number of objects that can be sent
           in an update for the selected data nodes.";
      }

      leaf minimum-dampening-period {
        if-feature yp:on-change;
        type uint32;
        units "centiseconds";
        description
          "The minimum dampening period supported for on-change
           subscriptions for the selected data nodes.";
      }

      leaf on-change-supported {
        if-feature yp:on-change;
        type notification-support;
        description
          "Specifies whether the publisher is capable of
           sending on-change notifications for the selected
           data store or data nodes and the subtree below them.";
      }

      leaf periodic-notifications-supported {
        type notification-support;
        description
          "Specifies whether the publisher is capable of
           sending periodic notifications for the selected
           data store or data nodes and the subtree below them.";
      }

      leaf-list supported-excluded-change-type {
        if-feature yp:on-change;
        type union {
          type enumeration {
            enum none {
              description "None of the change types can be excluded.";
            }
            enum all {
              description
                "Any combination of change types can be excluded.";
            }
          }
          type yp:change-type;
        }
        description "The change types that can be excluded in
          YANG-Push subscriptions.";
      }
    }
  }

  augment /sysc:system-capabilities {
    description "Add system level capabilities";
    uses subscription-capabilities {
      refine subscription-capabilities/supported-excluded-change-type {
        default none;
      }
    }
  }
  augment "/sysc:system-capabilities/sysc:datastore-capabilities" +
      "/sysc:per-node-capabilities" {
    description "Add datastore and node level capabilities";
    uses subscription-capabilities {
      refine subscription-capabilities/supported-excluded-change-type {
        default none;
      }
    }
  }
}
