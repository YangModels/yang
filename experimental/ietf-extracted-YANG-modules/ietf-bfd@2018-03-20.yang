module ietf-bfd {

  yang-version 1.1;

  namespace "urn:ietf:params:xml:ns:yang:ietf-bfd";

  prefix "bfd";

  import ietf-bfd-types {
    prefix "bfd-types";
    // RFC Ed.: replace XXXX with actual RFC number and remove this
    // note
    reference "RFC XXXX: YANG Data Model for BFD";
  }

  import ietf-routing {
    prefix "rt";
    reference
      "RFC 8349: A YANG Data Model for Routing Management
       (NMDA version)";
  }

  organization "IETF BFD Working Group";

  contact
    "WG Web:   <http://tools.ietf.org/wg/bfd>
     WG List:  <rtg-bfd@ietf.org>

     Editors:  Reshad Rahman (rrahman@cisco.com),
               Lianshu Zheng (vero.zheng@huawei.com),
               Mahesh Jethanandani (mjethanandani@gmail.com)";

  description
    "This module contains the YANG definition for BFD parameters as
     per RFC 5880.

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note

  reference "RFC XXXX";

  revision 2018-03-20 {
    description "Initial revision.";
    reference "RFC XXXX: YANG Data Model for BFD";
  }

  augment "/rt:routing/rt:control-plane-protocols/"
        + "rt:control-plane-protocol" {
     when "derived-from-or-self(rt:type, 'bfd-types:bfdv1')" {
      description
        "This augmentation is only valid for a control-plane protocol
         instance of BFD (type 'bfdv1').";
    }
    description "BFD augmentation.";

    container bfd {
      description "BFD top level container.";

      uses bfd-types:session-statistics-summary;
    }
  }
}
