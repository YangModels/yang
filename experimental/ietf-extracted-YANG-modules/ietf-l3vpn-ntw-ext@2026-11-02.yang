module ietf-l3vpn-ntw-ext {
  yang-version 1.1;
  namespace "urn:ietf:params:xml:ns:yang:ietf-l3vpn-ntw-ext";
  prefix l3nm-ext;

  import ietf-l3vpn-ntw {
    prefix l3nm;
    reference
      "RFC 9182: A YANG Network Data Model for Layer 3 VPNs";
  }
  import ietf-yang-types {
    prefix yang;
    reference
      "RFC 6991: Common YANG Data Types";
  }
  import ietf-inet-types {
    prefix inet;
    reference
      "RFC 6991: Common YANG Data Types";
  }
  import ietf-schedule {
    prefix schedule;
    reference
      "RFC 9922: A Common YANG Data Model for Scheduling";
  }

  organization
    "IETF ONSEN Working Group";
  contact
    "WG Web:   <https://datatracker.ietf.org/wg/onsen/>
     WG List:  <mailto:onsen@ietf.org>

     Editor:   Cancan Huang
               <mailto:huangcanc@chinatelecom.cn>
               Chongfeng Xie
               <mailto:xiechf@chinatelecom.cn>";
  description
    "This YANG module defines extensions to the L3VPN Network
     Model (L3NM) to support enhanced service features:
     time-scheduled networking provisioning, time-scheduled
     bandwidth adjustment,
     QoS enhancements (isolation, unified traffic
     classification, and time-scheduled QoS action rules),
     performance monitoring, and quantum-safe
     encryption.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2026 IETF Trust and the persons identified
     as authors of the code.  All rights reserved.

     Redistribution and use in source and binary forms, with or
     without modification, is permitted pursuant to, and
     subject to the license terms contained in, the Revised
     BSD License set forth in Section 4.c of the IETF Trust's
     Legal Provisions Relating to IETF Documents
     (https://trustee.ietf.org/license-info).

     This version of this YANG module is part of RFC XXXX; see
     the RFC itself for full legal notices.";

  revision 2026-11-02 {
    description
      "Time-scheduled QoS action rules added; dynamic-*
       constructs renamed to time-scheduled-*; ietf-schedule
       grouping reference fixed to icalendar-recurrence;
       BCP 14 boilerplate added; period and recurrence
       schedule branches wrapped in containers to avoid a
       duplicate 'time-zone-identifier' leaf
       (validation feedback).";
    reference
      "RFC XXXX: Extensions to the YANG Network Data Model
       for L3VPN";
  }

  /* Features */
  feature time-scheduled-l3vpn {
    description
      "Support for time-scheduled L3VPN service provisioning:
       dynamic service requirements realized as time-scheduled
       resource reservations.";
  }

  feature time-scheduled-networking {
    if-feature time-scheduled-l3vpn;
    description
      "Support for time-scheduled networking provisioning:
       scheduled activation and deactivation of VPN
       connectivity.";
  }

  feature time-scheduled-bandwidth-adjustment {
    if-feature time-scheduled-l3vpn;
    description
      "Support for time-scheduled bandwidth adjustment:
       temporary, scheduled bandwidth scaling on top of a
       persistent baseline bandwidth.";
  }

  feature unified-classification {
    description
      "Support for unified traffic classification policies
       defined outside the 'qos' container and reusable across
       functional modules.";
  }

  feature qos-isolation {
    description
      "Support for binding isolation requirements to QoS
       classes.";
  }

  feature perf-mon {
    description
      "Support for end-to-end performance monitoring between
       VPN nodes.";
  }

  feature perf-mon-custom {
    if-feature perf-mon;
    description
      "Support for custom (service-specific) performance
       monitoring configuration.";
  }

  feature post-quantum-encryption {
    description
      "Support for post-quantum encryption.";
  }
  feature pqc {
    if-feature post-quantum-encryption;
    description
      "Support for Post-Quantum Cryptography (PQC).";
  }

  feature qkd {
    if-feature post-quantum-encryption;
    description
      "Support for Quantum Key Distribution (QKD).";
  }

  /* Identities */

  identity application-base {
    description
      "Base identity for application identification used in
       traffic classification.";
  }

  identity isolation-level-base {
    description
      "Base identity for isolation levels.  Definitions are
       aligned with the IETF network slice NBI YANG data
       model.";
  }

  identity isolation-dedicated {
    base isolation-level-base;
    description
      "Dedicated isolation: the service is not impacted by the
       existence of other customers or services in the same
       network.";
  }

  identity isolation-shared {
    base isolation-level-base;
    description
      "Shared (logical) isolation.";
  }

  identity failure-action-base {
    description
      "Base identity for actions executed when the validity
       conditions for post-quantum encryption are not met.";
  }

  identity failure-fallback-conventional {
    base failure-action-base;
    description
      "Fall back to conventional cryptography.";
  }
  identity failure-terminate {
    base failure-action-base;
    description
      "Terminate the encryption service.";
  }

  identity pm-status-base {
    description
      "Base identity for performance monitoring session
       operational status.";
  }

  identity pm-up {
    base pm-status-base;
    description
      "The monitoring session is operating normally.";
  }

  identity pm-degraded {
    base pm-status-base;
    description
      "The monitoring session is partially operating.";
  }

  identity pm-down {
    base pm-status-base;
    description
      "The monitoring session is not operating.";
  }

  identity pqc-status-base {
    description
      "Base identity for PQC encryption operational status.";
  }

  identity pqc-active {
    base pqc-status-base;
    description
      "PQC encryption is active.";
  }

  identity pqc-inactive {
    base pqc-status-base;
    description
      "PQC encryption is not active.";
  }

  identity pqc-error {
    base pqc-status-base;
    description
      "PQC encryption is in an error state.";
  }
  identity qkd-status-base {
    description
      "Base identity for QKD encryption operational status.";
  }

  identity qkd-active {
    base qkd-status-base;
    description
      "QKD encryption is active.";
  }

  identity qkd-inactive {
    base qkd-status-base;
    description
      "QKD encryption is not active.";
  }

  identity qkd-error {
    base qkd-status-base;
    description
      "QKD encryption is in an error state.";
  }

  /* Groupings */

  grouping classification-policy-grouping {
    description
      "A reusable, ordered set of traffic classification rules
       that generate 'class-id' values for cross-module reuse
       (e.g., by 'qos' and 'security').";
    list classification-policy {
      key "rule-id";
      description
        "List of classification rules.";
      leaf rule-id {
        type string;
        description
          "Unique identifier of the classification rule.";
      }
      choice match-type {
        description
          "Classification can be based on flow fields or on
           application identification.";
        case match-flow {
          description
            "Match on packet header fields.";
          leaf dscp {
            type inet:dscp;
            description
              "Match on the DSCP value.";
          }
          leaf dot1p {
            type uint8;
            description
              "Match on the IEEE 802.1 priority value.";
          }
          leaf protocol-field {
            type uint8;
            description
              "Match on the IP protocol field.";
          }
          leaf ipv4-src-prefix {
            type inet:ipv4-prefix;
            description
              "Match on the IPv4 source prefix.";
          }
          leaf ipv4-dst-prefix {
            type inet:ipv4-prefix;
            description
              "Match on the IPv4 destination prefix.";
          }
          leaf ipv6-src-prefix {
            type inet:ipv6-prefix;
            description
              "Match on the IPv6 source prefix.";
          }
          leaf ipv6-dst-prefix {
            type inet:ipv6-prefix;
            description
              "Match on the IPv6 destination prefix.";
          }
          leaf l4-src-port {
            type inet:port-number;
            description
              "Match on the Layer 4 source port.";
          }
          leaf l4-dst-port {
            type inet:port-number;
            description
              "Match on the Layer 4 destination port.";
          }
          container l4-src-port-range {
            description
              "Match on a Layer 4 source port range.";
            leaf lower-port {
              type inet:port-number;
              description
                "Lower boundary of the port range.";
            }
            leaf upper-port {
              type inet:port-number;
              description
                "Upper boundary of the port range.";
            }
          }
          container l4-dst-port-range {
            description
              "Match on a Layer 4 destination port range.";
            leaf lower-port {
              type inet:port-number;
              description
                "Lower boundary of the port range.";
            }
            leaf upper-port {
              type inet:port-number;
              description
                "Upper boundary of the port range.";
            }
          }
        }
        case match-application {
          description
            "Match on an identified application.";
          leaf match-application {
            type identityref {
              base application-base;
            }
            description
              "Identifies the application to match.";
          }
        }
      }
      leaf target-class-id {
        type string;
        description
          "The class identifier generated by this rule.  Other
           functional modules (e.g., 'qos', 'security')
           reference this value to handle the classified
           traffic.";
      }
    }
  }

  grouping time-schedule {
    description
      "A set of schedules expressed as period-based or
       iCalendar-recurrence time slots, together with the
       actual activation timestamps reported by the network.";
    list schedule {
      key "schedule-id";
      description
        "List of schedule entries.";
      leaf schedule-id {
        type string;
        description
          "Unique identifier of the schedule entry.";
      }
      choice schedule-type {
        description
          "The schedule can be a single period of time or a
           recurring schedule.";
        case period {
          description
            "A period-based schedule.";
          container period {
            description
              "A period-based schedule, as defined by the
               'period-of-time' grouping of [RFC9922].";
            uses schedule:period-of-time;
          }
        }
        case recurrence {
          description
            "A recurring schedule based on iCalendar
             recurrence rules.";
          container recurrence {
            description
              "A recurring schedule, as defined by the
               'icalendar-recurrence' grouping of
               [RFC9922].";
            uses schedule:icalendar-recurrence;
          }
        }
      }
      leaf actual-start-time {
        type yang:date-and-time;
        config false;
        description
          "Reports the actual date and time when the service
           was activated.  The offset against the requested
           start time represents the actual provisioning
           delay.";
      }
      leaf actual-stop-time {
        type yang:date-and-time;
        config false;
        description
          "Reports the actual date and time when the service
           was deactivated.";
      }
    }
  }

  /* Augmentations */

  augment "/l3nm:l3vpn-ntw/l3nm:vpn-profiles"
        + "/l3nm:valid-provider-identifiers" {
    description
      "Adds profile identifier lists for enhanced service
       features.";
    list bandwidth-adjustment-profile-identifier {
      key "id";
      description
        "List of bandwidth adjustment profile identifiers,
         e.g., the maximum allowed bandwidth after
         adjustment.";
      leaf id {
        type string;
        description
          "Identifier of the bandwidth adjustment profile.";
      }
    }
    list provisioning-delay-profile-identifier {
      key "id";
      description
        "List of provisioning-delay SLO profile identifiers.";
      leaf id {
        type string;
        description
          "Identifier of the provisioning-delay profile.";
      }
    }
    list perf-mon-profile-identifier {
      key "id";
      description
        "List of performance monitoring profile identifiers.";
      leaf id {
        type string;
        description
          "Identifier of the performance monitoring profile.";
      }
    }
  }

  augment "/l3nm:l3vpn-ntw/l3nm:vpn-services"
        + "/l3nm:vpn-service/l3nm:vpn-nodes/l3nm:vpn-node" {
    description
      "Adds node-level unified traffic classification and
       performance monitoring.";
    uses classification-policy-grouping {
      if-feature unified-classification;
    }
    container perf-mon {
      if-feature perf-mon;
      description
        "End-to-end performance monitoring from this VPN node
         towards selected target VPN nodes.";
      leaf enable {
        type boolean;
        default "false";
        description
          "Enables performance monitoring.";
      }
      container monitoring {
        description
          "Monitoring configuration and state.";
        list monitor {
          key "target-vpn-node-id";
          description
            "One monitoring session per target VPN node.
             For a spoke VPN node, only hub VPN nodes may be
             selected as targets; for hub or any-to-any
             topologies, all other VPN nodes of the same VPN
             service may be selected.";
          leaf target-vpn-node-id {
            type leafref {
              path "/l3nm:l3vpn-ntw/l3nm:vpn-services"
                 + "/l3nm:vpn-service/l3nm:vpn-nodes"
                 + "/l3nm:vpn-node/l3nm:vpn-node-id";
            }
            description
              "The target VPN node of the monitoring
               session.";
          }
          container measurement-profile {
            description
              "The measurement configuration.";
            choice profile-type {
              description
                "Standard (predefined) or custom
                 configuration.";
              case standard {
                description
                  "Reference to a pre-provisioned
                   performance monitoring profile.";
                leaf profile-id {
                  type leafref {
                    path "/l3nm:l3vpn-ntw/l3nm:vpn-profiles"
                       + "/l3nm:valid-provider-identifiers"
                       + "/l3nm-ext:perf-mon-profile"
                       + "-identifier/l3nm-ext:id";
                  }
                  description
                    "Reference to a performance monitoring
                     profile.";
                }
              }
              case custom {
                description
                  "Custom monitoring configuration.";
                leaf measurement-interval {
                  if-feature perf-mon-custom;
                  type uint32;
                  units "seconds";
                  description
                    "The performance measurement interval.";
                }
              }
            }
          }
          leaf status {
            type identityref {
              base pm-status-base;
            }
            config false;
            description
              "Operational status of the monitoring
               session.";
          }
          container metrics {
            config false;
            description
              "Service-level performance metrics for the
               monitoring session.";
            leaf one-way-min-delay {
              type yang:gauge64;
              units "microseconds";
              description
                "Minimum one-way delay.";
            }
            leaf one-way-max-delay {
              type yang:gauge64;
              units "microseconds";
              description
                "Maximum one-way delay.";
            }
            leaf one-way-delay-variation {
              type yang:gauge64;
              units "microseconds";
              description
                "One-way delay variation.";
            }
            leaf one-way-packet-loss {
              type decimal64 {
                fraction-digits 4;
              }
              description
                "One-way packet loss ratio.";
            }
            leaf two-way-min-delay {
              type yang:gauge64;
              units "microseconds";
              description
                "Minimum two-way delay.";
            }
            leaf two-way-max-delay {
              type yang:gauge64;
              units "microseconds";
              description
                "Maximum two-way delay.";
            }
            leaf two-way-delay-variation {
              type yang:gauge64;
              units "microseconds";
              description
                "Two-way delay variation.";
            }
            leaf two-way-packet-loss {
              type decimal64 {
                fraction-digits 4;
              }
              description
                "Two-way packet loss ratio.";
            }
          }
        }
      }
    }
  }

  augment "/l3nm:l3vpn-ntw/l3nm:vpn-services"
        + "/l3nm:vpn-service/l3nm:vpn-nodes/l3nm:vpn-node"
        + "/l3nm:vpn-network-accesses"
        + "/l3nm:vpn-network-access" {
    description
      "Adds access-level unified traffic classification.";
    uses classification-policy-grouping {
      if-feature unified-classification;
    }
  }

  augment "/l3nm:l3vpn-ntw/l3nm:vpn-services"
        + "/l3nm:vpn-service/l3nm:vpn-nodes/l3nm:vpn-node"
        + "/l3nm:vpn-network-accesses"
        + "/l3nm:vpn-network-access/l3nm:service" {
    description
      "Adds time-scheduled L3VPN service provisioning
       capabilities.";
    container time-scheduled-l3vpn {
      if-feature time-scheduled-l3vpn;
      description
        "Groups all parameters associated with time-scheduled
         service provisioning.";
      choice time-scheduled-type {
        description
          "The type of time-scheduled L3VPN service.  The
           types are mutually exclusive for a given VPN
           network access.";
        case time-scheduled-networking {
          description
            "Scheduled activation and deactivation of VPN
             connectivity.";
          leaf provisioning-delay-profile-id {
            if-feature time-scheduled-networking;
            type leafref {
              path "/l3nm:l3vpn-ntw/l3nm:vpn-profiles"
                 + "/l3nm:valid-provider-identifiers"
                 + "/l3nm-ext:provisioning-delay-profile"
                 + "-identifier/l3nm-ext:id";
            }
            description
              "Reference to a provisioning-delay SLO
               profile.  The SLO quantifies the allowed
               offset between the requested-start and
               actual-start timestamps of the VPN
               connection.";
          }
          container networking-schedule {
            description
              "The time slots during which the VPN
               connectivity shall be activated.";
            uses time-schedule;
          }
        }
        case time-scheduled-bandwidth-adjustment {
          description
            "Temporary bandwidth scaling on top of the
             baseline bandwidth.";
          leaf bandwidth-adjustment-profile-id {
            if-feature time-scheduled-bandwidth-adjustment;
            type leafref {
              path "/l3nm:l3vpn-ntw/l3nm:vpn-profiles"
                 + "/l3nm:valid-provider-identifiers"
                 + "/l3nm-ext:bandwidth-adjustment-profile"
                 + "-identifier/l3nm-ext:id";
            }
            description
              "Reference to a bandwidth adjustment profile,
               e.g., indicating the maximum allowed
               bandwidth after adjustment.";
          }
          leaf temporary-pe-to-ce-bandwidth {
            if-feature time-scheduled-bandwidth-adjustment;
            type uint64;
            units "bps";
            description
              "The desired temporary PE-to-CE bandwidth
               after adjustment.  This is an absolute value,
               not a delta offset from the baseline
               bandwidth.";
          }
          leaf temporary-ce-to-pe-bandwidth {
            if-feature time-scheduled-bandwidth-adjustment;
            type uint64;
            units "bps";
            description
              "The desired temporary CE-to-PE bandwidth
               after adjustment.  This is an absolute value,
               not a delta offset from the baseline
               bandwidth.";
          }
          container bandwidth-adjustment-schedule {
            description
              "The time slots during which the temporary
               bandwidth applies.";
            uses time-schedule;
          }
        }
      }
    }
  }

  augment "/l3nm:l3vpn-ntw/l3nm:vpn-services"
        + "/l3nm:vpn-service/l3nm:vpn-nodes/l3nm:vpn-node"
        + "/l3nm:vpn-network-accesses"
        + "/l3nm:vpn-network-access/l3nm:service"
        + "/l3nm:qos/l3nm:qos-action/l3nm:rule" {
    description
      "Adds isolation requirements and activation schedules
       to QoS action rules.";
    leaf-list isolation {
      if-feature qos-isolation;
      type identityref {
        base isolation-level-base;
      }
      description
        "Isolation requirements bound to the traffic class
         targeted by this QoS action rule, e.g., for
         delivery over IETF network slices.";
    }
    container qos-schedule {
      if-feature time-scheduled-l3vpn;
      description
        "The time slots during which this QoS action rule
         is active.  When no schedule is present, the rule
         is active immediately upon configuration commit.";
      uses time-schedule;
    }
  }

  augment "/l3nm:l3vpn-ntw/l3nm:vpn-services"
        + "/l3nm:vpn-service/l3nm:vpn-nodes/l3nm:vpn-node"
        + "/l3nm:vpn-network-accesses"
        + "/l3nm:vpn-network-access/l3nm:security" {
    description
      "Adds fine-grained per-class encryption including
       post-quantum options.";
    container classes {
      description
        "Per-class encryption policies.  Each class is keyed
         by a 'class-id' generated by a classification
         policy applied to this VPN network access or to the
         enclosing VPN node.";
      list class {
        key "class-id";
        description
          "Encryption policy for one traffic class.";
        leaf class-id {
          type string;
          description
            "Identifies the traffic class.  The value MUST
             correspond to a 'target-class-id' generated by
             a 'classification-policy'.";
        }
        leaf algorithm {
          type string;
          description
            "The encryption algorithm applied to this
             traffic class.";
        }
        choice key-type {
          description
            "The type of keying.";
          case psk {
            description
              "Use of a pre-shared key.";
            leaf pre-shared-key {
              type string;
              description
                "The pre-shared key.";
            }
          }
        }
        container post-quantum-encryption {
          if-feature post-quantum-encryption;
          description
            "Aggregates all configuration items associated
             with post-quantum encryption.";
          container post-quantum-policy {
            description
              "Availability and failover policy for
               post-quantum encryption.";
            leaf pqc-only-acceptable {
              type boolean;
              description
                "If true, post-quantum communication is
                 maintained when only PQC is available.
                 If false, execute the 'failure-action'.";
            }
            leaf qkd-only-acceptable {
              type boolean;
              description
                "If true, post-quantum communication is
                 maintained when only QKD is available.
                 If false, execute the 'failure-action'.";
            }
            leaf failure-action {
              type identityref {
                base failure-action-base;
              }
              description
                "The action executed when the validity
                 conditions for post-quantum encryption are
                 not met.";
            }
          }
          container pqc {
            if-feature pqc;
            description
              "Aggregates all items associated with PQC.";
            leaf enable {
              type boolean;
              default "false";
              description
                "Enables PQC.";
            }
            leaf algorithm {
              type string;
              description
                "The PQC algorithm.";
            }
            leaf pqc-status {
              type identityref {
                base pqc-status-base;
              }
              config false;
              description
                "Operational status of PQC encryption.";
            }
          }
          container qkd {
            if-feature qkd;
            description
              "Aggregates all items associated with QKD-based
               encryption.";
            leaf enable {
              type boolean;
              default "false";
              description
                "Enables QKD-based encryption.";
            }
            leaf qkd-status {
              type identityref {
                base qkd-status-base;
              }
              config false;
              description
                "Operational status of QKD encryption.";
            }
            leaf qkd-key-pool-id {
              type string;
              description
                "Identifier of a QKD key pool managed by the
                 QKD key management entity (KME).  Identical
                 values shall be configured on both endpoints
                 of any QKD link.";
            }
            leaf key-refresh-interval {
              type uint32;
              units "seconds";
              description
                "Time interval for automatic refresh of
                 quantum keys stored in the key pool.";
            }
          }
        }
      }
    }
  }
}
