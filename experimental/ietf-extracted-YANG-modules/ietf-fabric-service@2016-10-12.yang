module ietf-fabric-service {

    yang-version 1.1;
    namespace "urn:ietf:params:xml:ns:yang:ietf-fabric-service";
    prefix fabric-services;

    import ietf-network { prefix nw;  }
    import ietf-network-topology { prefix nt;  }
        import ietf-fabric-types { prefix fabrictype; revision-date "2016-10-13"; }

        import ietf-inet-types { prefix "inet"; revision-date "2013-07-15"; }
    //import yang-ext { prefix "ext"; revision-date "2013-07-09"; }
    import ietf-fabric-topology { prefix fabric; revision-date "2016-09-29"; }
    //import ietf-access-control-list { prefix acl; revision-date "2016-02-18"; }

    organization
    "IETF I2RS (Interface to the Routing System) Working Group";

        contact
   " WG Web:    <http://tools.ietf.org/wg/i2rs/ >
     WG List:   <mailto:i2rs@ietf.org>

     WG Chair:  Susan Hares
                <mailto:shares@ndzh.com>

     WG Chair:  Russ White
                <mailto:russ@riw.us>

     Editor:    Yan Zhuang
                <mailto:zhuangyan.zhuang@huawei.com>

     Editor:    Danian Shi
                <mailto:shidanian@huawei.com>";

    description
        "This module contains a collection of YANG definitions for Fabric services.
                Copyright (c) 2016 IETF Trust and the persons identified as
                authors of the code.  All rights reserved.

                Redistribution and use in source and binary forms, with or
                without modification, is permitted pursuant to, and subject
                to the license terms contained in, the Simplified BSD License
                set forth in Section 4.c of the IETF Trust's Legal Provisions
                Relating to IETF Documents
                (http://trustee.ietf.org/license-info).

                This version of this YANG module is part of
                draft-zhuang-i2rs-yang-fabric-services;
                see the RFC itself for full legal notices.";

    revision "2016-10-12" {
        description
            "Initial revision of fabric service.";
                reference
                        "draft-zhuang-i2rs-yang-fabric-service-00";
    }

    augment "/nw:networks/nw:network/nw:node" {
        description "Augmentation for logic switch nodes provided by fabrices.";

        container lsw-attribute {
            config false;
                        description "attributes for logical switches";
            uses fabrictype:logical-switch;
        }
    }

    augment "/nw:networks/nw:network/nw:node" {
        description "Augmentation for logical router nodes provided by fabric services.";

        container lr-attribute {
            config false;
                        description "attributes for logical routers";
            uses fabrictype:logical-router;
        }
    }

    augment "/nw:networks/nw:network/nw:node/nt:termination-point" {
        description "Augmentation for logical port provided by fabric services.";

        container lport-attribute {
                        config false;
                        description "attributes for logical ports";
            uses fabrictype:logical-port;
        }
    }

    /**************servic api*******************/
    rpc create-logical-switch {
                description "create a logical switch";
        input {
            leaf fabric-id {
                type fabric:fabric-id;
                                description "its belonged fabric id";
            }
            leaf name {
                type string;
                                description "lsw name";
            }
            leaf vni {
                type int32;
                                description "virtual network identifier.usually it is allocated by fabric itself. ";
            }
            leaf external {
                type boolean;
                default false;
                                description "whether it is connected to external network";
            }
        }
        output {
            leaf node-id {
                type nw:node-id;
                                description "node id";
            }
            uses fabrictype:logical-switch;
        }
    }

    rpc rm-logical-switch {
                description "remove a logical switch";
        input {
            leaf fabric-id {
                type fabric:fabric-id;
                                description "fabric id";
            }
            leaf node-id {
                type nw:node-id;
                                description "node id";
            }
        }
    }

    rpc create-logical-router {
                description "create a  logical router";
        input {
            leaf fabric-id {
                type fabric:fabric-id;
                                description "fabric id";
            }
            leaf name {
                type string;
                                description "name";
            }
        }
        output {
            leaf node-id {
                type nw:node-id;
                                description "node id";
            }
            uses fabrictype:logical-router;
        }
    }

    rpc rm-logical-router {
                description "remove a logical router";
        input {
            leaf fabric-id {
                type fabric:fabric-id;
                                description "fabric id";
            }
            leaf node-id {
                type nw:node-id;
                                description "node id";
            }
        }
    }

    rpc add-static-route {
                description "add static routes";
        input {
            leaf fabric-id {
                type fabric:fabric-id;
                                description "fabric id";
            }
            leaf node-id {
                type nw:node-id;
                                description "node id";
            }
            uses fabrictype:route-group;
        }
    }

    rpc rm-static-route {
                description "remove static route";
        input {
            leaf fabric-id {
                type fabric:fabric-id;
                                description "fabric id";
            }
            leaf node-id {
                type nw:node-id;
                                description "node id";
            }
            leaf-list destination-prefix {
                type inet:ipv4-prefix;
                                description "DA";
            }
        }
    }

    rpc clear-static-route {
                description "clear all static route on a node";
        input {
            leaf fabric-id {
                type fabric:fabric-id;
                                description "fabric id";
            }
            leaf node-id {
                type nw:node-id;
                                description "node id";
            }
        }
    }

    rpc create-logical-port {
                description "create a logical port";
        input {
            leaf fabric-id {
                type fabric:fabric-id;
                                description "fabric id";
            }
            leaf name {
                type string;
                                description "name";
            }
            leaf logical-device {
                type nw:node-id;
                                description "node id";
            }
            container attribute {
                                description "logical port attributes";
                uses fabrictype:logical-port;
            }
        }
        output {
            leaf tp-id {
                type nt:tp-id;
                                description "tp id";
            }
            uses fabrictype:logical-port;
        }
    }

    rpc rm-logical-port {
                description "remove a logical port";
        input {
            leaf fabric-id {
                type fabric:fabric-id;
                                description "fabric id";
            }
            leaf logical-device {
                type nw:node-id;
                                description "node id";
            }
            leaf tp-id {
                type nt:tp-id;
                                description "tp id";
            }
        }
    }

    rpc create-gateway {
                description "create a gateway";
        input {
            leaf fabric-id {
                type fabric:fabric-id;
                                description "fabric id";
            }
            leaf ip-address {
                type inet:ip-address;
                                description "ip addr";
            }
            leaf network {
                type inet:ip-prefix;
                                description "ip prefix";
            }
            leaf logical-router {
                type nw:node-id;
                                description "lr id";
            }
            leaf logical-switch {
                type nw:node-id;
                                description "lsw id";
            }
        }
        output {
            leaf tp-id {
                type nt:tp-id;
                                description "port id";
            }
            uses fabrictype:logical-port;
        }
    }

    rpc rm-gateway {
                description "remove gateway";
        input {
            leaf fabric-id {
                type fabric:fabric-id;
                                description "fabric id";
            }
            leaf ip-address {
                type inet:ip-address;
                                description "ip addr";
            }
            leaf logical-router {
                type nw:node-id;
                                description "lr id";
            }
        }
    }

    rpc port-binding-logical-to-fabric {
                description "binding logical device to a fabric";
        input {
            leaf fabric-id {
                type fabric:fabric-id;
                                description "fabric id";
            }
            leaf logical-device {
                type nw:node-id;
                                description "node id";
            }
            leaf logical-port {
                type nt:tp-id;
                                description "port id";
            }
            leaf fabric-port {
                type nt:tp-id;
                                description "port id";
            }
        }
    }

    rpc port-binding-logical-to-device {
                description "binding a logical port on a logical device to a physical device and port";
        input {
            leaf fabric-id {
                type fabric:fabric-id;
                                description "fabric id";
            }
            leaf logical-device {
                type nw:node-id;
                                description "node id";
            }
            leaf logical-port {
                type nt:tp-id;
                                description "logical port id";
            }
            leaf physical-port {
                type fabrictype:tp-ref;
                                description "physical port ref";
            }
        }
    }

    rpc add-port-function {
                description "add port function to a port";
        input {
            leaf fabric-id {
                type fabric:fabric-id;
                                description "fabric id";
            }
            leaf logical-device {
                type nw:node-id;
                                description "node id";
            }
            leaf logical-port {
                type nt:tp-id;
                                description "logical port id";
            }
            uses fabrictype:port-functions;
        }
    }

    rpc add-acl {
                description "add acl";
        input {
            leaf fabric-id {
                type fabric:fabric-id;
                                description "fabric id";
            }
            leaf logical-device {
                type nw:node-id;
                                description "logical device id";
            }
            leaf logical-port {
                type nt:tp-id;
                                description "logical port id";
            }
            leaf acl-name {
                type string;
                                description "acl name";
            }
        }
    }

    rpc del-acl {
                description "delete acl";
        input {
            leaf fabric-id {
                type fabric:fabric-id;
                                description "fabric id";
            }
            leaf logical-device {
                type nw:node-id;
                                description "logical device id";
            }
            leaf logical-port {
                type nt:tp-id;
                                description "logical port id";
            }
            leaf acl-name {
                type string;
                                description "acl name";
            }
        }
    }
}
