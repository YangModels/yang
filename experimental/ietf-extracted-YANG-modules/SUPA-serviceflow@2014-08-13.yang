module SUPA-serviceflow {
  namespace "urn:TBD:params:xml:ns:yang:serviceflow";
        // replace with IANA namespace when assigned
  prefix "nc";
    import ietf-inet-types { prefix inet;}
  organization "TBD";
  contact "WILL-BE-DEFINED-LATER";
  description "This module defines a model for service flow";
  revision "2014-08-13";

  container flows {

    list flow {

      key flowName;
      max-elements "unbounded";
      min-elements "0";
      description "Flow";

      leaf flowName {
        description "Flow Name";
        config "true";
        type string {
          length "0..31";
        }
      }
      list flowFilter {
                                key flowFilterID;
        max-elements "unbounded";
        min-elements "0";
        description "Flow Filter";

        leaf flowFilterID {
        description "Flow Filter";
        config "true";
        type string {
          length "0..64";
        }
      }

        leaf sourceIP {
          description "source IP";
          config "true";
          default "0.0.0.0";
          type inet:ipv4-address;
                }
        leaf destinationIP {
          description "destination IP";
          config "true";
          default "0.0.0.0";
          type inet:ipv4-address;
        }
        leaf sourcePrefix {
          description "source Prefix";
          config "true";
          default "0.0.0.0";
          type inet:ipv4-address;
        }
        leaf destinationPrefix {
          description "destination Prefix";
          config "true";
          default "0.0.0.0";
          type inet:ipv4-address;
        }
        leaf prefix {
          description "Prefix";
          config "true";
          default "0.0.0.0";
          type inet:ipv4-address;
        }
        leaf sourcePort {
          description "Source Port";
          config "true";
          type inet:port-number{
          range "0..65535";
                }
        }
        leaf destinationPort {
          description "Destination Port";
          config "true";
          type inet:port-number{
                        range "0..65535";
                        }
        }
        leaf inIf {
          description "In Intreface Name";
          config "true";
          type string {
          length "0..64";
        }
        }
        leaf outIf {
          description "Out Interface Name";
          config "true";
          type string {
          length "0..64";
        }
        }
        leaf protocolId {
          description "Protocol ID";
          config "true";
          type string {
          length "0..64";
        }
      }

    }

  }

  container flowPolicies {

    list flowPolicy {

      key "policyName";
      max-elements "unbounded";
      min-elements "0";
      description "Flow Policy";

      leaf policyName {
        description "Policy Name";
        config "true";
        type string {
          length "0..64";
        }
      }
      leaf flowName {
        description "Flow Name";
        config "true";
        type string {
          length "0..64";
        }
      }
      leaf nodeKeyType {
        description "Node Key Type";
        config "true";
        default "lsr-id";
        type enumeration {
          enum lsr-id {
            value "0";
            description "lsr-id:";
          }
          enum invalid {
            value "1";
            description "invalid:";
          }
          enum system-id {
            value "2";
            description "system-id:";
          }
          enum router-id {
            value "3";
            description "router-id:";
          }
          enum fp-id {
            value "4";
            description "fp-id:";
          }
          enum mac {
            value "5";
            description "mac:";
          }
        }
      }
      leaf nodeId {
        description "Node Id";
        config "true";
        default "_leftNode_";
        type string {
          length "0..64";
        }
      }
      leaf tpType {
        description "Terminal Point Key";
        config "true";
        default "ip";
        type enumeration {
          enum ip {
            value "0";
            description "ip:";
          }
          enum invalid {
            value "1";
            description "invalid:";
          }
          enum interface {
            value "2";
            description "interface:";
          }
        }
      }
      leaf tpId {
        description "Terminal Point Id";
        config "true";
        default "_Tp_";
        type string {
          length "0..64";
        }
      }
    }

  }
}
}
