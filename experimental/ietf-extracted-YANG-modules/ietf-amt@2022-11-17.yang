module ietf-amt {
  yang-version "1.1";
  namespace "urn:ietf:params:xml:ns:yang:ietf-amt";
  prefix amt;

  import ietf-inet-types {
    prefix inet;
    reference
      "RFC 6991: Common YANG Data Types";
  }

  import ietf-yang-types {
    prefix yang;
    reference
      "RFC 6991: Common YANG Data Types";
  }

  import ietf-routing-types {
    prefix rt-types;
    reference
      "RFC 8294: Common YANG Data Types for the Routing Area";
  }

  import ietf-interfaces {
    prefix if;
    reference
      "RFC 8343: A YANG Data Model for Interface Management";
  }

  import ietf-routing {
    prefix rt;
    reference
      "RFC 8349: A YANG Data Model for Routing Management
                 (NMDA Version)";
  }
  organization
    "IETF Multicast Backbone Deployment (MBONED) Working Group";

  contact
    "WG Web:   <https://datatracker.ietf.org/wg/mboned/>
     WG List:  <mailto:mboned@ietf.org>

     Editor:   Yisong Liu
               <mailto:liuyisong@chinamobile.com>
     Editor:   Changwang Lin
               <mailto:linchangwang.04414@h3c.com>
     Editor:   Zheng(Sandy) Zhang
               <mailto:zhang.zheng@zte.com.cn>
     Editor:   Xuesong Geng
               <mailto:gengxuesong@huawei.com>
     Editor:   Vinod Kumar Nagaraj
               <mailto:vinkumar@juniper.net>";

  description
    "This module describes a YANG model for configuring and
     managing the AMT Protocol.

     This YANG model conforms to the Network Management
     Datastore Architecture (NMDA) as described in RFC 8342.

     Copyright (c) 2022 IETF Trust and the persons identified as
     authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see the
     RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  revision 2022-11-17 {
    description
      "Initial Version";
    reference
      "RFC XXXX: YANG Data Model for Automatic Multicast Tunneling";
  }

  identity address-family {
    description
      "Base identity from which identities describing address
       families are derived.";
  }

  identity ipv4 {
    base address-family;
    description
      "This identity represents an IPv4 address family.";
  }

  identity ipv6 {
    base address-family;
    description
      "This identity represents an IPv6 address family.";
  }

  typedef ip-multicast-source-address {
    type union {
      type rt-types:ipv4-multicast-source-address;
      type rt-types:ipv6-multicast-source-address;
    }
    description
      "This type represents a version-neutral IP multicast source
       address. The format of the textual representation implies
       the IP version.";
  }

  augment "/rt:routing/rt:control-plane-protocols" {
    description
      "AMT augmentation to the routing instance model.";
    container amt {
      description
        "Configuration parameters for the AMT protocol.";
      container relay {
        description
          "Parameters of AMT relay service.";
        container relay-addresses {
          description
            "Parameters of AMT relay addresses.";
          list relay-address {
            key "family";
            description
              "Each entry contains parameters for an AMT relay
               address identified by the 'family' key.";
            leaf family {
              type identityref {
                base address-family;
              }
              mandatory true;
              description
                "Address family.";
            }
            leaf anycast-prefix {
              type inet:ip-prefix;
              description
                "The anycast IP prefix of AMT relay discovery
                 address which is used when sending discovery
                 messages to a relay.";
            }
            leaf local-address {
              type inet:ip-address;
              description
                "The unicast IP address of AMT relay address
                 which is obtained as a result of the discovery
                 process.";
            }
          }
        }
        leaf tunnel-limit {
          type uint32;
          description
            "The total number of endpoints";
        }
        leaf secret-key-timeout {
          type uint32;
          description
            "The timeout interval of secret key.";
        }
        container tunnels {
          config false;
          description
            "The AMT tunnel information on the relay.";
          list tunnel {
            key "gateway-address gateway-port";
            description
              "An entry of AMT tunnel.";
            leaf gateway-address {
              type inet:ip-address;
              description
                "The IP address of AMT gateway.";
            }
            leaf gateway-port {
              type inet:port-number;
              description
                "The UDP port of AMT gateway.";
            }
            leaf local-address {
              type inet:ip-address;
              description
                "The local IP address of AMT relay.";
            }
            leaf local-port {
              type inet:port-number;
              description
                "The local UDP port of AMT relay.";
            }
            leaf state {
              type enumeration {
                enum up {
                  description
                    "The AMT tunnel has been successfully
                     established.";
                }
                enum establishing {
                  description
                    "The AMT tunnel is being established.";
                }
              }
              description
                "The state of AMT tunnel.";
            }
            container multicast-flows {
              config false;
              description
                "The multicast flow information in the AMT tunnel.";
              list multicast-flow {
                key "source-address group-address";
                description
                  "An entry of multicast flow.";
                leaf source-address {
                  type ip-multicast-source-address;
                  description
                    "The source IP address of multicast flow.";
                }
                leaf group-address {
                  type rt-types:ip-multicast-group-address;
                  description
                    "The group address of multicast flow.";
                }
              }
            }
            leaf multicast-group-num {
              type yang:gauge32;
              description
                "Number of multicast groups.";
            }
            leaf request-message-count {
              type yang:zero-based-counter64;
              description
                "Number of AMT request messages received
                 in the tunnel.";
            }
            leaf membership-query-message-count {
              type yang:zero-based-counter64;
              description
                "Number of AMT membership query messages sent
                 in the tunnel.";
            }
            leaf membership-update-message-count {
              type yang:zero-based-counter64;
              description
                "Number of AMT membership update messages received
                 in the tunnel.";
            }
          }
        }
        container relay-dns-resource-records {
          description
            "The DNS resource records of AMT relay.";
          list relay-dns-resource-record {
            key "source-address";
            description
              "An entry of AMT relay resource record.";
            leaf source-address {
              type inet:ip-address;
              description
                "The IP address of multicast sender.";
            }
            leaf precedence {
              type uint32;
              description
                "The precedence of this record.";
            }
            leaf d-flag {
              type boolean;
              default false;
              description
                "If the D-bit is set to true, the gateway MAY
                 send an AMT Request message directly to the
                 discovered relay address without first
                 sending an AMT Discovery message.
                 If the D-bit is set to false, the gateway MUST
                 receive an AMT relay advertisement message
                 for an address before sending an AMT
                 Request message to that address.";
            }
            leaf relay-type {
              type enumeration {
                enum empty {
                  value 0;
                  description
                    "The relay field is empty.";
                }
                enum ipv4-address {
                  value 1;
                  description
                    "The relay field contains a 4-octet IPv4
                     address.";
                }
                enum ipv6-address {
                  value 2;
                  description
                    "The relay field contains a 16-octet IPv6
                     address.";
                }
                enum domain-name {
                  value 3;
                  description
                    "The relay field contains a wire-encoded
                     domain name.";
                }
              }
              description
                "The type of Relay address.";
            }
            leaf discovery-address {
              type inet:ip-address;
              description
                "The IP address of AMT relay discovery address.";
            }
            leaf domain-name {
              type inet:domain-name;
              description
                "The wire-encoded domain name of AMT relay.";
            }
          }
        }
        container relay-message-statistics {
          config false;
          description
            "Message statistics of AMT relay.";
          container received {
            description
              "Received message statistics of AMT relay.";
            leaf relay-discovery {
              type yang:zero-based-counter64;
              description
                "Number of AMT relay discovery messages
                 received.";
            }
            leaf request {
              type yang:zero-based-counter64;
              description
                "Number of AMT membership request messages
                 received.";
            }
            leaf membership-update {
              type yang:zero-based-counter64;
              description
                "Number of AMT membership update messages
                 received.";
            }
            leaf teardown {
              type yang:zero-based-counter64;
              description
                "Number of AMT teardown messages received.";
            }
          }
          container sent {
            description
              "Sent message statistics of AMT relay.";
            leaf relay-advertisement {
              type yang:zero-based-counter64;
              description
                "Number of AMT relay advertisement messages sent.";
            }
            leaf membership-query {
              type yang:zero-based-counter64;
              description
                "Number of AMT membership query messages sent.";
            }
          }
          container error {
            description
              "Error message statistics of AMT relay.";
            leaf incomplete-packet {
              type yang:zero-based-counter64;
              description
                "Number of messages received with length errors
                 so severe that further classification could not
                 occur.";
            }
            leaf invalid-mac {
              type yang:zero-based-counter64;
              description
                "Number of messages received with an invalid
                 message authentication code (MAC).";
            }
            leaf unexpected-type {
              type yang:zero-based-counter64;
              description
                "Number of messages received with an unknown
                 message type specified.";
            }
            leaf invalid-relay-discovery-address {
              type yang:zero-based-counter64;
              description
                "Number of AMT relay discovery messages
                 received with an address other than the
                 configured anycast address.";
            }
            leaf invalid-membership-request-address {
              type yang:zero-based-counter64;
              description
                "Number of AMT membership request messages
                 received with an address other than the
                 configured AMT local address.";
            }
            leaf invalid-membership-update-address {
              type yang:zero-based-counter64;
              description
                "Number of AMT membership update messages
                 received with an address other than the
                 configured AMT local address.";
            }
            leaf incomplete-relay-discovery-messages {
              type yang:zero-based-counter64;
              description
                "Number of AMT relay discovery messages
                 received that are not fully formed.";
            }
            leaf incomplete-membership-request-messages {
              type yang:zero-based-counter64;
              description
                "Number of AMT membership request messages
                 received that are not fully formed.";
            }
            leaf incomplete-membership-update-messages {
              type yang:zero-based-counter64;
              description
                "Number of AMT membership update messages
                 received that are not fully formed.";
            }
            leaf no-active-gateway {
              type yang:zero-based-counter64;
              description
                "Number of AMT membership update messages
                 received for a tunnel that does not exist
                 for the gateway that sent the message.";
            }
            leaf invalid-inner-header-checksum {
              type yang:zero-based-counter64;
              description
                "Number of AMT membership update messages
                 received with an invalid IP checksum.";
            }
            leaf gateways-timed-out {
              type yang:gauge64;
              description
                "Number of gateways that timed out because
                 of inactivity.";
            }
          }
        }
      } // relay
      container gateway {
        description
          "Parameters of AMT gateway service.";
        container pseudo-interfaces {
          description
            "Parameters of AMT pseudo-interface.";
          list pseudo-interface {
            key "interface";
            description
              "An entry of AMT pseudo-interface.";
            leaf interface {
              type if:interface-ref;
              description
                "Pseudo interface.";
            }
            leaf discovery-method {
              type enumeration {
                enum by-amt-solicit {
                  description
                    "Find the relay address by sending an AMT
                     Discovery message.";
                }
                enum by-dns-reverse-ip {
                  description
                    "Find the relay address by DNS reverse IP
                     AMT Discovery.";
                }
              }
              description
                "The method used to discover the relay address.";
            }
            leaf relay-discovery-address {
              type inet:ip-address;
              description
                "IP address of the AMT relay discovery address.";
            }
            leaf relay-address {
              type inet:ip-address;
              description
                "IP address of the AMT relay address.";
            }
            leaf upstream-interface {
              type if:interface-ref;
              description
                "Upstream interface.";
            }
            leaf discovery-timeout {
              type uint32;
              description
                "Initial time to wait for a response to
                 a Relay Discovery message.";
            }
            leaf discovery-retrans-count {
              type uint32;
              description
                "Maximum number of Relay Discovery retransmissions
                 to allow before terminating relay discovery
                 and reporting an error.";
            }
            leaf request-timeout {
              type uint32;
              description
                "Initial time to wait for a response
                 to a Request message";
            }
            leaf request-retrans-count {
              type uint32;
              description
                "Maximum number of Request retransmissions
                 to allow before abandoning a relay and restarting
                 relay discovery or reporting an error.";
            }
            leaf dest-unreach-retry-count {
              type uint32;
              description
                "The maximum number of times a gateway should
                 attempt to send the same Request or Membership
                 Update message after receiving an ICMP Destination
                 Unreachable message.";
            }
            leaf relay-port {
              type inet:port-number;
              description
                "The UDP port of AMT relay.";
            }
            leaf local-address {
              type inet:ip-address;
              config false;
              description
                "The local IP address of this AMT tunnel.";
            }
            leaf local-port {
              type inet:port-number;
              config false;
              description
                "The local UDP port of this AMT tunnel.";
            }
            leaf tunnel-state {
              type enumeration {
                enum initial {
                  description
                    "Initial state.";
                }
                enum discoverying {
                  description
                    "The Relay Discovery message has been sent
                     and is waiting for the Advertisement message.";
                }
                enum requesting {
                  description
                    "The Request message has been sent,
                     waiting for the Query message.";
                }
                enum up {
                  description
                    "The AMT tunnel is Established.";
                }
              }
              config false;
              description
                "The tunnel's state.";
            }
            leaf relay-discovery-message-count {
              type yang:zero-based-counter64;
              config false;
              description
                "Number of AMT relay discovery messages sent
                 on the interface.";
            }
            leaf relay-advertisement-message-count {
              type yang:zero-based-counter64;
              config false;
              description
                "Number of AMT relay advertisement messages received
                 on the interface.";
            }
            leaf request-message-count {
              type yang:zero-based-counter64;
              config false;
              description
                "Number of AMT membership request messages sent
                 on the interface.";
            }
            leaf membership-query-message-count {
              type yang:zero-based-counter64;
              config false;
              description
                "Number of AMT membership query messages received
                 on the interface.";
            }
            leaf membership-update-message-count {
              type yang:zero-based-counter64;
              config false;
              description
                "Number of AMT membership update messages sent
                 on the interface.";
            }
          }
        }
        container gateway-message-statistics {
          config false;
          description
            "Message statistics of AMT Gateway.";
          container received {
            description
              "Received message statistics of AMT Gateway.";
            leaf relay-advertisement {
              type yang:zero-based-counter64;
              description
                "Number of AMT relay advertisement messages
                 received.";
            }
            leaf membership-query {
              type yang:zero-based-counter64;
              description
                "Number of AMT membership query messages
                 received.";
            }
          }
          container sent {
            description
              "Sent message statistics of AMT Gateway.";
            leaf relay-discovery {
              type yang:zero-based-counter64;
              description
                "Number of AMT relay discovery messages sent.";
            }
            leaf request {
              type yang:zero-based-counter64;
              description
                "Number of AMT membership request messages sent.";
            }
            leaf membership-update {
              type yang:zero-based-counter64;
              description
                "Number of AMT membership update messages sent.";
            }
            leaf teardown {
              type yang:zero-based-counter64;
              description
                "Number of AMT teardown messages sent.";
            }
          }
        }
      } // gateway
    } // amt
  } // augment
}
