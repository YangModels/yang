module ietf-nvo-vpn-routeprotocol {
    namespace "urn:ietf:params:xml:ns:yang:ietf-nvo-vpn-routeprotocol";
    prefix RouteProtocol;
    import ietf-yang-types { prefix yang; }
    import ietf-nvo-common-types {
        prefix  CommonTypes;
    }

    organization "";
    contact "";
    description "ietf-nvo-vpn-routeprotocol";
    revision 2016-10-24 {
        reference "draft-chen-opsawg-composite-vpn-dm-00";
    }

    grouping RouteProtocolSpec {
        description "RouteProtocolSpec Grouping.";

        leaf type {
            type CommonTypes:RouteProtocolType;
            description "Protocol type" ;
        }
        choice para {
            description "para" ;
            case staticRouting {
                list staticRouteItems {
                    key "index";
                    uses RouteProtocol:StaticRouteItem;
                    description "staticRouteItems" ;
                }
            }
            case bgp {
                    list bgpProtocols {
                            key "index";
                            uses RouteProtocol:BGPProtocolItem;
                            description "bgpProtocols" ;
                    }

            }
        }
    }

    grouping StaticRouteItem {
        description "StaticRouteItem Grouping.";

        leaf index {
            type uint32;
            description "static item index";
        }
        leaf destinationCidr {
            type string;
            description "destination ip cidr. ";
        }
        leaf egressTP {
            type yang:uuid;
            description "egress tp";
        }
        leaf routePreference {
            type string;
            description "route priority. Ordinary, work route have
            higher priority.";
        }
        leaf nextHopIp {
            type string {length "0..200";}
            description "nextHopIp";
        }
    }

    grouping BGPProtocolItem {
        description "BGPProtocolItem Grouping.";

        leaf index {
            type uint32;
            description "index of BGP protocol item";
        }
        leaf peerAsNumber {
            type uint64;
            description "";
        }
        leaf bgpMaxPrefix {
            type int32;
            description "";
        }
        leaf bgpMaxPrefixAlarm {
            type uint32;
            description "alarm threshold of BGP rout";
        }
        leaf peerIp {
            type string;
            description "peerIp";
        }
    }
}
