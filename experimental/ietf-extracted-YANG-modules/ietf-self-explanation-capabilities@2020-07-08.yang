module ietf-self-explanation-capabilities {
  yang-version 1.1;
  namespace urn:ietf:params:xml:ns:yang:ietf-self-explanation-capabilities;
  prefix sec;
  import ietf-system-capabilities  { prefix sysc ; }
  import ietf-module-tags  { prefix tags; }
  organization
    "IETF NETMOD (Network Modeling) Working Group";
  contact
    "WG Web:   <https://tools.ietf.org/wg/netconf/>
     WG List:  <mailto:netconf@ietf.org>

     Editor:   Qin Wu
               <mailto:bill.wu@huawei.com>
               Bo Wu
               <mailto:lana.wubo@huawei.com";
  description
    "This module defines an extension to System Capabilities model
     and provides additional self explaination data node tag attributes
     associated with node selector for queries filtering.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";
         revision 2020-07-08 {
    description
      "Initial revision";
    reference
      "RFC XXXX";
  }
    augment "/sysc:system-capabilities/sysc:datastore-capabilities" +
         "/sysc:per-node-capabilities" +
          "/sysc:node-selection/sysc:node-selector" {
     description "Allows per-node capabilities have additional self-explanation attributes";
     list self-describing-attributes {
      key self-tag-id;
      description "self describing attributes for each data node.";
       leaf self-tag-id {
         type string;
         description
          "This self tag id is used to uniquely identify a set of data nodes
          of the same group which have a common characteristic. If the opm-tag
          is metric, self-tag-id represents specific metric name. If the opm-tag
          is metric-group, self-tag-id represents specific metric group name.";
       }
         leaf opm-tag {
           type tags:tag ;
           description
            "Object, Property and Metric(OPM) Tags associated with
            the data node within YANG module.
            See the IANA 'YANG Data Node Tag Prefixes' registry
            for reserved prefixes and the IANA
            'IETF YANG Data Node Tags' registry for IETF tags.";
       }
         leaf metric-precision {
           type tags:tag;
           description
             "The numeric expression precision of performance
              metric related data node.";
         }

        leaf metric-scale {
            type tags:tag;
            description
             "The measurement scale of performance
              metric related data node.";
         }
         leaf operation-type{
          type tags:tag;
          description
           "Statistics operation of performance metric related
           data node.If the operation type is threshold type, the corresponding
           data object support threshold handling,e.g.,scan all interfaces
            for a certain type every 5 seconds and check the counters or
           status to cross threshold, return an array of interface entries
           that match the search.If the operation type is average,min,max, sum,
           it indicate the data object supports statistics operation, e.g.,
           scan all interfaces for a certain type every 5 seconds up to 60 seconds,
           only return min, average, max, sum value of specific data object rather than
           the values that are current at the end of 60 seconds.";
         }
         leaf-list service-tag {
          type tags:tag;
          description
           "The node-service-tag can be used to provide a service
           classification information (e.g., tunnel, l3vpn,l2vpn)
           information associated with YANG data node.";
         }
         leaf-list task-tag {
          type tags:tag;
          description
           "The node-task-tag can be used to provide a task
           classification information (e.g., fault management,
           performance measurement) information associated with
           YANG data node.";
         }
         leaf data-source {
          type tags:tag;
          description
           "The data source type can be used to identify different
            data source type(e.g., service flow, resource, policy,
            qos, hardware).";
         }
         leaf multi-source-tag {
          type tags:tag;
          description
           "The multiple source tag can be used to aggregate peformance
            metric from different sources.";
         }
     }
   }
}
