module ietf-dhcpv6 {
    namespace "urn:ietf:params:xml:ns:yang:dhcpv6";
    prefix "dhcpv6";

    import ietf-inet-types { prefix inet; revision-date "2013-07-15"; }
    import ietf-yang-types { prefix yang; revision-date "2013-07-15"; }

    organization "dhc wg";
    contact "yong@csnet1.cs.tsinghua.edu.cn
             wangh13@mails.tsinghua.edu.cn
             lh.sunlinh@gmail.com
             ";

    description "This model defines a YANG data model that can be used to configure
        and manage DHCPv6 server, DHCPv6 relay and DHCPv6 client.";

    revision 2015-03-24 {
        description "Version01: Correct grammar errors, Reuse groupings, Update
            "dhcpv6-realy" feature, Add notifications.;
    }

    revision 2015-03-04 {
        description "Version00: Initial revision.";
    }

/*
 * Features
 */

    feature dhcpv6-server {
      description
        "Server in DHCPv6.";
      reference
        "RFC3315";
    }

    feature dhcpv6-relay {
      description
        "Relay agent in DHCPv6.";
      reference
        "RFC3315";
    }

    feature dhcpv6-client {
      description
        "Client in DHCPv6.";
      reference
        "RFC3315";
    }

/*
 * Grouping
 */

    grouping vendor-info {
        container vendorinfo {
            config "false";
            leaf entnum {
                type uint8;
            }
            leaf-list data {
                type string;
            }
        }
    }

/*
 * Data Nodes
 */

    container server {
        if-feature dhcpv6-server;
        container servattributes {
            description "This container contains basic attributes of a DHCPv6 server
                such as DUID, server name and so on. Some optional functions that
                can be provided by the server is also included.";
            leaf name {
                type string;
            }
            leaf duid {
                config false;
                description "Each server and client has only one DUID (DHCP Unique Identifier).
                    The DUID here identifies a unique DHCPv6 server for clients.";
                type uint32;
            }
            leaf enable {
                type boolean;
            }
            leaf description {
                type string;
            }
            leaf pd-function {
                description "Whether the server can act as a delegating router to perform
                    prefix delegation ([RFC3633]).";
                type boolean;
            }
            leaf two-step-interaction {
                description "A boolean value specifies whether the server support client-server
                    exchanges involving two messages defined in ([RFC3315]).";
                type boolean;
            }
            leaf rapidcommit {
                description "A boolean value specifies whether the server support client-server
                    exchanges involving two messages defined in ([RFC3315]).";
                type boolean;
            }
            uses vendor-info;
        }
        container address-pools {
            description "A container describes the DHCPv6 server's address pools.";
            list address-pool {
                description "A DHCPv6 server can be configured with several address pools.
                    This list defines such address pools which are distinguish by
                    the key called 'pool-name'.";
                key pool-name;
                leaf pool-name {
                    type string;
                }
                leaf pool-prefix {
                    type inet:ipv6-prefix;
                }
                leaf start-address {
                    type inet:ipv6-address-no-zone;
                }
                leaf end-address {
                    type inet:ipv6-address-no-zone;
                }
                leaf preferred-lifetime {
                    type yang:timeticks;
                }
                leaf valid-lifetime {
                    type yang:timeticks;
                }
                leaf used-ipv6-count {
                    config "false";
                    type uint32;
                }
                leaf idle-ipv6-count {
                    config "false";
                    type uint32;
                }
            }
            list bindinginfo {
                config "false";
                description "A list records a binding information for each DHCPv6 client that
                    has already been allocated IPv6 addresses.";
                key cliduid;
                leaf cliduid {
                    type uint32;
                }
                list cliia {
                    key iaid;
                    leaf iaid {
                        type uint8;
                    }
                    leaf iatype {
                        type string;
                    }
                    leaf-list cliaddr {
                        type inet:ipv6-address;
                    }
                    leaf pool-name {
                        type string;
                    }
                }
            }
        }
        container prefix-pools {
            description "If a server supports prefix delegation function, this container
                will be used to define the delegating router's refix pools.";
            list prefix-pool {
                description "Similar to server's address pools, a delegating router can also
                    be configured with multiple prefix pools specified by a list called
                    'prefix-pool'.";
                key pool-name;
                leaf pool-name {
                    description "";
                    type string;
                }
                leaf  prefix {
                    description "";
                    type inet:ipv6-prefix;
                }
                leaf prefix-length {
                    description "";
                    type uint8;
                }
                leaf preferred-lifetime {
                    description "";
                    type yang:timeticks;
                }
                leaf valid-lifetime {
                    description "";
                    type yang:timeticks;
                }
            }
            list bindinginfo {
                config "false";
                description "A list records a binding information for each DHCPv6 client that
                    has already been allocated IPv6 addresses.";
                key cliduid;
                leaf cliduid {
                    type uint32;
                }
                list cliiapd {
                    key iaid;
                    leaf iaid {
                        type uint8;
                    }
                    leaf-list cliprefix {
                        type inet:ipv6-prefix;
                    }
                    leaf-list cliprefixlen {
                        type uint8;
                    }
                    leaf pool-name {
                        type string;
                    }
                }
            }
        }
        container otherparas {
            description "This container defines extra configuration parameters provided
                by the DHCPv6 server apart from the address and prefix information.
                Such parameters may include DNS servers, SIP servers, SNTP servers,
                etc.";
            list dnsserver {
                key dnsname;
                leaf dnsname {
                    type string;
                }
                leaf dnsservaddr {
                    type inet:ipv6-address;
                }
            }
            leaf domainsearchlist {
                type string;
            }
            list sipserver {
                key sipservdomainname;
                leaf sipserverdomainname {
                    type string;
                }
                leaf sipservaddr {
                    type inet:ipv6-address;
                }
            }
            list sntpserver {
                key sntpservname;
                leaf sntpservname {
                    type string;
                }
                leaf sntpservaddr {
                    type inet:ipv6-address;
                }
            }
            list ntpservparas {
                key ntpname;
                leaf ntpname {
                    type string;
                }
                leaf ntpservaddr {
                    type inet:ipv6-address;
                }
                leaf ntpservmuladdr {
                    type inet:ipv6-address;
                }
                leaf ntpservfqdn {
                    type string;
                }
            }
            container nisparas {
                leaf nisservaddr {
                    type inet:ipv6-address;
                }
                list niscli {
                    key cliduid;
                    leaf cliduid {
                        type uint32;
                    }
                    leaf clidomainname {
                        type string;
                    }
                }
            }
            container nispparas {
                leaf nispservaddr {
                    type inet:ipv6-address;
                }
                list nispcli {
                    key cliduid;
                    leaf cliduid {
                        type uint32;
                    }
                    leaf clidomainname {
                        type string;
                    }
                }
            }
        }
        container relayopaqueparas {
            description "This container contains some opaque values in Relay Agent options
                that need to be configured on the server side only for value match.
                Such Relay Agent options include Interface-Id option, Remote-Id
                option and Subscriber-Id option.";
            list relays {
                key relayname;
                leaf relayname {
                    type string;
                }
                list interfaceinfo {
                    key ifname;
                    leaf ifname {
                        type string;
                    }
                    leaf interface-id {
                        type string;
                    }
                }
                list subscribers {
                    key subscribername;
                    leaf subscribername {
                        type string;
                    }
                    leaf subscribernameid {
                        type string;
                    }
                }
                list remotehost {
                    key entnum;
                    leaf entnum {
                        type uint8;
                    }
                    leaf remote-id {
                        type string;
                    }
                }
            }
        }
        container packetstats {
            config "false";
            description "A container presents the packet statistics related to the DHCPv6
                server.";
            leaf solicit-count {
                type uint32;
            }
            leaf request-count {
                type uint32;
            }
            leaf renew-count {
                type uint32;
            }
            leaf rebind-count {
                type uint32;
            }
            leaf decline-count {
                type uint32;
            }
            leaf release-count {
                type uint32;
            }
            leaf inforeq-count {
                type uint32;
            }
            leaf advertise-count {
                type uint32;
            }
            leaf confirm-count {
                type uint32;
            }
            leaf reply-count {
                type uint32;
            }
            leaf reconfigure-count {
                type uint32;
            }
            leaf relay-forward-count {
                type uint32;
            }
            leaf relay-reply-count {
                type uint32;
            }
        }
    }

    container relay {
        if-feature dhcpv6-relay;
        container relayattributes {
            description "A container describes some basic attributes of the relay agent
                including some relay agent specific options data that need to be configured
                previously. Such options include Remote-Id option and Subscriber-Id option.";
            leaf name {
                type string;
            }
            leaf enable {
                type boolean;
            }
            leaf-list destaddrs {
                description "Each DHCPv6 relay agent may be configured with a list of destination
                    addresses. This node defines such a list of IPv6 addresses that
                    may include unicast addresses, multicast addresses or other addresses.";
                type inet:ipv6-address;
            }
            list subscribers {
                key subscribername;
                leaf subscribername {
                    type string;
                }
                leaf subscriber-id {
                    type string;
                }
            }
            list remotehost {
                key entnum;
                leaf entnum {
                    type uint8;
                }
                leaf remote-id {
                    type string;
                }
            }
            uses vendor-info;
            container relayinterfaces {
                description "It is a container that defines common configuration and state
                    parameters in the interfaces of a DHCPv6 relay agent. In this
                    YANG data model for DHCPv6 relay agent, the parameters are configured
                    in a per-interface manner.";
                list relayif {
                    description "A list describes a specific interface and its corresponding parameters.
                        Here we use a string called 'ifName' as the key of list.";
                    key ifname;
                    leaf ifname {
                        type string;
                    }
                    leaf enable {
                        type boolean;
                    }
                    leaf interface-id {
                        type string;
                    }
                    list nextentity {
                        description "This node defines a list that is used to describe the next hop
                            entity of this relay distinguished by their addresses.";
                        key destaddr;
                        leaf destaddr {
                            type inet:ipv6-address;
                        }
                        leaf available {
                            type boolean;
                        }
                        leaf multicast {
                            type boolean;
                        }
                        leaf server {
                            type boolean;
                        }
                        container packetstats {
                            config "false";
                            description "A container shows packet state information of a specific interface.
                                It is a sub-container of the 'relayInterfaces' container.";
                            leaf clipacketrvd-count {
                                type uint32;
                            }
                            leaf solicitrvd-count {
                                type uint32;
                            }
                            leaf requestrvd-count {
                                type uint32;
                            }
                            leaf renewrvd-count {
                                type uint32;
                            }
                            leaf rebindrvd-count {
                                type uint32;
                            }
                            leaf declinervd-count {
                                type uint32;
                            }
                            leaf releaservd-count {
                                type uint32;
                            }
                            leaf inforeqrvd-count {
                                type uint32;
                            }
                            leaf relayforvd-count {
                                type uint32;
                            }
                            leaf relayreprvd-count {
                                type uint32;
                            }
                            leaf packettocli-count {
                                type uint32;
                            }
                            leaf advertisesent-count {
                                type uint32;
                            }
                            leaf confirmsent-count {
                                type uint32;
                            }
                            leaf replysent-count {
                                type uint32;
                            }
                            leaf reconfigsent-count {
                                type uint32;
                            }
                            leaf relayforsent-count {
                                type uint32;
                            }
                            leaf relayrepsent-count {
                                type uint32;
                            }
                        }
                    }
                }
            }
        }
        container relaystats {
            config "false";
            description "The container records and presents the overall packet statistics
                of the relay agent.";
            leaf clipacketrvd-count {
                type uint32;
            }
            leaf relayforrvd-count {
                type uint32;
            }
            leaf relayreprvd-count {
                type uint32;
            }
            leaf packettocli-count {
                type uint32;
            }
            leaf relayforsent-count {
                type uint32;
            }
            leaf relayrepsent-count {
                type uint32;
            }
            leaf discardedpacket-count {
                type uint32;
            }
        }
    }

    container client {
        if-feature dhcpv6-client;
        container clientinterfaces {
            description "A client may have several interfaces, it is more reasonable to
                configure and manage parameters on the interface-level. This container
                includes configuration and state data of a DHCPv6 client in a
                per-interface manner.";
            list clientif {
                description "The list defines a specific client interface and its data. Different
                    interfaces are distinguished by the key which is a configurable string
                    value.";
                key ifname;
                leaf ifname {
                    type string;
                }
                leaf duid {
                    config "false";
                    description "Each server and client has only one DUID (DHCP Unique Identifier).
                        The DUID here will be carried in the Client ID option to identify
                        a specific DHCPv6 client.";
                    type uint32;
                }
                leaf enable {
                    type boolean;
                }
                leaf clifqdn {
                    description "A DHCPv6 server needs to know the Fully Qualified Domain Name
                        (FQDN) of the client to achieve the DNS update.";
                    type string;
                }
                leaf pd-function {
                    description "Whether the client can act as a requesting router to request
                        prefixes using prefix delegation ([RFC3633]).";
                    type boolean;
                }
                leaf rapidcommit {
                    description "'1' indicates a client can initiate a Solicit-Reply message exchange
                        by adding a Rapid Commit option in Solicit message. '0' means
                        the client is not allowed to add a Rapid Commit option to request
                        addresses in a two-message exchange pattern.";
                    type boolean;
                }
                leaf dual-stack {
                    type boolean;
                }
                container mo-tab {
                    description "The management tab label indicates the operation mode of the
                        DHCPv6 client. 'm'=1 and 'o'=1 indicate the client will use DHCPv6
                        to obtain all the configuration data. 'm'=1 and 'o'=0 are a meaningless
                        combination. 'm'=0 and 'o'=1 indicate the client will use stateless
                        DHCPv6 to obtain configuration data apart from addresses/prefixes
                        data. 'm'=0 and 'o'=0 represent the client will not use DHCPv6
                        but use SLAAC to achieve configuration.";
                    leaf m-tab {
                        type boolean;
                    }
                    leaf o-tab {
                        type boolean;
                    }
                }
                uses vendor-info;
                container identity-associations {
                    config "false";
                    description "IA is a construct through which a server and a client can identify,
                        group, and manage a set of related IPv6 addresses. The key of
                        the list is a 4-byte number IAID defined in [RFC3315] .";
                    list identity-association {
                        key iaid;
                        leaf iaid {
                            type uint8;
                        }
                        leaf iatype {
                            type string;
                        }
                        leaf-list ipv6addr {
                            type inet:ipv6-address;
                        }
                        leaf-list ipv6prefix {
                            type inet:ipv6-prefix;
                        }
                        leaf-list prefix-length {
                            type uint8;
                        }
                        leaf t1-time {
                            type yang:date-and-time;
                        }
                        leaf t2-time {
                            type yang:date-and-time;
                        }
                        leaf preferred-lifetime {
                            type yang:timeticks;
                        }
                        leaf valid-lifetime {
                            type yang:timeticks;
                        }
                    }
                }
                container ifotherparas {
                    config "false";
                    description "A client can obtain extra configuration data other than address
                        and prefix information through DHCPv6. This container describes
                        such data the client was configured. The potential configuration
                        data may include DNS server addresses, SIP server domain names, etc.";
                    leaf-list dnsservaddr {
                        type inet:ipv6-address;
                    }
                    leaf domainsearchlist {
                        type string;
                    }
                    leaf-list sipservaddr {
                        type inet:ipv6-address;
                    }
                    leaf sipservdomainnamelist {
                        type string;
                    }
                    leaf unidhcpv6servaddr {
                        type inet:ipv6-address;
                    }
                    leaf-list sntpservaddr {
                        type inet:ipv6-address;
                    }
                    container ntpservparas {
                        leaf ntpservaddr {
                            type inet:ipv6-address;
                        }
                        leaf ntpservmuladdr {
                            type inet:ipv6-address;
                        }
                        leaf ntpservfqdn {
                            type string;
                        }
                    }
                    container nisparas {
                        leaf nisservaddr {
                            type inet:ipv6-address;
                        }
                        leaf nisclidomainname {
                            type string;
                        }
                    }
                    container nispparas {
                        leaf nispservaddr {
                            type inet:ipv6-address;
                        }
                        leaf nispclidomainname {
                            type string;
                        }
                    }
                }
                container packetstats {
                    config "false";
                    description "A container records all the packet status information of a specific
                        interface.";
                    leaf solicit-count {
                        type uint32;
                    }
                    leaf request-count {
                        type uint32;
                    }
                    leaf renew-count {
                        type uint32;
                    }
                    leaf rebind-count {
                        type uint32;
                    }
                    leaf decline-count {
                        type uint32;
                    }
                    leaf release-count {
                        type uint32;
                    }
                    leaf inforeq-count {
                        type uint32;
                    }
                    leaf advertise-count {
                        type uint32;
                    }
                    leaf confirm-count {
                        type uint32;
                    }
                    leaf reply-count {
                        type uint32;
                    }
                    leaf reconfigure-count {
                        type uint32;
                    }
                }
            }
        }
    }

/*
 * Notifications
 */

    notification notifications {
        container dhcpv6-server-event {
            if-feature dhcpv6-server;
            container addr-used-up {
                leaf servduid {
                    type uint32;
                }
                leaf servname {
                    type string;
                }
                leaf pool-name {
                    type string;
                }
            }
            container prefix-used-up {
                leaf servduid {
                    type uint32;
                }
                leaf servname {
                    type string;
                }
                leaf pool-name {
                    type string;
                }
            }
            container invalid-client-detected {
                leaf cliduid {
                    type uint32;
                }
                leaf description {
                    type string;
                }
            }
        }
        container dhcpv6-relay-event {
            if-feature dhcpv6-relay;
            container topo-changed {
                leaf relayifname {
                    type string;
                }
                leaf first-hop {
                    type boolean;
                }
                leaf lastentityaddr {
                    type inet:ipv6-address;
                }
            }
        }
        container dhcpv6-client-event {
            if-feature dhcpv6-client;
            container invalid-ia-detected {
                leaf cliduid {
                    type uint32;
                }
                leaf iaid {
                    type uint8;
                }
                leaf servduid {
                    type uint32;
                }
                leaf description {
                    type string;
                }
            }
            container retransmission-failed {
                leaf cliduid {
                    type uint32;
                }
                leaf description {
                    type enumeration {
                        enum "MRC failed";
                        enum "MRD failed";
                    }
                }
            }
            container failed-status-turn-up {
                leaf cliduid {
                    type uint32;
                }
                leaf statuscode {
                    type enumeration {
                        enum "1" {
                            description "UnspecFail";
                        }
                        enum "2" {
                            description "NoAddrAvail";
                        }
                        enum "3" {
                            description "NoBinding";
                        }
                        enum "4" {
                            description "NotOnLink";
                        }
                        enum "5" {
                            description "UseMulticast";
                        }
                    }
                }
            }
        }
    }
}
