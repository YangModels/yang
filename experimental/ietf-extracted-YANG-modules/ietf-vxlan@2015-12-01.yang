module ietf-vxlan {
    namespace "urn:ietf:params:xml:ns:yang:ietf-vxlan";
    prefix "vxlan";

    import ietf-interfaces {
      prefix "if";
     }

    import ietf-inet-types {
       prefix "inet";
     }

    import ietf-yang-types {
       prefix yang;
     }

    organization
      "IETF NVO3(Network Virtualization Overlays) Working Group";

      contact
       "
         WG List:  <mailto:nvo3@ietf.org>

         WG Chair: Matthew Bocci
                  <mailto:matthew.bocci@alcatel-lucent.com>

         WG Chair: Benson Schliesser
                  <mailto:bensons@queuefull.net>

         Editor:   Fangwei Hu
                   <mailto:hu.fangwei@zte.com.cn>

         Editor:   Ran Chen
                   <mailto:chen.ran@zte.com.cn>

         Editor:   Mallik Mahalingam
                   <mailto:mallik_mahalingam@yahoo.com>

         Editor:   Zu Qiang
                   <mailto:Zu.Qiang@Ericsson.com>
        ";

    description
       "The YANG module defines a generic configuration
         model for VxLAN protocol";

    revision 2015-12-01 {
       description
         "02 revision.";
       reference
         "draft-chen-nvo3-vxlan-yang-02";
     }

    revision 2015-10-12 {
       description
         "01 revision.";
       reference
         "draft-chen-nvo3-vxlan-yang-01";
     }

    revision 2015-05-05 {
      description "Initial revision";
      reference
         "draft-chen-nvo3-vxlan-yang-00";
    }

    /* Typedefs  */

    typedef bgp-rt-type {
      type enumeration {
        enum import {
        description "For import";
       }
       enum export {
         description "For export";
       }
       enum both {
         description "For both import and export";
       }
     }
     description "BGP route-target type. Import from BGP YANG";
    }

    typedef vlan {
      type uint16 {
        range 1..4094;
      }
      description
      "Typedef for VLAN";
    }

    typedef vxlan-id {
      type uint32;
      description
        "Typedef for VxLAN ID.";
    }

    typedef access-type-vlan {
      type enumeration {
        enum access-type-vlan1to1 {
          description
            "Access type is VLAN 1:1.";
        }
        enum access-type-vlan1ton {
          description
            "Access type is VLAN 1:n.";
        }

      }
      default access-type-vlan1to1 ;
      description
        "VxLAN access type is VLAN.";
    }

    typedef access-type-mac {
       type empty ;
       description
         "VxLAN access type is MAC.";
    }

    typedef inner-vlan-handling-mode {
       type enumeration {
         enum discard-inner-vlan {
              description
                "Discard inner-VLAN.";
         }
         enum no-discard-inner-vlan {
              description
                "No discard inner-VLAN.";
         }
       }
       default discard-inner-vlan ;
       description
        "Typedef for inner-vlan-handling-mode";
    }

    typedef address-family-type {
       type enumeration {
         enum ipv4 {
           description
             "IPv4";
         }
         enum ipv6 {
           description
             "IPv6";
         }
       }
       description
         "Typedef for address family type.";
     }

    /* Configuration Data */

      container vxlan{
        list vxlan-instance {
           key vxlan-id ;
           leaf vxlan-id {
             type vxlan-id;
             description
              "VxLAN ID.";
           }

           choice vxlan-access-types {

              case access-type-vlan {

                leaf access-type-vlan {
                  type access-type-vlan;

                  description
                     "Access type is VLAN.";
                }

                list access-vlan-list {
                  key vlan-id ;
                  leaf vlan-id {
                    type vlan;
                    description
                      "VLAN ID.";
                  }
                  description
                    "VLAN ID list." ;
                }
                  description
                    "VxLAN access type choice is VLAN.";
              }

              case access-type-mac {
                leaf access-type-mac {
                  type empty ;
                  description
                    "Access type is MAC.";
                }

                leaf mac {
                    type yang:mac-address ;
                    mandatory true ;
                    description
                      "MAC Address.";
                  }
                description
                  "VxLAN access type choice is MAC Address.";
              }

              case access-type-l2interface {
                leaf access-type-l2interface {
                  type empty ;
                  description
                    "VXLAN map layer two interface.";
                }

                leaf vlan-id {
                    type vlan;
                    mandatory true ;
                    description
                      "VLAN ID.";
                 }

                leaf interface-name {
                    type if:interface-ref;
                    mandatory true ;
                    description
                      "Layer two interface name.";
                }
                description
                  "VxLAN access type choice is layer two interface.";
              }

              case access-type-l3interface {
                leaf access-type-l3interface {
                  type empty ;
                  description
                    "Access type of VxLAN is layer three interface.";
                }

                list map-l3interface {
                  key interface-name ;
                  leaf interface-name {
                    type if:interface-ref;
                    description
                      "Layer three interface name.";
                  }
                  description
                     "Layer three interface list.";
                }
                description
                  "VxLAN access type choice is layer three interface.";
              }
              description
                 "VxLAN access type choice.";
            }

            container vxlan-evpn {
              leaf route-distinguisher {
                type string;
                description "VxLAN EVPN BGP RD";
              }

              list vpn-targets {
                key rt-value;
                description "VxLAN EVPN Route Targets";
                leaf rt-value {
                  type string;
                  description "Route-Target value";
                }

                leaf rt-type {
                  type bgp-rt-type;
                  mandatory true;
                  description "Type of RT";
                }
              }
              description
                 "EVPN VxLAN parameters.";
            }
          description
             "VxLAN instance.";
        }

      container interfaces {
        list interface{
            key name;
            leaf name {
               type if:interface-ref;
               description
                  "VTEP interface name.";
             }

            list vtep-instances {
               key vtep-id ;
               leaf vtep-id {
                  type uint32;
                  description
                     "VTEP ID.";
                }

               leaf vtep-name{
                  type string;
                  description
                     "VTEP instance name.";
                }

               leaf source-interface {
                  type if:interface-ref;
                  description
                     "Source interface name.";
                }

                leaf multicast-ip {
                  type inet:ip-address;
                  mandatory true ;
                  description
                     "VxLAN multicast IP address.";
                }

               leaf inner-vlan-handling-mode {
                  type inner-vlan-handling-mode;
                  description
                     "The inner vlan tag handling mode.";
                }

               list bind-vxlan-id {
                  key vxlan-id;
                  leaf vxlan-id {
                    type vxlan-id;
                    description
                       "VxLAN ID.";
                  }
                 description
                    "VxLAN ID list for the VTEP.";
               }
             description
                "VTEP instance.";
            }

            list static-vxlan-tunnel{
               key vxlan-tunnel-id;
               leaf vxlan-tunnel-id {
                  type uint32;
                  description
                     "Static VxLAN tunnel ID.";
               }

               leaf vxlan-tunnel-name {
                  type string;
                  description
                    "Name of the static VxLAN tunnel.";
               }

               list address-family {
                 key "af";
                 leaf af {
                    type address-family-type;
                    description
                     "Address family type value.";
                 }

                 leaf tunnel-source-ip {
                    type address-family-type;
                    description
                     "Source IP address for the static VxLAN tunnel";
                 }

                 leaf tunnel-destination-ip {
                    type address-family-type;
                    description
                       "Destination IP address for the static VxLAN tunnel";
                 }

                 list bind-vxlan-id {
                    key vxlan-id;
                    leaf vxlan-id {
                      type vxlan-id;
                      description
                        "VxLAN ID.";
                    }
                    description
                       "VxLAN ID list for the VTEP.";
                 }
                description
                   "Per-af params.";
               }
            description
              "Configure the static VxLAN tunnel";
           }

          description
            "VTEP interface.";
        }
        description
          "VTEP interfaces configuration.";
      }
      description
       "VxLAN configure model.";
     }

      /* Operational  data */
     container vxlan-state{
      container vxlan-instance {
          leaf vxlan-id {
            type  vxlan-id;
            description
               "Show VxLAN ID.";
            }

          choice vxlan-access-types {

              case access-type-vlan {

                leaf access-type-vlan {
                  type access-type-vlan;
                  description
                    "Access type is VLAN.";
                }

                list access-vlan {
                  key vlan-id;
                  leaf vlan-id {
                    type vlan;
                    description
                      "VLAN ID.";
                  }
                  description
                    "VLAN ID list.";
                }
                description
                  "VxLAN access type choice is VLAN.";
              }

              case vxlan-access-mac {
                leaf access-type-mac {
                  type empty ;
                  description
                    "Access type is MAC.";
                }

                leaf mac {
                    type yang:mac-address ;
                    description
                      "MAC Address.";
                  }
                description
                  "VxLAN access type choice is MAC.";
              }

              case vxlan-access-l2interface {
                leaf access-type-l2interface {
                  type empty ;
                  description
                    "VxLAN access is layer two interface.";
                }
                leaf vlan-id {
                    type vlan;
                    description
                      "VLAN ID.";
                 }

                leaf interface-name {
                    type if:interface-ref;
                   description
                     "Layer two interface name.";
                }
                description
                  "VxLAN access type choice is layer two interface.";
              }

              case vxlan-access-l3interface {
                leaf access-type-l3interface {
                  type empty ;
                  description
                    "VxLAN access type is layer three interface.";
                }

                list map-l3interface {
                  key interface-name ;
                  leaf interface-name {
                    type if:interface-ref;
                    description
                      "Layer three interface name.";
                  }
                  description
                    "VxLAN access layer three interfaces.";
                }
                description
                  "VxLAN access type choice is layer three interface.";
              }
              description
                "VxLAN access type choice.";
            }

            container vxlan-evpn {
              leaf route-distinguisher {
                type string;
                description "VxLAN EVPN BGP RD";
              }

              list vpn-targets {
                key rt-value;
                description "VxLAN EVPN Route Targets";
                leaf rt-value {
                  type string;
                  description "Route-Target value";
                }

                leaf rt-type {
                  type bgp-rt-type;
                  mandatory true;
                  description "Type of RT";
                }
              }
              description "Show EVPN VxLAN parameters.";
            }
          description
            "Show VxLAN instance information.";
        }

        container vtep-instance {
          leaf vtep-id {
            type  uint32;
            description
              "Show VTEP ID.";
            }

          leaf vtep-name {
            type  string;
            description
              "Show VTEP name.";
            }

          leaf source-interface{
            type if:interface-ref;
            description
              "Show source interface.";
            }

          leaf multicast-ip {
             type inet:ip-address;
             description
               "Show VxLAN multicast IP address.";
             }

          leaf inner-vlan-handling-mode {
            type inner-vlan-handling-mode;
            default discard-inner-vlan ;
            description
              "Show inner vlan tag handling mode." ;
          }

          list bind-vxlan-id {
             key vxlan-id;
             leaf vxlan-id {
               type vxlan-id;
               description
                 "Show VxLAN ID." ;
             }
             description
               "Show VxLAN ID list for the VTEP.";
            }
           description
             "Show VTEP information.";
        }

        list static-vxlan-tunnel{
           key vxlan-tunnel-id;
           leaf vxlan-tunnel-id {
             type uint32;
             description
             "Show static VxLAN tunnel ID.";
            }

            leaf vxlan-tunnel-name {
              type string;
              description
                 "Name of the static VxLAN tunnel.";
            }

            list address-family {
              key "af";
              leaf af {
                type address-family-type;
                description
                  "Address family type value.";
              }

              leaf tunnel-source-ip {
                 type address-family-type;
                 description
                   "Show source IP address of the static VxLAN tunnel";
              }

              leaf tunnel-destination-ip {
                 type address-family-type;
                 description
                   "Show destination IP address of the static VxLAN tunnel";
                 }

              list bind-vxlan-id {
                 key vxlan-id;
                 leaf vxlan-id {
                   type vxlan-id;
                   description
                     "VxLAN ID.";
                   }
                 description
                   "Show VxLAN ID list for the VTEP.";
              }

            description
               "Per-af params.";
               }
          description
            "Configure the static VxLAN tunnel";
        }
        config "false";
        description
           "Show VxLAN operational state information.";
       }
     }
