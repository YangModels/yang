module ietf-te-mpls-types {

  namespace "urn:ietf:params:xml:ns:yang:ietf-te-mpls-types";

  /* Replace with IANA when assigned */
  prefix "te-mpls-types";

  organization
    "IETF TEAS Working Group";

  contact "Fill me";

  description
    "This module contains a collection of generally
    useful TE specific YANG data type defintions.";

  revision "2017-03-10" {
    description "Latest revision of TE MPLS types";
    reference "RFC3209";
  }

  identity backup-protection-type {
    description
      "Base identity for backup protection type";
  }

  identity backup-protection-link {
    base backup-protection-type;
    description
      "backup provides link protection only";
  }

  identity backup-protection-node-link {
    base backup-protection-type;
    description
      "backup offers node (preferred) or link protection";
  }

  identity bc-model-type {
    description
      "Base identity for Diffserv-TE bandwidth constraint
      model type";
  }

  identity bc-model-rdm {
    base bc-model-type;
    description
      "Russian Doll bandwidth constraint model type.";
  }

  identity bc-model-mam {
    base bc-model-type;
    description
      "Maximum Allocation bandwidth constraint
      model type.";
  }

  identity bc-model-mar {
    base bc-model-type;
    description
      "Maximum Allocation with Reservation
      bandwidth constraint model type.";
  }

  typedef bandwidth-kbps {
    type uint64;
    units "Kbps";
    description
      "Bandwidth values expressed in kilobits per second";
  }

  typedef bandwidth-mbps {
    type uint64;
    units "Mbps";
    description
      "Bandwidth values expressed in megabits per second";
  }

  typedef bandwidth-gbps {
    type uint64;
    units "Gbps";
    description
      "Bandwidth values expressed in gigabits per second";
  }

  typedef te-bandwidth-type {
    type enumeration {
      enum SPECIFIED {
        description
          "Bandwidth is explicitly specified";
      }
      enum AUTO {
        description
          "Bandwidth is automatically computed";
      }
    }
    description
      "enumerated type for specifying whether bandwidth is
       explicitly specified or automatically computed";
  }

  typedef bfd-type {
    type enumeration {
      enum classical {
        description "BFD classical session type.";
      }
      enum seamless {
        description "BFD seamless session type.";
      }
    }
    default "classical";
    description
      "Type of BFD session";
  }

  typedef bfd-encap-mode-type {
    type enumeration {
      enum gal {
        description
          "BFD with GAL mode";
      }
      enum ip {
        description
          "BFD with IP mode";
      }
    }
    default ip;
    description
      "Possible BFD transport modes when running over TE
      LSPs.";
  }
}
