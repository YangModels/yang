module udmcore {

   namespace "urn:com:nsn:udmcore";
   prefix "udm";

   import yang-types {prefix "yt";}
   import complex-types {prefix "ct";}

   ct:complex-type BasicObject {
      ct:abstract true;
      key "distinguishedName";
            leaf globalId {type int64;}
            leaf distinguishedName {type string; mandatory true;}
   }

   ct:complex-type ManagedObject {
      ct:extends BasicObject;
      ct:abstract true;
      leaf instance {type string;}
      leaf objectState {type int32;}
      leaf release {type string;}
   }

   ct:complex-type Resource {
            ct:extends ManagedObject;
            ct:abstract true;
      leaf usageState {type int16;}
      leaf managementMethodSupported {type string;}
      leaf managementMethodCurrent {type string;}
      leaf managementInfo {type string;}
      leaf managementDomain {type string;}
      leaf version {type string;}
      leaf entityIdentification {type string;}
      leaf desription {type string;}
      leaf rootEntityType {type string;}
   }

   ct:complex-type LogicalResource {
      ct:extends Resource;
      ct:abstract true;
      leaf lrStatus {type int32;}
      leaf serviceState {type int32;}
      leaf isOperational {type boolean;}
   }

   ct:complex-type PhysicalResource {
      ct:extends Resource;
      ct:abstract true;
      leaf manufactureDate {type string;}
      leaf otherIdentifier {type string;}
      leaf powerState {type int32;}
      leaf serialNumber {type string;}
      leaf versionNumber {type string;}
   }

   ct:complex-type Hardware {
      ct:extends PhysicalResource;
      ct:abstract true;
      leaf width {type string;}
      leaf height {type string;}
      leaf depth {type string;}
      leaf measurementUnits {type int32;}
      leaf weight {type string;}
      leaf weightUnits {type int32;}
      leaf-list physicalLink {
         type instance-identifier {
            ct:instance-type PhysicalLink;
         }
      }
      ct:instance-list containedHardware {
         ct:instance-type Hardware;
      }
      ct:instance-list physicalConnector {
         ct:instance-type PhysicalConnector;
      }
   }

   ct:complex-type PhysicalLink {
      ct:extends PhysicalResource;
      leaf isWiereless {type boolean;}
      leaf currentLength {type string;}
      leaf maximumLength {type string;}
      leaf mediaType {type int32;}
      leaf-list hardware {
         type instance-identifier {
            ct:instance-type Hardware;
         }
      }
   }

   ct:complex-type ManagedHardware {
      ct:extends Hardware;
      leaf additionalinfo {type string;}
      leaf physicalAlarmReportingEnabled {type boolean;}
      leaf pyhsicalAlarmStatus {type int32;}
      leaf coolingRequirements {type string;}
      leaf hardwarePurpose {type string;}
      leaf isPhysicalContainer {type boolean;}
   }

   ct:complex-type AuxiliaryComponent {
      ct:extends ManagedHardware;
      ct:abstract true;
   }

   ct:complex-type PhysicalPort {
      ct:extends ManagedHardware;
      leaf portNumber {type int32;}
      leaf duplexMode {type int32;}
      leaf ifType {type int32;}
      leaf vendorPortName {type string;}
   }

   ct:complex-type PhysicalConnector {
      ct:extends Hardware;
      leaf location {type string;}
      leaf cableType {type int32;}
      leaf gender {type int32;}
      leaf inUse {type boolean;}
      leaf pinDescription {type string;}
      leaf typeOfConnector {type int32;}
      leaf-list sourcePhysicalConnector {
         type instance-identifier {
            ct:instance-type PhysicalConnector;
         }
      }
      leaf-list targetPhysicalConnector {
         type instance-identifier {
            ct:instance-type PhysicalConnector;
         }
      }
   }

   ct:complex-type Equipment {
      ct:extends ManagedHardware;
      leaf installStatus {type int32;}
      leaf expectedEquipmentType {type string;}
      leaf installedEquipmentType {type string;}
      leaf installedVersion {type string;}
      leaf redundancy {type int32;}
      leaf vendorName {type string;}
      leaf dateOfLastService {type yt:date-and-time;}
      leaf interchangeability {type string;}
      leaf identificationCode {type string;}
      ct:instance-list equipment {
         ct:instance-type Equipment;
      }
   }

   ct:complex-type EquipmentHolder {
      ct:extends ManagedHardware;
      leaf vendorName {type string;}
      leaf locationName {type string;}
      leaf dateOfLastService {type yt:date-and-time;}
      leaf partNumber {type string;}
      leaf availabilityStatus {type int16;}
      leaf nameFromPlanningSystem {type string;}
      leaf modelNumber {type string;}
      leaf acceptableEquipmentList {type string;}
      leaf isSolitaryHolder {type boolean;}
      leaf holderStatus {type int16;}
      leaf interchangeability {type string;}
      leaf equipmentHolderSpecificType {type string; }
      leaf position {type string;}
      leaf atomicCompositeType {type int16;}
      leaf uniquePhysical {type boolean;}
      leaf physicalDescription {type string;}
      leaf serviceApproach {type string;}
      leaf mountingOptions {type int32;}
      leaf cableManagementStrategy {type string;}
      leaf isSecureHolder {type boolean;}
      ct:instance-list equipment {
         ct:instance-type Equipment;
            }
      ct:instance-list equipmentHolder {
         ct:instance-type EquipmentHolder;
      }
   }

   // ... other resource complex types ...
}
