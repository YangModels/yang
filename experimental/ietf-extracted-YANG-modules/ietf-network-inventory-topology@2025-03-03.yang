module ietf-network-inventory-topology {
  yang-version 1.1;
  namespace
    "urn:ietf:params:xml:ns:yang:ietf-network-inventory-topology";
  prefix nwit;

  import ietf-network {
    prefix nw;
    reference
      "RFC 8345: A YANG Data Model for Network Topologies,
                 Section 4.1";
  }
  import ietf-network-topology {
    prefix nt;
    reference
      "RFC 8345: A YANG Data Model for Network Topologies,
                 Section 4.2";
  }
  import ietf-network-inventory {
    prefix nwi;
    reference
      "RFC AAAA: A YANG Data Model for Network Inventory";
  }

  organization
    "IETF Network Inventory YANG (ivy) Working Group";
  contact
    "WG Web:   <https://datatracker.ietf.org/wg/ivy>
     WG List:  <mailto:inventory-yang@ietf.org>

     Editor: Bo Wu
             <lana.wubo@huawei.com>
     Editor: Mohamed Boucadair
             <mohamed.boucadair@orange.com>
     Author: Cheng Zhou
             <zhouchengyjy@chinamobile.com>
     Author: Qin Wu
             <bill.wu@huawei.com>";
  description
    "This YANG module defines a YANG module for network
     topology and inventory mapping.

     Copyright (c) 2025 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2025-03-03 {
    description
      "Initial revision.";
    reference
      "RFC XXXX: A Network Data Model for Inventory Topology
                 Mapping";
  }

  /* features */

  feature inventory-to-topology-navigate {
    description
      "Indicates support for navigating from inventory to topology.";
  }

  feature topology-to-inventory-navigate {
    description
      "Indicates support for navigating from topology to inventory.";
  }

  /* Groupings */
  /* Node Grouping Feature with 1:1 mapping to NE*/

  grouping node-inventory-feature-attributes {
    description
      "Network Inventory mapping node scope attributes";
    container inventory-mapping-attributes {
      if-feature "topology-to-inventory-navigate";
      description
        "The container node attributes of Network Inventory
         mapping.";
      leaf ne-ref {
        type nwi:ne-ref;
        config false;
        description
          "1:1 mapping to the Network Element (NE) from which this
           node is abstracted.";
      }
    }
  }

  grouping tp-inventory-feature-attributes {
    description
      "Network Inventory mapping Termination Point (TP) scope
       attributes.";
    container inventory-mapping-attributes {
      if-feature "topology-to-inventory-navigate";
      description
        "Specifies the TP attributes of Network Inventory mapping.";
      /* 1:1 mapping to physical port component */
      uses nwi:port-ref;
      leaf physical-interface-name {
        type string;
        config false;
        description
          "1:1 mapping to physical interface name (e.g., eth0/1).";
      }
    }
  }

  grouping link-inventory-feature-attributes {
    description
      "Network Inventory mapping link scope attributes.";
    container inventory-mapping-attributes {
      if-feature "topology-to-inventory-navigate";
      description
        "Specifies  the link attributes of network inventory
         mapping.";
      leaf cable-name {
        type string;
        config false;
        description
          "Reports the reference of the cable inventory from which
           this link is abstracted.";
      }
      leaf link-type {
        type string;
        config false;
        description
          "Reports the type of the link.";
      }
    }
  }

  /* Main blocks */

  augment "/nw:networks/nw:network/nw:node" {
    description
      "Groups parameters for inventory at the node level.";
    uses node-inventory-feature-attributes;
  }

  augment "/nw:networks/nw:network/nt:link" {
    description
      "Augments inventory topology link information.";
    uses link-inventory-feature-attributes;
  }

  augment "/nw:networks/nw:network/nw:node/nt:termination-point" {
    description
      "Augments inventory termination point information.";
    uses tp-inventory-feature-attributes;
  }

  /* Augment the network-inventory to add topology navigate */

  augment "/nwi:network-inventory/nwi:network-elements"
        + "/nwi:network-element" {
    if-feature "inventory-to-topology-navigate";
    description
      "Augments the network element with 1:1 mapping with the network
       the element is part of.";
    uses nw:node-ref;
  }
}
