module nvo3-oam {
  namespace "urn:cisco:params:xml:ns:yang:nvo3-oam";
  prefix nvo3-oam;

  import gen-oam {
    prefix goam;
  }
  import ietf-inet-types {
    prefix inet;
  }
  import ietf-interfaces {
    prefix if;
  }
  import ietf-yang-types {
    prefix yang;
  }

  revision 2014-04-24 {
    description
      "Initial revision.";
  }

  identity nvo3 {
    base goam:technology-types;
    description
      "nvo3 type";
  }

  identity nvo3-mtv {
    base goam:command-sub-type;
  }

  identity nvo3-trace-route {
    base goam:command-sub-type;
  }

  identity nvo3-ping {
    base goam:command-sub-type;
  }

  identity technology-sub-type {
    description
      "certain implementations such as nvo3 can have
       different encap types such as vxlan, nvgre and so on.
       Instead of defining seperate models for each such encap
       we define technology sub type. Technology subtype
       is associated at MA level";
  }

  identity technology-sub-type-vxlan {
    base technology-sub-type;
    description
      "technology subtype is vxlan";
  }

  grouping command-ext-nvo3 {
    description
      "group the rpc command extensions for nvo3";
    choice context-id-nvo3 {
      case vni {
        leaf vni {
          type vni;
        }
      }
    }
    choice out-of-band {
      case ipv4-address {
        leaf ipv4-address {
          type inet:ipv4-address;
        }
      }
      case ipv6-address {
        leaf ipv6-address {
          type inet:ipv6-address;
        }
      }
      description
        "presence of this node indicate out of band request needed";
    }
  }

  typedef flow-entropy-vxlan {
    type inet:port-number;
  }

  typedef vni {
    type uint32;
  }

  typedef flags-vxlan {
    type bits {
      bit oam {
        position 0;
      }
      bit r1 {
        position 1;
      }
      bit r2 {
        position 2;
      }
      bit r3 {
        position 3;
      }
      bit r4 {
        position 4;
      }
      bit r5 {
        position 5;
      }
      bit r6 {
        position 6;
      }
      bit r7 {
        position 7;
      }
    }
  }

  typedef End-station-address {
    type union {
      type yang:mac-address;
      type inet:ipv4-address;
      type inet:ipv6-address;
    }
    description
      "Defines addresses of different End stations, MAC, IPv4 or
IPv6";
  }

  augment "/goam:domains/goam:domain/goam:MAs/goam:MA" {
    leaf technology-sub-type {
      type identityref {
        base technology-sub-type;
      }
    }
  }
  augment "/goam:domains/goam:domain/goam:MAs/goam:MA/goam:context-
id" {
    case context-id-nvo3 {
      leaf vni {
        type vni;
      }
    }
  }
  augment "/goam:domains/goam:domain/goam:MAs/goam:MA/goam:flow-
entropy" {
    case flow-entropy-vxlan {
      leaf flags-vxlan {
        type flags-vxlan;
      }
      leaf flow-entropy-vxlan {
        type flow-entropy-vxlan;
      }
    }
  }
  augment
"/goam:domains/goam:domain/goam:MAs/goam:MA/goam:MEP/goam:flow-
entropy" {
    case flow-entropy-vxlan {
      leaf flags-vxlan {
        type flags-vxlan;
      }
      leaf flow-entropy-vxlan {
        type flow-entropy-vxlan;
      }
    }
  }
  augment
"/goam:domains/goam:domain/goam:MAs/goam:MA/goam:MEP/goam:context-id"
{
    case context-id-nvo3 {
      leaf vni {
        type vni;
      }
    }
  }
  augment
"/goam:domains/goam:domain/goam:MAs/goam:MA/goam:MEP/goam:session/goa
m:context-id" {
    case context-id-nvo3 {
      leaf vni {
        type vni;
      }
    }
  }
  augment
"/goam:domains/goam:domain/goam:MAs/goam:MA/goam:MEP/goam:session/goa
m:flow-entropy" {
    case flow-entropy-vxlan {
      leaf flags-vxlan {
        type flags-vxlan;
      }
      leaf flow-entropy-vxlan {
        type flow-entropy-vxlan;
      }
    }
  }
  augment "/goam:ping/goam:input" {
    uses command-ext-nvo3;
  }
  augment "/goam:ping/goam:input" {
    leaf technology-sub-type {
      type identityref {
        base technology-sub-type;
      }
    }
  }
  augment "/goam:ping/goam:input" {
    case flow-entropy-vxlan {
      leaf flags-vxlan {
        type flags-vxlan;
      }
      leaf flow-entropy-vxlan {
        type flow-entropy-vxlan;
      }
    }
  }
  augment "/goam:trace-route/goam:input" {
    uses command-ext-nvo3;
  }
  augment "/goam:trace-route/goam:input" {
    leaf technology-sub-type {
      type identityref {
        base technology-sub-type;
      }
    }
  }
  augment "/goam:trace-route/goam:input" {
    case flow-entropy-vxlan {
      leaf flags-vxlan {
        type flags-vxlan;
      }
      leaf flow-entropy-vxlan {
        type flow-entropy-vxlan;
      }
    }
  }
  rpc mtv {
    description
      "Generates Trace-route and return response. Starts with TTL
       of one and increment by one at each hop. Untill destination
       reached or TTL reach max valune";
    input {
      uses goam:maintenance-domain {
        description
          "Specifies the MA-domain";
      }
      uses goam:ma-identifier {
        description
          "identfies the Maintenance association";
      }
      leaf technology-sub-type {
        type identityref {
          base technology-sub-type;
        }
      }
      uses command-ext-nvo3 {
        description
          "defines extensions needed for nvo3
           We are using this structure so mtv command is in line
           with ping and trace-route";
      }
      leaf max-hop-count {
        type uint8;
        default "255";
        description
          "Defines maximum value of hop count";
      }
      leaf command-sub-type {
        type identityref {
          base goam:command-sub-type;
        }
        description
          "defines different command types";
      }
      choice flow-entropy {
        case flow-entropy-null {
          leaf flow-entropy-null {
            type empty;
          }
        }
        case flow-entropy-vxlan {
          leaf flow-entropy-vxlan {
            type flow-entropy-vxlan;
          }
          leaf flags-vxlan {
            type flags-vxlan;
          }
        }
      }
      leaf-list scope {
        type inet:ip-address;
      }
      leaf ecmp-choice {
        type goam:ecmp-choices;
        description
          "0 means use platform defined path selection
           1 means use round robin";
      }
      list outgoing-interfaces {
        key "interface";
        leaf interface {
          type if:interface-ref;
        }
      }
      container source-mep {
        uses goam:mep-address;
        leaf mep-id {
          type goam:MEP-id;
        }
      }
      container destination-mep {
        uses goam:mep-address;
        leaf mep-id {
          type goam:MEP-id;
        }
      }
    }
    output {
      list response {
        key "mep-address mep-id";
        leaf hop-count {
          type uint8;
        }
        leaf mep-id {
          type goam:MEP-id;
        }
        leaf mep-address {
          type inet:ip-address;
        }
        leaf-list next-hop-device {
          type inet:ip-address;
          description
            "list of downstream devices. This is not specifically
             sorted it is a leaf list";
        }
        leaf upstream-device {
          type inet:ip-address;
        }
        leaf multicast-receiver-count {
          type uint32;
          description
            "number of ports that are interested in this multicast
stream";
        }
        uses goam:monitor-stats;
      }
    }
  }
  rpc End-station-locator {
    description
      "Allows to discover where the end station is located.";
    input {
      uses goam:maintenance-domain {
        description
          "Specifies the MA-domain";
      }
      uses goam:ma-identifier {
        description
          "identfies the Maintenance association";
      }
      uses command-ext-nvo3;
      container source-mep {
        uses goam:mep-address;
        leaf mep-id {
          type goam:MEP-id;
        }
      }
      leaf end-station-address {
        type End-station-address;
        description
          "End station address can be MAC address, IPv4 or IPv6
address.";
      }
    }
    output {
      list devices {
        leaf mep-id {
          type goam:MEP-id;
        }
        leaf mep-address {
          type inet:ip-address;
        }
        leaf mep-name {
          type string;
          description
            "End-station locator response MAY return the textual name
             of MEP that owns the end-station.
             If textual name is not available word Unknown SHOULD
             be returned";
        }
      }
    }
  }
}
