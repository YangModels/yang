module ietf-l3vpn-ntw {
  yang-version 1.1;
  namespace "urn:ietf:params:xml:ns:yang:ietf-l3vpn-ntw";
  prefix l3nm;

  import ietf-vpn-common {
    prefix vpn-common;
    reference
      "RFC UUUU: A Layer 2/3 VPN Common YANG Model";
  }
  import ietf-inet-types {
    prefix inet;
    reference
      "Section 4 of RFC 6991";
  }
  import ietf-yang-types {
    prefix yang;
    reference
      "Section 3 of RFC 6991";
  }
  import ietf-key-chain {
    prefix key-chain;
    reference
      "RFC 8177: YANG Key Chain.";
  }
  import ietf-routing-types {
    prefix rt-types;
    reference
      "RFC 8294: Common YANG Data Types for the Routing Area";
  }

  organization
    "IETF OPSA (Operations and Management Area) Working Group ";
  contact
    "WG Web:   <http://tools.ietf.org/wg/opsawg/>
     WG List:  <mailto:opsawg@ietf.org>

     Editor:    Samier Barguil
                <mailto:samier.barguilgiraldo.ext@telefonica.com>
     Editor:    Oscar Gonzalez de Dios
                <mailto:oscar.gonzalezdedios@telefonica.com>
     Editor:    Mohamed Boucadair
                <mailto:mohamed.boucadair@orange.com>
     Author:    Luis Angel Munoz
                <mailto:luis-angel.munoz@vodafone.com>
     Author:    Alejandro Aguado
                <mailto:alejandro.aguado_martin@nokia.com>
    ";
  description
    "This YANG module defines a generic network-oriented model
     for the configuration of Layer 3 Virtual Private Networks.

     Copyright (c) 2021 IETF Trust and the persons identified as
     authors of the code.  All rights reserved.

     Redistribution and use in source and binary forms, with or
     without modification, is permitted pursuant to, and subject to
     the license terms contained in, the Simplified BSD License set
     forth in Section 4 of the IETF Trust's Legal Provisions
     Relating to IETF Documents
     (https://trustee.ietf.org/license-info).

     This version of this YANG module is part of RFC XXXX
     (https://www.rfc-editor.org/info/rfcXXXX); see the RFC itself
     for full legal notices.";

  revision 2021-02-19 {
    description
      "Initial revision.";
    reference
      "RFC XXXX: A Layer 3 VPN Network YANG Model";
  }
  /* Features */

  feature msdp {
    description
      "This feature indicates that Multicast Source Discovery Protocol
       (MSDP) capabilities are supported by the VPN.";
    reference
      "RFC 3618: Multicast Source Discovery Protocol (MSDP)";
  }

  /* Identities */

  identity address-allocation-type {
    description
      "Base identity for address allocation type in the
       Provider Edge (PE)-Customer Edge (CE) link.";
  }

  identity provider-dhcp {
    base address-allocation-type;
    description
      "The Provider's network provides a DHCP service to the customer.";
  }

  identity provider-dhcp-relay {
    base address-allocation-type;
    description
      "The Provider's network provides a DHCP relay service to the
       customer.";
  }

  identity provider-dhcp-slaac {
    base address-allocation-type;
    description
      "The Provider's network provides a DHCP service to the customer
       as well as IPv6 Stateless Address Autoconfiguration (SLAAC).";
    reference
      "RFC 7527: IPv6 Stateless Address Autoconfiguration";
  }

  identity static-address {
    base address-allocation-type;
    description
      "The Provider-to-customer addressing is static.";
  }

  identity slaac {
    if-feature "vpn-common:ipv6";
    base address-allocation-type;
    description
      "Use IPv6 SLAAC.";
    reference
      "RFC 7527: IPv6 Stateless Address Autoconfiguration";
  }

  identity bearer-inf-type {
    description
      "Identity for the bearer interface type.";
  }

  identity port-id {
    base bearer-inf-type;
    description
      "Identity for the priority-tagged interface.";
  }

  identity lag-id {
    base bearer-inf-type;
    description
      "Identity for the lag-tagged interface.";
  }

  identity local-defined-next-hop {
    description
      "Defines a base identity type of local defined
       next-hops.";
  }

  identity discard {
    base local-defined-next-hop;
    description
      "Indicates an action to discard traffic for the
       corresponding destination.
       For example, this can be used to blackhole traffic.";
  }

  identity local-link {
    base local-defined-next-hop;
    description
      "Treat traffic towards addresses within the specified next-hop
       prefix as though they are connected to a local link.";
  }

  typedef predefined-next-hop {
    type identityref {
      base local-defined-next-hop;
    }
    description
      "Pre-defined next-hop designation for locally generated routes.";
  }

  /* Typedefs */

  typedef area-address {
    type string {
      pattern '[0-9A-Fa-f]{2}(\.[0-9A-Fa-f]{4}){0,6}';
    }
    description
      "This type defines the area address format.";
  }

  /* Main Blocks */
  /* Main l3vpn-ntw */

  container l3vpn-ntw {
    description
      "Main container for L3VPN services management.";
    container vpn-profiles {
      description
        "Contains a set of valid VPN Profiles to reference in the VPN
         service.";
      uses vpn-common:vpn-profile-cfg;
    }
    container vpn-services {
      description
        "Top-level container for the VPN services.";
      list vpn-service {
        key "vpn-id";
        description
          "List of VPN services.";
        uses vpn-common:vpn-description;
        leaf parent-service-id {
          type vpn-common:vpn-id;
          description
            "Pointer to the parent service, if any.
             A parent service can an L3SM, a slice request, a VPN+
             service, etc.";
        }
        leaf vpn-type {
          type identityref {
            base vpn-common:service-type;
          }
          description
            "Indicates the service type.";
        }
        leaf vpn-service-topology {
          type identityref {
            base vpn-common:vpn-topology;
          }
          default "vpn-common:any-to-any";
          description
            "VPN service topology.";
        }
        uses vpn-common:service-status;
        container ie-profiles {
          description
            "Container for Import/Export profiles.";
          list ie-profile {
            key "ie-profile-id";
            description
              "List for Imort/Export profile.";
            leaf ie-profile-id {
              type string;
              description
                "IE profile id.";
            }
            uses vpn-common:rt-rd;
          }
        }
        container underlay-transport {
          description
            "Container for underlay transport.";
          uses vpn-common:underlay-transport;
        }
        container external-connectivity {
          if-feature "vpn-common:external-connectivity";
          description
            "Container for external connectivity.";
          choice profile {
            description
              "Choice for the external connectivity profile.";
            case profile {
              leaf profile-name {
                type leafref {
                  path "/l3vpn-ntw/vpn-profiles"
                     + "/valid-provider-identifiers"
                     + "/external-connectivity-identifier/id";
                }
                description
                  "Name of the service provider's profile to be applied
                   at the VPN service level.";
              }
            }
          }
        }
        container vpn-nodes {
          description
            "Container for VPN nodes.";
          list vpn-node {
            key "vpn-node-id";
            description
              "List for VPN node.";
            leaf vpn-node-id {
              type union {
                type vpn-common:vpn-id;
                type uint32;
              }
              description
                "Type STRING or NUMBER identifier.";
            }
            leaf description {
              type string;
              description
                "Textual description of the VPN node.";
            }
            leaf ne-id {
              type string;
              description
                "Unique identifier of the network element where the VPN
                 node is deployed.";
            }
            leaf node-role {
              type identityref {
                base vpn-common:role;
              }
              default "vpn-common:any-to-any-role";
              description
                "Role of the VPN node in the IP VPN.";
            }
            leaf local-autonomous-system {
              if-feature "vpn-common:rtg-bgp";
              type inet:as-number;
              description
                "Provider's AS number in case the customer requests BGP
                 routing.";
            }
            leaf address-family {
              type identityref {
                base vpn-common:address-family;
              }
              description
                "The address family used for router-id information.";
            }
            leaf router-id {
              type inet:ip-address;
              description
                "The router-id information can be an IPv4 or IPv6
                 address.";
            }
            uses vpn-common:rt-rd;
            leaf node-ie-profile {
              type leafref {
                path "/l3vpn-ntw/vpn-services/vpn-service"
                   + "/ie-profiles/ie-profile/ie-profile-id";
              }
              description
                "Node's Import/Export profile.";
            }
            container maximum-routes {
              description
                "Defines maximum routes for the VRF.";
              list selector {
                key "address-family protocol";
                description
                  "List of address families.";
                leaf address-family {
                  type identityref {
                    base vpn-common:address-family;
                  }
                  description
                    "Indicates the address family (IPv4 or IPv6).";
                }
                leaf protocol {
                  type identityref {
                    base vpn-common:routing-protocol-type;
                  }
                  description
                    "Indicates the routing protocol. 'any' value can
                     be used to identify a limit that will apply for
                     any active routing protocol.";
                }
                leaf maximum-routes {
                  type uint32;
                  description
                    "Indicates the maximum prefixes the VRF can accept
                     for this address family and protocol.";
                }
              }
            }
            uses vpn-common:vpn-components-group;
            container multicast {
              if-feature "vpn-common:multicast";
              description
                "Global multicast parameters.";
              uses vpn-common:service-status;
              leaf-list tree-flavor {
                type identityref {
                  base vpn-common:multicast-tree-type;
                }
                description
                  "Type of tree to be used.";
              }
              container rp {
                description
                  "RP parameters.";
                container rp-group-mappings {
                  description
                    "RP-to-group mappings parameters.";
                  list rp-group-mapping {
                    key "id";
                    description
                      "List of RP-to-group mappings.";
                    leaf id {
                      type uint16;
                      description
                        "Unique identifier for the mapping.";
                    }
                    container provider-managed {
                      description
                        "Parameters for a provider-managed RP.";
                      leaf enabled {
                        type boolean;
                        default "false";
                        description
                          "Set to true if the Rendezvous Point (RP)
                           must be a provider-managed node.  Set to
                           false if it is a customer-managed node.";
                      }
                      leaf rp-redundancy {
                        type boolean;
                        default "false";
                        description
                          "If true, a redundancy mechanism for the
                           RP is required.";
                      }
                      leaf optimal-traffic-delivery {
                        type boolean;
                        default "false";
                        description
                          "If true, the SP must ensure that
                           traffic uses an optimal path.  An SP may
                           use Anycast RP or RP-tree-to-SPT
                           switchover architectures.";
                      }
                      container anycast {
                        when "../rp-redundancy = 'true' and
                              ../optimal-traffic-delivery = 'true'" {
                          description
                            "Only applicable if RP redundancy is enabled
                             and delivery through optimal path is
                             activated.";
                        }
                        description
                          "PIM Anycast-RP parameters.";
                        leaf local-address {
                          type inet:ip-address;
                          description
                            "IP local address for PIM RP. Usually, it
                             corresponds to router ID or primary
                             address";
                        }
                        leaf-list rp-set-address {
                          type inet:ip-address;
                          description
                            "Address other RP routers that share the
                             same RP IP address.";
                        }
                      }
                    }
                    leaf rp-address {
                      when "../provider-managed/enabled = 'false'" {
                        description
                          "Relevant when the RP is not
                           provider-managed.";
                      }
                      type inet:ip-address;
                      mandatory true;
                      description
                        "Defines the address of the RP.
                         Used if the RP is customer-managed.";
                    }
                    container groups {
                      description
                        "Multicast groups associated with the RP.";
                      list group {
                        key "id";
                        description
                          "List of multicast groups.";
                        leaf id {
                          type uint16;
                          description
                            "Identifier for the group.";
                        }
                        choice group-format {
                          mandatory true;
                          description
                            "Choice for multicast group format.";
                          case group-prefix {
                            leaf group-address {
                              type inet:ip-prefix;
                              description
                                "A single multicast group prefix.";
                            }
                          }
                          case startend {
                            leaf group-start {
                              type inet:ip-address;
                              description
                                "The first multicast group address in
                                 the multicast group address range.";
                            }
                            leaf group-end {
                              type inet:ip-address;
                              description
                                "The last multicast group address in
                                 the multicast group address range.";
                            }
                          }
                        }
                      }
                    }
                  }
                }
                container rp-discovery {
                  description
                    "RP discovery parameters.";
                  leaf rp-discovery-type {
                    type identityref {
                      base vpn-common:multicast-rp-discovery-type;
                    }
                    default "vpn-common:static-rp";
                    description
                      "Type of RP discovery used.";
                  }
                  container bsr-candidates {
                    when "derived-from-or-self(../rp-discovery-type, "
                       + "'vpn-common:bsr-rp')" {
                      description
                        "Only applicable if discovery type is BSR-RP.";
                    }
                    description
                      "Container for List of Customer BSR candidate's
                       addresses.";
                    leaf-list bsr-candidate-address {
                      type inet:ip-address;
                      description
                        "Specifies the address of candidate Bootstrap
                         Router (BSR).";
                    }
                  }
                }
              }
              container msdp {
                if-feature "msdp";
                description
                  "Includes MSDP-related parameters.";
                leaf peer {
                  type inet:ip-address;
                  description
                    "Indicates the IP address of the MSDP peer.";
                }
                leaf local-address {
                  type inet:ip-address;
                  description
                    "Indicates the IP address of the local end.
                     This local address must be configured on
                     the node.";
                }
                uses vpn-common:service-status;
              }
              container igmp {
                if-feature "vpn-common:igmp and vpn-common:ipv4";
                description
                  "Includes IGMP-related parameters.";
                list static-group {
                  key "group-addr";
                  description
                    "Multicast static source/group associated to the
                     IGMP session";
                  leaf group-addr {
                    type rt-types:ipv4-multicast-group-address;
                    description
                      "Multicast group IPv4 addresss.";
                  }
                  leaf source-addr {
                    type rt-types:ipv4-multicast-source-address;
                    description
                      "Multicast source IPv4 addresss.";
                  }
                }
                leaf max-groups {
                  type uint32;
                  description
                    "Indicates the maximum groups.";
                }
                leaf max-entries {
                  type uint32;
                  description
                    "Indicates the maximum IGMP entries.";
                }
                leaf version {
                  type identityref {
                    base vpn-common:igmp-version;
                  }
                  default "vpn-common:igmpv2";
                  description
                    "Version of the IGMP.";
                }
                uses vpn-common:service-status;
              }
              container mld {
                if-feature "vpn-common:mld and vpn-common:ipv6";
                description
                  "Includes MLD-related parameters.";
                list static-group {
                  key "group-addr";
                  description
                    "Multicast static source/group associated to the
                     MLD session";
                  leaf group-addr {
                    type rt-types:ipv6-multicast-group-address;
                    description
                      "Multicast group IPv6 addresss.";
                  }
                  leaf source-addr {
                    type rt-types:ipv6-multicast-source-address;
                    description
                      "Multicast source IPv6 addresss.";
                  }
                }
                leaf max-groups {
                  type uint32;
                  description
                    "Indicates the maximum groups.";
                }
                leaf max-entries {
                  type uint32;
                  description
                    "Indicates the maximum MLD entries.";
                }
                leaf version {
                  type identityref {
                    base vpn-common:mld-version;
                  }
                  default "vpn-common:mldv2";
                  description
                    "Version of the MLD protocol.";
                }
                uses vpn-common:service-status;
              }
              container pim {
                if-feature "vpn-common:pim";
                description
                  "Only applies when protocol type is PIM.";
                leaf hello-interval {
                  type uint8;
                  units "seconds";
                  default "30";
                  description
                    "PIM hello-messages interval.";
                }
                leaf dr-priority {
                  type uint16;
                  description
                    "Value to increase or decrease the
                     chances of a given DR being elected.";
                }
                uses vpn-common:service-status;
              }
            }
            uses vpn-common:service-status;
            container vpn-network-accesses {
              description
                "List of network accesses.";
              list vpn-network-access {
                key "id";
                description
                  "List of network accesses.";
                leaf id {
                  type vpn-common:vpn-id;
                  description
                    "Identifier for the network access.";
                }
                leaf port-id {
                  type vpn-common:vpn-id;
                  description
                    "Identifier for the interface.";
                }
                leaf description {
                  type string;
                  description
                    "Textual description of the network access.";
                }
                leaf vpn-network-access-type {
                  type identityref {
                    base vpn-common:site-network-access-type;
                  }
                  default "vpn-common:point-to-point";
                  description
                    "Describes the type of connection, e.g.,
                     point-to-point or multipoint.";
                }
                uses vpn-common:service-status;
                container connection {
                  description
                    "Encapsulation types.";
                  leaf encapsulation-type {
                    type identityref {
                      base vpn-common:encapsulation-type;
                    }
                    default "vpn-common:untagged-int";
                    description
                      "Encapsulation type. By default, the encapsulation
                       type is set to 'untagged'.";
                  }
                  container logical-interface {
                    description
                      "Reference of a logical interface
                       type.";
                    leaf peer-reference {
                      type uint32;
                      description
                        "Specifies the associated logical peer
                         interface.";
                    }
                  }
                  container tagged-interface {
                    description
                      "Container for tagged interfaces.";
                    leaf type {
                      type identityref {
                        base vpn-common:encapsulation-type;
                      }
                      default "vpn-common:priority-tagged";
                      description
                        "Tagged interface type. By default, the type of
                         the tagged interface is 'priority-tagged'.";
                    }
                    container dot1q-vlan-tagged {
                      when "derived-from-or-self(../type, "
                         + "'vpn-common:dot1q')" {
                        description
                          "Only applies when the type of the
                           tagged interface is 'dot1q'.";
                      }
                      if-feature "vpn-common:dot1q";
                      description
                        "Tagged interface.";
                      leaf tag-type {
                        type identityref {
                          base vpn-common:tag-type;
                        }
                        default "vpn-common:c-vlan";
                        description
                          "Tag type. By default, the tag type is
                           'c-vlan'.";
                      }
                      leaf cvlan-id {
                        type uint16;
                        description
                          "VLAN identifier.";
                      }
                    }
                    container priority-tagged {
                      when "derived-from-or-self(../type, "
                         + "'vpn-common:priority-tagged')" {
                        description
                          "Only applies when the type of the
                           tagged interface is 'priority-tagged'.";
                      }
                      description
                        "Priority tagged.";
                      leaf tag-type {
                        type identityref {
                          base vpn-common:tag-type;
                        }
                        default "vpn-common:c-vlan";
                        description
                          "Tag type. By default, the tag type is
                           'c-vlan'.";
                      }
                    }
                    container qinq {
                      when "derived-from-or-self(../type, "
                         + "'vpn-common:qinq')" {
                        description
                          "Only applies when the type of the tagged
                           interface is 'qinq'.";
                      }
                      if-feature "vpn-common:qinq";
                      description
                        "QinQ.";
                      leaf tag-type {
                        type identityref {
                          base vpn-common:tag-type;
                        }
                        default "vpn-common:c-s-vlan";
                        description
                          "Tag type. By default, the tag type is
                           'c-s-vlan'.";
                      }
                      leaf svlan-id {
                        type uint16;
                        mandatory true;
                        description
                          "SVLAN identifier.";
                      }
                      leaf cvlan-id {
                        type uint16;
                        mandatory true;
                        description
                          "CVLAN identifier.";
                      }
                    }
                    container qinany {
                      when "derived-from-or-self(../type, "
                         + "'vpn-common:qinany')" {
                        description
                          "Only applies when the type of the
                           tagged interface is 'qinany'.";
                      }
                      if-feature "vpn-common:qinany";
                      description
                        "Container for QinAny.";
                      leaf tag-type {
                        type identityref {
                          base vpn-common:tag-type;
                        }
                        default "vpn-common:s-vlan";
                        description
                          "Tag type. By default, the tag type is
                           's-vlan'.";
                      }
                      leaf svlan-id {
                        type uint16;
                        mandatory true;
                        description
                          "Service VLAN ID.";
                      }
                    }
                    container vxlan {
                      when "derived-from-or-self(../type, "
                         + "'vpn-common:vxlan')" {
                        description
                          "Only applies when the type of the
                           tagged interface is 'vxlan'.";
                      }
                      if-feature "vpn-common:vxlan";
                      description
                        "QinQ.";
                      leaf vni-id {
                        type uint32;
                        mandatory true;
                        description
                          "VXLAN Network Identifier (VNI).";
                      }
                      leaf peer-mode {
                        type identityref {
                          base vpn-common:vxlan-peer-mode;
                        }
                        default "vpn-common:static-mode";
                        description
                          "Specifies the VXLAN access mode. By default,
                           the peer mode is set to 'static-mode'.";
                      }
                      list peer-list {
                        key "peer-ip";
                        description
                          "List of peer IP addresses.";
                        leaf peer-ip {
                          type inet:ip-address;
                          description
                            "Peer IP address.";
                        }
                      }
                    }
                  }
                  container bearer {
                    description
                      "Defines physical properties of a site
                       attachment.";
                    leaf bearer-reference {
                      if-feature "vpn-common:bearer-reference";
                      type string;
                      description
                        "This is an internal reference for the service
                         provider.";
                    }
                    container pseudowire {
                      description
                        "Pseudowire termination parameters";
                      leaf vcid {
                        type uint32;
                        description
                          "Indicates a PW or VC identifier.";
                      }
                      leaf far-end {
                        type union {
                          type uint32;
                          type inet:ip-address;
                        }
                        description
                          "SDP/Far End/LDP neighbour reference.";
                      }
                    }
                    container vpls {
                      description
                        "Pseudowire termination parameters";
                      leaf vcid {
                        type union {
                          type uint32;
                          type string;
                        }
                        description
                          "VCID identifier, IRB/RVPPLs interface
                           supported using string format.";
                      }
                      leaf far-end {
                        type union {
                          type uint32;
                          type inet:ip-address;
                        }
                        description
                          "SDP/Far End/LDP Neighbour reference.";
                      }
                    }
                  }
                }
                container ip-connection {
                  description
                    "Defines connection parameters.";
                  container ipv4 {
                    if-feature "vpn-common:ipv4";
                    description
                      "IPv4-specific parameters.";
                    leaf local-address {
                      type inet:ipv4-prefix;
                      description
                        "This address is used at provider side.";
                    }
                    leaf address-allocation-type {
                      type identityref {
                        base address-allocation-type;
                      }
                      must "not(derived-from-or-self(current(), "
                         + "'slaac') or derived-from-or-self(current(),"
                         + " 'provider-dhcp-slaac'))" {
                        error-message
                          "SLAAC is only applicable to IPv6.";
                      }
                      description
                        "Defines how addresses are allocated to the
                         peer site.

                         If there is no value for the address
                         allocation type, then IPv4 is not enabled.";
                    }
                    choice allocation-type {
                      description
                        "Choice of the IPv4 address allocation.";
                      case provider-dhcp {
                        when "derived-from-or-self(./address-"
                           + "allocation-type, 'provider-dhcp')" {
                          description
                            "Only applies when addresses are allocated
                             by DHCP.";
                        }
                        description
                          "DHCP allocated addresses related
                           parameters.";
                        leaf dhcp-server-enable {
                          type boolean;
                          default "true";
                          description
                            "Enables a DHCP service on this access.
                             The following information are passed to
                             the provider's DHCP server.";
                        }
                        choice address-assign {
                          default "number";
                          description
                            "Choice for how IPv4 addresses are
                             assigned.";
                          case number {
                            leaf number-of-dynamic-address {
                              type uint16;
                              default "1";
                              description
                                "Specifies the number of IP addresses
                                 to be assigned to the customer on this
                                 access.";
                            }
                          }
                          case explicit {
                            container customer-addresses {
                              description
                                "Container for customer addresses to be
                                 allocated using DHCP.";
                              list address-group {
                                key "group-id";
                                description
                                  "Describes IP addresses to be
                                   allocated by DHCP.

                                   When only start-address or only
                                   end-address is present, it
                                   represents a single address.

                                   When both start-address and
                                   end-address are specified, it
                                   implies a range inclusive of
                                   both addresses.  If no address
                                   is specified, it implies customer
                                   addresses group is not supported.";
                                leaf group-id {
                                  type string;
                                  description
                                    "Group-id for the address range from
                                     start-address to end-address.";
                                }
                                leaf start-address {
                                  type inet:ipv4-address;
                                  description
                                    "Indicates the first address in
                                     the group.";
                                }
                                leaf end-address {
                                  type inet:ipv4-address;
                                  description
                                    "Indicates the last address in the
                                     group.";
                                }
                              }
                            }
                          }
                        }
                      }
                      case dhcp-relay {
                        when "derived-from-or-self(./address-allocation"
                           + "-type, 'provider-dhcp-relay')" {
                          description
                            "Only applies when the provider is required
                             to implement DHCP relay function.";
                        }
                        description
                          "DHCP relay provided by operator.";
                        leaf dhcp-relay-enable {
                          type boolean;
                          default "true";
                          description
                            "Enables the DHCP relay function for this
                             access.";
                        }
                        container customer-dhcp-servers {
                          description
                            "Container for list of customer
                             DHCP servers.";
                          leaf-list server-ip-address {
                            type inet:ipv4-address;
                            description
                              "IP address of customer DHCP server.";
                          }
                        }
                      }
                      case static-addresses {
                        when "derived-from-or-self(./address-allocation"
                           + "-type, 'static-address')" {
                          description
                            "Only applies when address allocation
                             type is static.";
                        }
                        description
                          "Describes IPv4 addresses used.";
                        leaf primary-address {
                          type leafref {
                            path "../address/address-id";
                          }
                          description
                            "Primary address of the connection.";
                        }
                        list address {
                          key "address-id";
                          description
                            "Describes IPv4 addresses used.";
                          leaf address-id {
                            type string;
                            description
                              "Used static IPv4 address.";
                          }
                          leaf customer-address {
                            type inet:ipv4-address;
                            description
                              "IPv4 address at the customer side.";
                          }
                        }
                      }
                    }
                  }
                  container ipv6 {
                    if-feature "vpn-common:ipv6";
                    description
                      "IPv6-specific parameters.";
                    leaf local-address {
                      type inet:ipv6-prefix;
                      description
                        "Address of the provider side.";
                    }
                    leaf address-allocation-type {
                      type identityref {
                        base address-allocation-type;
                      }
                      description
                        "Defines how addresses are allocated.
                         If there is no value for the address
                         allocation type, then IPv6 is
                         not enabled.";
                    }
                    choice allocation-type {
                      description
                        "IPv6 allocation type.";
                      case provider-dhcp {
                        when "derived-from-or-self(./address-allo"
                           + "cation-type, 'provider-dhcp') "
                           + "or derived-from-or-self(./address-allo"
                           + "cation-type, 'provider-dhcp-slaac')" {
                          description
                            "Only applies when addresses are
                             allocated by DHCPv6.";
                        }
                        description
                          "DHCPv6 allocated addresses related
                           parameters.";
                        leaf dhcp-server-enable {
                          type boolean;
                          default "true";
                          description
                            "Enables DHCPv6 service for this access.";
                        }
                        choice address-assign {
                          default "number";
                          description
                            "Choice for the way to assign IPv6
                             prefixes.";
                          case number {
                            leaf number-of-dynamic-address {
                              type uint16;
                              default "1";
                              description
                                "Describes the number of IPv6 prefixes
                                 that are allocated to the customer
                                 on this access.";
                            }
                          }
                          case explicit {
                            container customer-addresses {
                              description
                                "Container for customer IPv6 addresses
                                 allocated by DHCPv6.";
                              list address-group {
                                key "group-id";
                                description
                                  "Describes IPv6 addresses allocated
                                   by DHCPv6.

                                   When only start-address or only
                                   end-address is present, it
                                   represents a single address.

                                   When both start-address and
                                   end-address are specified, it
                                   implies a range inclusive of
                                   both addresses.

                                   If no address is specified, it
                                   implies customer addresses group
                                   is not supported.";
                                leaf group-id {
                                  type string;
                                  description
                                    "Group-id for the address range
                                     from identified by start-address
                                     and end-address.";
                                }
                                leaf start-address {
                                  type inet:ipv6-address;
                                  description
                                    "Indicates the first address.";
                                }
                                leaf end-address {
                                  type inet:ipv6-address;
                                  description
                                    "Indicates the last address.";
                                }
                              }
                            }
                          }
                        }
                      }
                      case dhcp-relay {
                        when "derived-from-or-self(./address-allo"
                           + "cation-type, 'provider-dhcp-relay')" {
                          description
                            "Only applies when the provider is required
                             to implement DHCP relay function.";
                        }
                        description
                          "DHCP relay provided by operator.";
                        leaf dhcp-relay-enable {
                          type boolean;
                          default "true";
                          description
                            "Enables the DHCP relay function for this
                             access.";
                        }
                        container customer-dhcp-servers {
                          description
                            "Container for list of customer DHCP
                             servers.";
                          leaf-list server-ip-address {
                            type inet:ipv6-address;
                            description
                              "This node contains the IP address of
                               the customer DHCP server.  If the DHCP
                               relay function is implemented by the
                               provider, this node contains the
                               configured value.";
                          }
                        }
                      }
                      case static-addresses {
                        when "derived-from-or-self(./address-allocation"
                           + "-type, 'static-address')" {
                          description
                            "Only applies when protocol allocation type
                             is static.";
                        }
                        description
                          "IPv6-specific parameters for static
                           allocation.";
                        leaf primary-address {
                          type leafref {
                            path "../address/prefix-id";
                          }
                          description
                            "Principal address of the connection";
                        }
                        list address {
                          key "prefix-id";
                          description
                            "Describes IPv6 prefixes used.";
                          leaf prefix-id {
                            type string;
                            description
                              "An identifier of an IPv6 prefix.";
                          }
                          leaf customer-prefix {
                            type inet:ipv6-prefix;
                            description
                              "An IPv6 prefix of the customer side.";
                          }
                        }
                      }
                    }
                  }
                }
                container routing-protocols {
                  description
                    "Defines routing protocols.";
                  list routing-protocol {
                    key "id";
                    description
                      "List of routing protocols used on
                       the CE/PE link.  This list can be augmented.";
                    leaf id {
                      type string;
                      description
                        "Unique identifier for routing protocol.";
                    }
                    leaf type {
                      type identityref {
                        base vpn-common:routing-protocol-type;
                      }
                      description
                        "Type of routing protocol.";
                    }
                    list routing-profiles {
                      key "id";
                      description
                        "Routing profiles.";
                      leaf id {
                        type leafref {
                          path "/l3vpn-ntw/vpn-profiles"
                             + "/valid-provider-identifiers"
                             + "/routing-profile-identifier/id";
                        }
                        description
                          "Routing profile to be used.";
                      }
                      leaf type {
                        type identityref {
                          base vpn-common:ie-type;
                        }
                        description
                          "Import, export or both.";
                      }
                    }
                    container static {
                      when "derived-from-or-self(../type, "
                         + "'vpn-common:static')" {
                        description
                          "Only applies when protocol is static.";
                      }
                      description
                        "Configuration specific to static routing.";
                      container cascaded-lan-prefixes {
                        description
                          "LAN prefixes from the customer.";
                        list ipv4-lan-prefixes {
                          if-feature "vpn-common:ipv4";
                          key "lan next-hop";
                          description
                            "List of LAN prefixes for the site.";
                          leaf lan {
                            type inet:ipv4-prefix;
                            description
                              "LAN prefixes.";
                          }
                          leaf lan-tag {
                            type string;
                            description
                              "Internal tag to be used in VPN
                               policies.";
                          }
                          leaf next-hop {
                            type union {
                              type inet:ip-address;
                              type predefined-next-hop;
                            }
                            description
                              "The next-hop that is to be used
                               for the static route. This may be
                               specified as an IP address, an interface,
                               or a pre-defined next-hop type (e.g.,
                               discard or local-link).";
                          }
                          leaf bfd-enable {
                            if-feature "vpn-common:bfd";
                            type boolean;
                            description
                              "Enables BFD.";
                          }
                          leaf metric {
                            type uint32;
                            description
                              "Indicates the metric associated with
                               the static route.";
                          }
                          leaf preference {
                            type uint32;
                            description
                              "Indicates the preference of the static
                               routes.";
                          }
                          uses vpn-common:service-status;
                        }
                        list ipv6-lan-prefixes {
                          if-feature "vpn-common:ipv6";
                          key "lan next-hop";
                          description
                            "List of LAN prefixes for the site.";
                          leaf lan {
                            type inet:ipv6-prefix;
                            description
                              "LAN prefixes.";
                          }
                          leaf lan-tag {
                            type string;
                            description
                              "Internal tag to be used in VPN
                               policies.";
                          }
                          leaf next-hop {
                            type union {
                              type inet:ip-address;
                              type predefined-next-hop;
                            }
                            description
                              "The next-hop that is to be used for the
                               static route. This may be specified as
                               an IP address, an interface, or a
                               pre-defined next-hop type (e.g.,
                               discard or local-link).";
                          }
                          leaf bfd-enable {
                            if-feature "vpn-common:bfd";
                            type boolean;
                            description
                              "Enables BFD.";
                          }
                          leaf metric {
                            type uint32;
                            description
                              "Indicates the metric associated with
                               the static route.";
                          }
                          leaf preference {
                            type uint32;
                            description
                              "Indicates the preference associated
                               with the static route.";
                          }
                          uses vpn-common:service-status;
                        }
                      }
                    }
                    container bgp {
                      when "derived-from-or-self(../type, "
                         + "'vpn-common:bgp')" {
                        description
                          "Only applies when protocol is BGP.";
                      }
                      if-feature "vpn-common:rtg-bgp";
                      description
                        "BGP-specific configuration.";
                      leaf description {
                        type string;
                        description
                          "Includes a description of the BGP session.

                           Such description is meant to be used for
                           diagnosis purposes. The semantic of the
                           description is local to an
                           implementation.";
                      }
                      leaf local-autonomous-system {
                        type inet:as-number;
                        description
                          "Is set to the ASN to override a peers' ASN
                           if such feature is requested by the
                           Customer.";
                      }
                      leaf peer-autonomous-system {
                        type inet:as-number;
                        mandatory true;
                        description
                          "Indicates the Customer's AS Number (ASN) in
                           case the Customer requests BGP routing.";
                      }
                      leaf address-family {
                        type identityref {
                          base vpn-common:address-family;
                        }
                        description
                          "This node contains the address families to be
                           activated. Dual-stack means that both IPv4
                           and IPv6 will be activated.";
                      }
                      leaf-list neighbor {
                        type inet:ip-address;
                        description
                          "IP address(es) of the BGP neighbor. IPv4
                           and IPv6 neighbors may be indicated if
                           two sessions will be used for IPv4 and
                           IPv6.";
                      }
                      leaf multihop {
                        type uint8;
                        description
                          "Describes the number of IP hops allowed
                           between a given BGP neighbor and the PE.";
                      }
                      leaf as-override {
                        type boolean;
                        default "false";
                        description
                          "Defines whether AS override is enabled,
                           i.e., replace the ASN of the customer
                           specified in the AS Path attribute with
                           the local ASN.";
                      }
                      leaf default-route {
                        type boolean;
                        default "false";
                        description
                          "Defines whether default route(s) can be
                           advertised to its peer. If set, the
                           default route(s) is advertised to its
                           peer.";
                      }
                      leaf site-of-origin {
                        when "../address-family = 'vpn-common:ipv4' or "
                           + "'vpn-common:dual-stack'" {
                          description
                            "Only applies if IPv4 is activated.";
                        }
                        type rt-types:route-origin;
                        description
                          "The Site of Origin attribute is encoded as
                           a Route Origin Extended Community. It is
                           meant to uniquely identify the set of routes
                           learned from a site via a particular CE/PE
                           connection and is used to prevent routing
                           loops.";
                        reference
                          "RFC4364, Section 7";
                      }
                      leaf ipv6-site-of-origin {
                        when "../address-family = 'vpn-common:ipv6' or "
                           + "'vpn-common:dual-stack'" {
                          description
                            "Only applies if IPv6 is activated.";
                        }
                        type rt-types:ipv6-route-origin;
                        description
                          "IPv6 Route Origins are IPv6 Address Specific
                           BGP Extended that are meant to the Site of
                           Origin for VRF information.";
                        reference
                          "RFC 5701: IPv6 Address Specific BGP Extended
                                     Community Attribute";
                      }
                      container bgp-max-prefix {
                        description
                          "Controls the behavior when a prefix
                           maximum is reached.";
                        leaf max-prefix {
                          type uint32;
                          default "5000";
                          description
                            "Indicates the maximum number of BGP
                             prefixes allowed in the BGP session.

                             It allows to control how many prefixes
                             can be received from a neighbor.

                             If the limit is exceeded, the action
                             indicated in violate-action will be
                             followed.";
                          reference
                            "RFC4271, Section 8.2.2.";
                        }
                        leaf warning-threshold {
                          type decimal64 {
                            fraction-digits 5;
                            range "0..100";
                          }
                          units "percent";
                          default "75";
                          description
                            "When this value is reached, a warning
                             notification will be triggered.";
                        }
                        leaf violate-action {
                          type enumeration {
                            enum warning {
                              description
                                "Only a warning message is sent to
                                 the peer when the limit is
                                 exceeded.";
                            }
                            enum discard-extra-paths {
                              description
                                "Discards extra paths when the
                                 limit is exceeded.";
                            }
                            enum restart {
                              description
                                "Restarts after a time interval.";
                            }
                          }
                          description
                            "BGP neighbour max-prefix violate
                             action";
                        }
                        leaf restart-interval {
                          type uint16;
                          units "minutes";
                          description
                            "Time interval (min) after which the
                             BGP session will be reestablished.";
                        }
                      }
                      container bgp-timers {
                        description
                          "Includes two BGP timers that can be
                           customized when building a VPN service
                           with BGP used as CE-PE routing
                           protocol.";
                        leaf keep-alive {
                          type uint16 {
                            range "0..21845";
                          }
                          units "seconds";
                          default "30";
                          description
                            "This timer indicates the KEEPALIVE
                             messages'  frequency between a PE
                             and a BGP peer.

                             If set to '0', it indicates KEEPALIVE
                             messages are disabled.

                             It is suggested that the maximum time
                             between  KEEPALIVEmessages would be
                             one third of the Hold Time interval.";
                          reference
                            "Section 4.4 of RFC 4271";
                        }
                        leaf hold-time {
                          type uint16 {
                            range "0 | 3..65535";
                          }
                          units "seconds";
                          default "90";
                          description
                            "It indicates the maximum number of
                             seconds that may elapse between the
                             receipt of successive KEEPALIVE
                             and/or UPDATE   messages from the peer.

                             The Hold Time must be either zero or
                             at least three seconds.";
                          reference
                            "Section 4.2 of RFC 4271";
                        }
                      }
                      container security {
                        description
                          "Container for BGP security parameters
                           between a PE and a CE.";
                        leaf enable {
                          type boolean;
                          default "false";
                          description
                            "Enables or disables authentication.";
                        }
                        container keying-material {
                          when "../enable = 'true'";
                          description
                            "Container for describing how a BGP routing
                             session is to be secured between a PE and
                             a CE.";
                          choice option {
                            description
                              "Choice of authentication options.";
                            case tcp-ao {
                              description
                                "Uses TCP-Authentication Option
                                 (TCP-AO).";
                              reference
                                "RFC 5925: The TCP Authentication
                                           Option.";
                              leaf enable-tcp-ao {
                                type boolean;
                                description
                                  "Enables TCP-AO.";
                              }
                              leaf ao-keychain {
                                type key-chain:key-chain-ref;
                                description
                                  "Reference to the TCP-AO key chain.";
                                reference
                                  "RFC 8177: YANG Key Chain.";
                              }
                            }
                            case md5 {
                              description
                                "Uses MD5 to secure the session.";
                              reference
                                "Section 13.2 of RFC 4364";
                              leaf md5-keychain {
                                type key-chain:key-chain-ref;
                                description
                                  "Reference to the MD5 key chain.";
                                reference
                                  "RFC 8177: YANG Key Chain.";
                              }
                            }
                            case explicit {
                              leaf key-id {
                                type uint32;
                                description
                                  "Key Identifier";
                              }
                              leaf key {
                                type string;
                                description
                                  "OSPF authentication key.";
                              }
                              leaf crypto-algorithm {
                                type identityref {
                                  base key-chain:crypto-algorithm;
                                }
                                description
                                  "Indicates the cryptographic algorithm
                                   associated with the key.";
                              }
                            }
                            case ipsec {
                              description
                                "Specifies a reference to an IKE
                                 Security Association (SA).";
                              leaf sa {
                                type string;
                                description
                                  "Indicates the name of the SA.";
                              }
                            }
                          }
                        }
                      }
                      uses vpn-common:service-status;
                    }
                    container ospf {
                      when "derived-from-or-self(../type, "
                         + "'vpn-common:ospf')" {
                        description
                          "Only applies when protocol is OSPF.";
                      }
                      if-feature "vpn-common:rtg-ospf";
                      description
                        "OSPF-specific configuration.";
                      leaf address-family {
                        type identityref {
                          base vpn-common:address-family;
                        }
                        description
                          "Indicates whether IPv4, IPv6, or
                           both are to be activated.";
                      }
                      leaf area-id {
                        type yang:dotted-quad;
                        mandatory true;
                        description
                          "Area ID.";
                      }
                      leaf metric {
                        type uint16;
                        default "1";
                        description
                          "Metric of the PE-CE link. It is used
                           in the routing state calculation and
                           path selection.";
                      }
                      container sham-links {
                        if-feature "vpn-common:rtg-ospf-sham-link";
                        description
                          "List of sham links.";
                        list sham-link {
                          key "target-site";
                          description
                            "Creates a sham link with another site.";
                          leaf target-site {
                            type vpn-common:vpn-id;
                            description
                              "Target site for the sham link connection.
                               The site is referred to by its ID.";
                          }
                          leaf metric {
                            type uint16;
                            default "1";
                            description
                              "Metric of the sham link.  It is used in
                               the routing state calculation and path
                               selection.  The default value is set
                               to 1.";
                          }
                        }
                      }
                      leaf max-lsa {
                        type uint32 {
                          range "1..4294967294";
                        }
                        description
                          "Maximum number of allowed LSAs OSPF.";
                      }
                      container security {
                        description
                          "Authentication configuration.";
                        leaf enable {
                          type boolean;
                          default "false";
                          description
                            "Enables or disables authentication.";
                        }
                        container keying-material {
                          when "../enable = 'true'";
                          description
                            "Container for describing how an OSPF
                             session is to be secured between a CE
                             and a PE.";
                          choice option {
                            description
                              "Options for OSPF authentication.";
                            case auth-key-chain {
                              leaf key-chain {
                                type key-chain:key-chain-ref;
                                description
                                  "key-chain name.";
                              }
                            }
                            case auth-key-explicit {
                              leaf key-id {
                                type uint32;
                                description
                                  "Key Identifier";
                              }
                              leaf key {
                                type string;
                                description
                                  "OSPF authentication key.";
                              }
                              leaf crypto-algorithm {
                                type identityref {
                                  base key-chain:crypto-algorithm;
                                }
                                description
                                  "Indicates the cryptographic algorithm
                                   associated with the key.";
                              }
                            }
                            case ipsec {
                              leaf sa {
                                type string;
                                description
                                  "Indicates the name of the SA.";
                              }
                            }
                          }
                        }
                      }
                      uses vpn-common:service-status;
                    }
                    container isis {
                      when "derived-from-or-self(../type, "
                         + "'vpn-common:isis')" {
                        description
                          "Only applies when protocol is IS-IS.";
                      }
                      if-feature "vpn-common:rtg-isis";
                      description
                        "IS-IS specific configuration.";
                      leaf address-family {
                        type identityref {
                          base vpn-common:address-family;
                        }
                        description
                          "Indicates whether IPv4, IPv6, or both
                           are to be activated.";
                      }
                      leaf area-address {
                        type yang:dotted-quad;
                        mandatory true;
                        description
                          "Area address.";
                      }
                      leaf level {
                        type identityref {
                          base vpn-common:isis-level;
                        }
                        description
                          "Can be level1, level2, or level1-2.";
                      }
                      leaf metric {
                        type uint16;
                        default "1";
                        description
                          "Metric of the PE-CE link.  It is used
                           in the routing state calculation and
                           path selection.";
                      }
                      leaf mode {
                        type enumeration {
                          enum active {
                            description
                              "Interface sends or receives IS-IS
                               protocol control packets.";
                          }
                          enum passive {
                            description
                              "Suppresses the sending of IS-IS
                               updates through the specified
                               interface.";
                          }
                        }
                        default "active";
                        description
                          "IS-IS interface mode type.";
                      }
                      container security {
                        description
                          "Authentication configuration.";
                        leaf enable {
                          type boolean;
                          default "false";
                          description
                            "Enables or disables authentication.";
                        }
                        container keying-material {
                          when "../enable = 'true'";
                          description
                            "Container for describing how an IS-IS
                             session is to be secured between a CE
                             and a PE.";
                          choice option {
                            description
                              "Options for IS-IS authentication.";
                            case auth-key-chain {
                              leaf key-chain {
                                type key-chain:key-chain-ref;
                                description
                                  "key-chain name.";
                              }
                            }
                            case auth-key-explicit {
                              leaf key-id {
                                type uint32;
                                description
                                  "Key Identifier";
                              }
                              leaf key {
                                type string;
                                description
                                  "IS-IS authentication key.";
                              }
                              leaf crypto-algorithm {
                                type identityref {
                                  base key-chain:crypto-algorithm;
                                }
                                description
                                  "Indicates the cryptographic algorithm
                                   associated with the key.";
                              }
                            }
                          }
                        }
                      }
                      uses vpn-common:service-status;
                    }
                    container rip {
                      when "derived-from-or-self(../type, "
                         + "'vpn-common:rip')" {
                        description
                          "Only applies when the protocol is RIP.
                           For IPv4, the model assumes that RIP
                           version 2 is used.";
                      }
                      if-feature "vpn-common:rtg-rip";
                      description
                        "Configuration specific to RIP routing.";
                      leaf address-family {
                        type identityref {
                          base vpn-common:address-family;
                        }
                        description
                          "Indicates whether IPv4, IPv6, or both
                           address families are to be activated.";
                      }
                      uses vpn-common:service-status;
                    }
                    container vrrp {
                      when "derived-from-or-self(../type, "
                         + "'vpn-common:vrrp')" {
                        description
                          "Only applies when protocol is VRRP.";
                      }
                      if-feature "vpn-common:rtg-vrrp";
                      description
                        "Configuration specific to VRRP.";
                      leaf address-family {
                        type identityref {
                          base vpn-common:address-family;
                        }
                        description
                          "Indicates whether IPv4, IPv6, or both
                           address families are to be enabled.";
                      }
                      leaf vrrp-group {
                        type uint8 {
                          range "1..255";
                        }
                        description
                          "Includes the VRRP group identifier.";
                      }
                      leaf backup-peer {
                        type inet:ip-address;
                        description
                          "Indicates the IP address of the peer.";
                      }
                      leaf priority {
                        type uint8 {
                          range "1..254";
                        }
                        default "100";
                        description
                          "Sets the local priority of the VRRP
                           speaker.";
                      }
                      leaf ping-reply {
                        type boolean;
                        description
                          "Controls whether the VRRP speaker should
                           answer to ping requests.";
                      }
                      uses vpn-common:service-status;
                    }
                  }
                }
                container oam {
                  description
                    "Defines the Operations, Administration,
                     and Maintenance (OAM) mechanisms used.

                     BFD is set as a fault detection mechanism,
                     but other mechanisms can be defined in the
                     future.";
                  container bfd {
                    if-feature "vpn-common:bfd";
                    description
                      "Container for BFD.";
                    choice holdtime {
                      default "fixed";
                      description
                        "Choice for holdtime flavor.";
                      case fixed {
                        leaf fixed-value {
                          type uint32;
                          units "msec";
                          description
                            "Expected BFD holdtime.

                             The customer may impose some fixed
                             values for the holdtime period if the
                             provider allows the customer use this
                             function.

                             If the provider doesn't allow the
                             customer to use this function,
                             the fixed-value will not be set.";
                        }
                      }
                      case profile {
                        description
                          "Well-known SP profile.";
                        leaf profile-name {
                          type leafref {
                            path "/l3vpn-ntw/vpn-profiles"
                               + "/valid-provider-identifiers"
                               + "/bfd-profile-identifier/id";
                          }
                          description
                            "Well-known service provider profile name.

                             The provider can propose some profiles
                             to the customer, depending on the
                             service level the customer wants to
                             achieve.";
                        }
                      }
                    }
                    container authentication {
                      presence "Enables BFD authentication";
                      description
                        "Parameters for BFD authentication.";
                      leaf key-chain {
                        type key-chain:key-chain-ref;
                        description
                          "Name of the key-chain.";
                      }
                      leaf meticulous {
                        type boolean;
                        description
                          "Enables meticulous mode.";
                        reference
                          "Section 6.7 of RFC 5880";
                      }
                    }
                    uses vpn-common:service-status;
                  }
                }
                container security {
                  description
                    "Site-specific security parameters.";
                  container encryption {
                    if-feature "vpn-common:encryption";
                    description
                      "Container for CE-PE security encryption.";
                    leaf enabled {
                      type boolean;
                      default "false";
                      description
                        "If true, traffic encryption on the
                         connection is required. It is
                         disabled, otherwise.";
                    }
                    leaf layer {
                      when "../enabled = 'true'" {
                        description
                          "Indicates the layer on which encryption
                           is enabled.";
                      }
                      type enumeration {
                        enum layer2 {
                          description
                            "Encryption occurs at Layer 2.";
                        }
                        enum layer3 {
                          description
                            "Encryption occurs at Layer 3.
                             For example, IPsec may be used when
                             a customer requests Layer 3
                             encryption.";
                        }
                      }
                      description
                        "Indicates the layer on which encryption
                         is applied.";
                    }
                  }
                  container encryption-profile {
                    when "../encryption/enabled = 'true'" {
                      description
                        "Indicates the layer on which encryption
                         is enabled.";
                    }
                    description
                      "Container for encryption profile.";
                    choice profile {
                      description
                        "Choice for the encryption profile.";
                      case provider-profile {
                        leaf profile-name {
                          type leafref {
                            path "/l3vpn-ntw/vpn-profiles"
                               + "/valid-provider-identifiers"
                               + "/encryption-profile-identifier/id";
                          }
                          description
                            "Name of the service provider's profile
                             to be applied.";
                        }
                      }
                      case customer-profile {
                        leaf customer-key-chain {
                          type key-chain:key-chain-ref;
                          description
                            "Customer-supplied key chain.";
                        }
                      }
                    }
                  }
                }
                container service {
                  description
                    "Service parameters on the attachment.";
                  leaf input-bandwidth {
                    type uint64;
                    units "bps";
                    mandatory true;
                    description
                      "From the customer site's perspective, the
                       service input bandwidth of the connection
                       or download bandwidth from the SP to
                       the site.";
                  }
                  leaf output-bandwidth {
                    type uint64;
                    units "bps";
                    mandatory true;
                    description
                      "From the customer site's perspective,
                       the service output bandwidth of the
                       connection or upload bandwidth from
                       the site to the SP.";
                  }
                  leaf mtu {
                    type uint16;
                    units "bytes";
                    mandatory true;
                    description
                      "MTU at service level.  If the service is IP,
                       it refers to the IP MTU.  If CsC is enabled,
                       the requested MTU will refer
                       to the MPLS MTU and not to the IP MTU.";
                  }
                  container qos {
                    if-feature "vpn-common:qos";
                    description
                      "QoS configuration.";
                    container qos-classification-policy {
                      description
                        "Configuration of the traffic classification
                         policy.";
                      uses vpn-common:qos-classification-policy;
                    }
                    container qos-action {
                      description
                        "List of QoS action policies.";
                      list rule {
                        key "id";
                        description
                          "List of QoS actions.";
                        leaf id {
                          type string;
                          description
                            "An identifier of the QoS action rule.";
                        }
                        leaf target-class-id {
                          type string;
                          description
                            "Identification of the class of service.
                             This identifier is internal to the
                             administration.";
                        }
                        leaf inbound-rate-limit {
                          type decimal64 {
                            fraction-digits 5;
                            range "0..100";
                          }
                          units "percent";
                          description
                            "Specifies whether/how to rate-limit the
                             inbound traffic matching this QoS policy.
                             It is expressed as a percent of the value
                             that is indicated in 'input-bandwidth'.";
                        }
                        leaf outbound-rate-limit {
                          type decimal64 {
                            fraction-digits 5;
                            range "0..100";
                          }
                          units "percent";
                          description
                            "Specifies whether/how to rate-limit the
                             outbound traffic matching this QoS policy.
                             It is expressed as a percent of the value
                             that is indicated in 'output-bandwidth'.";
                        }
                      }
                    }
                    container qos-profile {
                      description
                        "QoS profile configuration.";
                      list qos-profile {
                        key "profile";
                        description
                          "QoS profile.
                           Can be standard profile or customized
                           profile.";
                        leaf profile {
                          type leafref {
                            path "/l3vpn-ntw/vpn-profiles"
                               + "/valid-provider-identifiers"
                               + "/qos-profile-identifier/id";
                          }
                          description
                            "QoS profile to be used.";
                        }
                        leaf direction {
                          type identityref {
                            base vpn-common:qos-profile-direction;
                          }
                          default "vpn-common:both";
                          description
                            "The direction to which the QoS profile
                             is applied.";
                        }
                      }
                    }
                  }
                  container carrierscarrier {
                    if-feature "vpn-common:carrierscarrier";
                    description
                      "This container is used when the customer
                       provides MPLS-based services.  This is
                       only used in the  case of CsC (i.e., a
                       customer builds an MPLSservice using an
                       IP VPN to carry its traffic).";
                    leaf signalling-type {
                      type enumeration {
                        enum ldp {
                          description
                            "Use LDP as the signalling protocol
                             between the PE and the CE.  In this
                             case, an IGP routing protocol must
                             also be activated.";
                        }
                        enum bgp {
                          description
                            "Use BGP as the signalling protocol
                             between the PE and the CE.
                             In this case, BGP must also be configured
                             as the routing protocol.";
                          reference
                            "RFC 8277: Using BGP to Bind MPLS Labels
                                       to Address Prefixes";
                        }
                      }
                      default "bgp";
                      description
                        "MPLS signalling type.";
                    }
                  }
                  container multicast {
                    if-feature "vpn-common:multicast";
                    description
                      "Multicast parameters for the network
                       access.";
                    leaf access-type {
                      type enumeration {
                        enum receiver-only {
                          description
                            "The peer site only has receivers.";
                        }
                        enum source-only {
                          description
                            "The peer site only has sources.";
                        }
                        enum source-receiver {
                          description
                            "The peer site has both sources and
                             receivers.";
                        }
                      }
                      default "source-receiver";
                      description
                        "Type of multicast site.";
                    }
                    leaf address-family {
                      type identityref {
                        base vpn-common:address-family;
                      }
                      description
                        "Indicates the address family.";
                    }
                    leaf protocol-type {
                      type enumeration {
                        enum host {
                          description
                            "Hosts are directly connected to the
                             provider network.

                             Host protocols such as IGMP or MLD are
                             required.";
                        }
                        enum router {
                          description
                            "Hosts are behind a customer router.
                             PIM will be implemented.";
                        }
                        enum both {
                          description
                            "Some hosts are behind a customer router,
                             and some others are directly connected
                             to the provider network.  Both host and
                             routing protocols must be used.
                             Typically,  IGMP and PIM will be
                             implemented.";
                        }
                      }
                      default "both";
                      description
                        "Multicast protocol type to be used with
                         the customer site.";
                    }
                    leaf remote-source {
                      type boolean;
                      default "false";
                      description
                        "When true, there is no PIM adjacency on
                         the interface.";
                    }
                    container igmp {
                      when "../protocol-type = 'host' and "
                         + "../address-family = 'vpn-common:ipv4' or "
                         + "'vpn-common:dual-stack'";
                      if-feature "vpn-common:igmp";
                      description
                        "Includes IGMP-related parameters.";
                      list static-group {
                        key "group-addr";
                        description
                          "Multicast static source/group associated to
                           to IGMP session";
                        leaf group-addr {
                          type rt-types:ipv4-multicast-group-address;
                          description
                            "Multicast group IPv4 addresss.";
                        }
                        leaf source-addr {
                          type rt-types:ipv4-multicast-source-address;
                          description
                            "Multicast source IPv4 addresss.";
                        }
                      }
                      leaf max-groups {
                        type uint32;
                        description
                          "Indicates the maximum groups.";
                      }
                      leaf max-entries {
                        type uint32;
                        description
                          "Indicates the maximum IGMP entries.";
                      }
                      leaf max-group-sources {
                        type uint32;
                        description
                          "The maximum number of group sources.";
                      }
                      leaf version {
                        type identityref {
                          base vpn-common:igmp-version;
                        }
                        default "vpn-common:igmpv2";
                        description
                          "Version of the IGMP.";
                      }
                      uses vpn-common:service-status;
                    }
                    container mld {
                      when "../protocol-type = 'host' and "
                         + "../address-family = 'vpn-common:ipv6' or "
                         + "'vpn-common:dual-stack'";
                      if-feature "vpn-common:mld";
                      description
                        "Includes MLD-related parameters.";
                      list static-group {
                        key "group-addr";
                        description
                          "Multicast static source/group associated to
                           the MLD session";
                        leaf group-addr {
                          type rt-types:ipv6-multicast-group-address;
                          description
                            "Multicast group IPv6 addresss.";
                        }
                        leaf source-addr {
                          type rt-types:ipv6-multicast-source-address;
                          description
                            "Multicast source IPv6 addresss.";
                        }
                      }
                      leaf max-groups {
                        type uint32;
                        description
                          "Indicates the maximum groups.";
                      }
                      leaf max-entries {
                        type uint32;
                        description
                          "Indicates the maximum MLD entries.";
                      }
                      leaf max-group-sources {
                        type uint32;
                        description
                          "The maximum number of group sources.";
                      }
                      leaf version {
                        type identityref {
                          base vpn-common:mld-version;
                        }
                        default "vpn-common:mldv2";
                        description
                          "Version of the MLD protocol.";
                      }
                      uses vpn-common:service-status;
                    }
                    container pim {
                      when "../protocol-type = 'router'";
                      if-feature "vpn-common:pim";
                      description
                        "Only applies when protocol type is PIM.";
                      leaf priority {
                        type uint8;
                        description
                          "PIM priority definition.";
                      }
                      leaf hello-interval {
                        type uint8;
                        units "seconds";
                        default "30";
                        description
                          "PIM hello-messages interval.";
                      }
                      leaf dr-priority {
                        type uint16;
                        description
                          "Value to increase or decrease the
                           chances of a given DR being elected.";
                      }
                      uses vpn-common:service-status;
                    }
                  }
                }
              }
            }
          }
        }
      }
    }
  }
}
