module flow-base { 
  namespace "urn:ietf:params:xml:ns:yang:ietf-supa-service"; 
  prefix "service"; 

  identity flow { 
    description 
    "Base identity of flow definition."; 
    } 
  container flows { 
    list flow { 
      key "flowId"; 
      leaf flowId { 
        description "uuid for the flow"; 
        config "true"; 
        type string; 
      } 
      leaf flowName { 
        description  
          "Human-readable name for the flow. Might not be 
          unique"; 
        config "true"; 
        type string; 
        mandatory "true"; 
      } 
    } 
  } 
}
