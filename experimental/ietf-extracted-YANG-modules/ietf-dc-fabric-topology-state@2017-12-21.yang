module ietf-dc-fabric-topology-state {

yang-version 1.1;
namespace "urn:ietf:params:xml:ns:yang:ietf-dc-fabric-topology-state";
prefix sfabric;

import ietf-network-state {
    prefix nws;
    reference
    "draft-ietf-i2rs-yang-network-topo-20
    NOTE TO RFC EDITOR:
    (1) Please replace above reference to
    draft-ietf-i2rs-yang-network-topo-20 with RFC
    number when published (i.e. RFC xxxx).
    (2) Please replace the date in the revision statement with the
     date of publication when published.";
}
import ietf-dc-fabric-types {
    prefix fabrictypes;

    reference
    "draft-ietf-i2rs-yang-dc-fabric-network-topology-03
    NOTE TO RFC EDITOR:
    (1) Please replace above reference to draft-ietf-i2rs-yang-dc
    -fabric-network-topology-03 with RFC number when published
    (i.e. RFC xxxx).
    (2) Please replace the data in the revision statement with the
    data of publication when published.";
}
import ietf-dc-fabric-topology {
    prefix fabric;

    reference
    "draft-ietf-i2rs-yang-dc-fabric-network-topology-03
     NOTE TO RFC EDITOR:
     (1) Please replace above reference to draft-ietf-i2rs-yang-dc
     -fabric-network-topology-03 with RFC number when published
     (i.e. RFC xxxx).
     (2) Please replace the data in the revision statement with the
     data of publication when published.";
}

organization
"IETF I2RS (Interface to the Routing System) Working Group";

contact
"WG Web:    <http://tools.ietf.org/wg/i2rs/ >
 WG List:   <mailto:i2rs@ietf.org>

 Editor:    Yan Zhuang
            <mailto:zhuangyan.zhuang@huawei.com>

 Editor:    Danian Shi
            <mailto:shidanian@huawei.com>";

description
    "This module contains a collection of YANG definitions
    for Fabric state, representing topology that is either
    learned, or topology that results from applying toplogy
    that has been configured per the ietf-dc-fabric-topology
    model, mirroring the corresponding data nodes in this model.

    This model mirrors the configuration tree of
    ietf-dc-fabric-topology, but contains only read-only state
    data. The model is not needed when the implemtation
    infrastructure supports the Network Management Datastore
    Architecture(NMDA).

    Copyright (c) 2016 IETF Trust and the persons identified
    as authors of the code.  All rights reserved.

    Redistribution and use in source and binary forms, with or
    without modification, is permitted pursuant to, and subject
    to the license terms contained in, the Simplified BSD License
    set forth in Section 4.c of the IETF Trust's Legal Provisions
    Relating to IETF Documents(http://trustee.ietf.org/license-info).

    This version of this YANG module is part of
    draft-ietf-i2rs-yang-dc-fabric-network-topology;see the RFC
    itself for full legal notices.

    NOTE TO RFC EDITOR: Please replace above reference to
    draft-ietf-i2rs-yang-dc-fabric-network-topology-03 with RFC number
    when published (i.e. RFC xxxx).";

revision "2017-12-21" {
    description
        "Initial revision.
         NOTE TO RFC EDITOR: Please replace the following reference to
         draft-ietf-i2rs-yang-dc-fabric-network-topology-03 with RFC
         number when published (i.e. RFC xxxx).";
    reference
        "draft-ietf-i2rs-yang-dc-fabric-network-topology-03";
}

//grouping statements
grouping fabric-network-type {
  description "Identify the topology type to be fabric.";
  container fabric-network {
     presence "indicates fabric Network";
     description
      "The presence of the container node indicates fabric Topology";
    }
}

grouping fabric-options {
  description "Options for a fabric";
  leaf gateway-mode {
    type enumeration {
      enum centralized {
        description "The Fabric uses centerilized gateway, in which
        gateway is deployed on SPINE node.";
      }
      enum distributed {
        description "The Fabric uses distributed gateway, in which
        gateway is deployed on LEAF node.";
      }
    }
    default "distributed";
    description "Gateway mode of the fabric";
  }

  leaf traffic-behavior {
    type enumeration {
      enum normal {
        description "Normal";
      }
      enum policy-driven {
        description "Policy driven";
      }
    }
    default "normal";
    description "Traffic behavior of the fabric";
  }

  leaf-list capability-supported {
    type fabrictypes:service-capabilities;
    description
      "Supported services of the fabric";
  }
}

grouping device-attributes {
  description "device attributes";
  leaf device-ref {
    type fabrictypes:node-ref;
    description "The device the fabric includes.";
  }
  leaf role {
    type fabrictypes:device-role;
    default fabrictypes:leaf;
    description "Role of the node";
  }
}

grouping link-attributes {
  description "Link attributes";
  leaf link-ref {
    type fabrictypes:link-ref;
    description "The link it includes";
  }
}

grouping port-attributes {
  description "Port attributes";
  leaf port-ref {
    type fabrictypes:tp-ref;
    description "The port it refers to.";
  }
  leaf port-type {
    type fabrictypes:port-type;
    description
      "Port type: ethernet or serial or others";
    }
  leaf bandwidth {
    type fabrictypes:bandwidth;
    description "Bandwidth of the port";
  }
}

grouping fabric-attributes {
  description "Attributes of a fabric";
  leaf fabric-id {
    type fabric:fabric-id;
    description "Fabric id";
  }
  leaf name {
    type string;
    description     "Name of the fabric";
  }
  leaf type {
    type fabrictypes:underlay-network-type;
     description
      "The type of physical network that implements this
      fabric.Examples are vlan, and trill.";
    }
  container vni-capacity {
    description "Number of vnis the fabric has";
      leaf min {
        type int32;
        description "Vni min capacity";
      }
      leaf max {
        type int32;
        description "Vni max capacity";
      }
  }
  leaf description {
    type string;
    description "Description of the fabric";
  }
  container options {
    description "Options of the fabric";
    uses fabric-options;
  }
  list device-nodes {
    key device-ref;
    description "Device nodes that include in a fabric.";
    uses device-attributes;
  }
  list device-links {
    key link-ref;
    description "Links that include within a fabric.";
    uses link-attributes;
  }
  list device-ports {
    key port-ref;
    description "Ports that include in the fabric.";
    uses port-attributes;
  }
}

// augment statements

augment "/nws:networks/nws:network/nws:network-types" {
  description
    "Introduce new network type for Fabric-based logical topology";
  uses fabric-network-type;
}

augment "/nws:networks/nws:network/nws:node" {
  when "/nws:networks/nws:network/nws:network-types/sfabric:fabric-network" {
    description "Augmentation parameters apply only for networks with
    fabric topology.";
  }
  description "Augmentation for fabric nodes.";
  container fabric-attributes-state {
    description
      "Attributes for a fabric network";
    uses fabric-attributes;
  }
}
}
