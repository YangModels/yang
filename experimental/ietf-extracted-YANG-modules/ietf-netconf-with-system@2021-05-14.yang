module ietf-netconf-with-system {
   yang-version 1.1;
   namespace "urn:ietf:params:xml:ns:yang:ietf-netconf-with-system";
   prefix ncws;

   import ietf-netconf {
     prefix nc;
     reference
       "RFC 6241: Network Configuration Protocol (NETCONF)";
   }

   organization
    "IETF NETMOD (Network Modeling) Working Group";

   contact
    "WG Web:   <http://tools.ietf.org/wg/netmod/>
     WG List:  <mailto:netmod@ietf.org>";
   description
    "This module defines an extension to the NETCONF protocol
     that allows the NETCONF client to control how system configuration
     data are handled by the server in particular NETCONF operations.

     Copyright (c) 2010 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
   // RFC Ed.: replace XXXX with actual RFC number and remove this note

   revision 2021-05-14 {
     description
       "Initial version.";
     reference
      "RFC XXXX: System configuration Data handling Behavior";
   }

 augment /nc:get-config/nc:input {
    description " Allows the get-config operation to use
      with-system to retrieve the complete system configuration.";
    leaf with-system {
        type empty ;
        description
          "Support system configuration retrieval on
           conventional configuration datastore. ";
       }
  }

 augment /nc:get/nc:input {
    description " Allows the get operation to use
      with-system to retrieve the complete system configuration.";
    leaf with-system {
        type empty ;
        description
          "Support system configuration retrieval on
           running datastore.";
        }
  }
}
