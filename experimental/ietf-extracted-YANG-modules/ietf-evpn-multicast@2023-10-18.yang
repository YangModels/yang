module ietf-evpn-multicast {
  namespace "urn:ietf:params:xml:ns:yang:ietf-evpn-multicast";
  prefix "evpn-multicast";

  import ietf-inet-types {
    prefix "inet";
  }

  import ietf-routing-types {
    prefix "rt-types";
  }

  import ietf-ethernet-segment {
    prefix "es";
  }

  import ietf-evpn {
    prefix "evpn";
  }

  organization  "ietf";
  contact       "ietf";

  description   "evpn multicast";

  revision "2023-10-18" {
    description "Initial draft";
    reference   "";
  }

  /*
   * Features
   */

  feature evpn-igmp-proxy {
    description
      "Support IGMP Proxy for EVPN.";
    reference
      "RFC 9251";
  }

  feature evpn-mld-proxy {
    description
      "Support MLD Proxy for EVPN.";
    reference
      "RFC 9251";
  }

  /* Groupings */

  grouping route-rd-rt-grp {
    description "A grouping for a route's route distinguishers " +
                "and route targets";
    list rd-rt {
      key "route-distinguisher";
      leaf route-distinguisher {
        type rt-types:route-distinguisher;
        description "Route distinguisher";
      }
      list vpn-target {
        key "route-target";
        leaf route-target {
          type rt-types:route-target;
          description "BGP route target";
        }
        description "A list of route targets";
      }
      description "A list of route distinguishers and " +
                  "corresponding VPN route targets";
    }
  }

  /* augments */
  augment "/evpn:evpn/evpn:evpn-instances/evpn:evpn-instance" {
    description "";

    leaf evpn-igmp-proxy {
        if-feature "evpn-igmp-proxy";
        type boolean;
        description "Trigger an IMET route update with Multicast
          Flags Extended Community and IGMP proxy bit is set.";
    }
    leaf evpn-mld-proxy {
        if-feature "evpn-mld-proxy";
        type boolean;
        description "Trigger an IMET route update with Multicast
          Flags Extended Community and MLD proxy bit is set.";
    }
  }

  augment "/evpn:evpn/evpn:evpn-instances/evpn:evpn-instance/evpn:routes" {
   when "../evpn-igmp-proxy = 'true' or ../evpn-mld-proxy = 'true'" {
       description
         "If IGMP or MLD Proxy for EVPN is enabled,
          Type6~8 route could be generated.";
    }
    description "Type6~8 route";
    list selective-multicast-ethernet-tag-route {
       uses route-rd-rt-grp;
       leaf ethernet-tag {
         type uint32;
         description "An ethernet tag (etag) indentifying a " +
                     "broadcast domain";
       }
       leaf multicast-source-address {
        type inet:ip-address;
        description
          "";
       }
       leaf multicast-group-address {
          type rt-types:ip-multicast-group-address;
          description
            "Multicast group address.";
        }
       leaf originator-ip-prefix {
         type inet:ip-prefix;
         description "originator-ip-prefix";
       }
       description "SMET route (type6)";
     }
    list multicast-membership-report-synch-route {
       uses route-rd-rt-grp;
       leaf ethernet-segment-identifier {
         type es:ethernet-segment-identifier-type;
         description "Ethernet segment identifier (esi)";
       }
       leaf ethernet-tag {
         type uint32;
         description "An ethernet tag (etag) indentifying a " +
                     "broadcast domain";
       }
       leaf multicast-source-address {
        type inet:ip-address;
        description
          "";
       }
       leaf multicast-group-address {
          type rt-types:ip-multicast-group-address;
          description
            "Multicast group address.";
        }
       leaf originator-ip-prefix {
         type inet:ip-prefix;
         description "originator-ip-prefix";
       }
       description "type7 route";
     }
    list multicast-leave-synch-route {
       uses route-rd-rt-grp;
       leaf ethernet-segment-identifier {
         type es:ethernet-segment-identifier-type;
         description "Ethernet segment identifier (esi)";
       }
       leaf ethernet-tag {
         type uint32;
         description "An ethernet tag (etag) indentifying a " +
                     "broadcast domain";
       }
       leaf multicast-source-address {
        type inet:ip-address;
        description
          "";
       }
       leaf multicast-group-address {
          type rt-types:ip-multicast-group-address;
          description
            "Multicast group address.";
        }
       leaf originator-ip-prefix {
         type inet:ip-prefix;
         description "originator-ip-prefix";
       }
       leaf maximum-response-time {
         type uint16;
         units "seconds";
         description
           "Query maximum response time specifies the maximum time
            allowed before sending a responding report.";
         reference
           "Sections 4.1.1, 8.3 of RFC 3376: Internet Group
            Management Protocol, Version 3";
       }
       description "type8 route";
     }
  }
}
