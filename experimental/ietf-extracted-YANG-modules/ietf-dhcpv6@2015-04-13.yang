module ietf-dhcpv6 {
    namespace "urn:ietf:params:xml:ns:yang:dhcpv6";
    prefix "dhcpv6";

    import ietf-inet-types { prefix inet; revision-date "2013-07-15"; }
    import ietf-yang-types { prefix yang; revision-date "2013-07-15"; }

    organization "dhc wg";
    contact "yong@csnet1.cs.tsinghua.edu.cn
             wangh13@mails.tsinghua.edu.cn
             lh.sunlinh@gmail.com
             Ted.Lemon@nominum.com
             ";

    description "This model defines a YANG data model that can be used to configure
        and manage DHCPv6 server, DHCPv6 relay and DHCPv6 client.";

    revision 2015-04-13 {
        description "Version02: Correct grammar errors.";
    }

    revision 2015-04-02 {
        description "Version01: Correct grammar errors, Reuse groupings, Update
            'dhcpv6-realy' feature, Add notifications.";
    }

    revision 2015-03-04 {
        description "Version00: Initial revision.";
    }

/*
 * Features
 */

    feature dhcpv6-server {
      description
        "Server in DHCPv6.";
      reference
        "RFC3315";
    }

    feature dhcpv6-relay {
      description
        "Relay agent in DHCPv6.";
      reference
        "RFC3315";
    }

    feature dhcpv6-client {
      description
        "Client in DHCPv6.";
      reference
        "RFC3315";
    }

/*
 * Grouping
 */

    grouping vendor-info {
        container vendor-info {
            config "false";
            leaf ent-num {
                mandatory true;
                type uint8;
            }
            leaf-list data {
                type string;
            }
        }
    }

/*
 * Data Nodes
 */

    container server {
        if-feature dhcpv6-server;
        container serv-attributes {
            description "This container contains basic attributes of a DHCPv6 server
                such as DUID, server name and so on. Some optional functions that
                can be provided by the server is also included.";
            leaf name {
                mandatory true;
                type string;
            }
            leaf duid {
                config false;
                description "Each server and client has only one DUID (DHCP Unique Identifier).
                    The DUID here identifies a unique DHCPv6 server for clients.";
                mandatory true;
                type uint32;
            }
            leaf enable {
                mandatory true;
                type boolean;
            }
            leaf description {
                type string;
            }
            leaf pd-function {
                description "Whether the server can act as a delegating router to perform
                    prefix delegation ([RFC3633]).";
                mandatory true;
                type boolean;
            }
            leaf stateless-service {
                description "A boolean value specifies whether the server support client-server
                    exchanges involving two messages defined in ([RFC3315]).";
                mandatory true;
                type boolean;
            }
            leaf rapid-commit {
                description "A boolean value specifies whether the server support client-server
                    exchanges involving two messages defined in ([RFC3315]).";
                mandatory true;
                type boolean;
            }
            uses vendor-info;
        }
        container address-pools {
            description "A container describes the DHCPv6 server's address pools.";
            list address-pool {
                description "A DHCPv6 server can be configured with several address pools.
                    This list defines such address pools which are distinguish by
                    the key called 'pool-name'.";
                key pool-id;
                leaf pool-id {
                    mandatory true;
                    type uint8;
                }
                leaf pool-prefix {
                    mandatory true;
                    type inet:ipv6-prefix;
                }
                leaf start-address {
                    mandatory true;
                    type inet:ipv6-address-no-zone;
                }
                leaf end-address {
                    mandatory true;
                    type inet:ipv6-address-no-zone;
                }
                leaf preferred-lifetime {
                    mandatory true;
                    type yang:timeticks;
                }
                leaf valid-lifetime {
                    mandatory true;
                    type yang:timeticks;
                }
                leaf used-ipv6-count {
                    config "false";
                    mandatory true;
                    type uint32;
                }
                leaf idle-ipv6-count {
                    config "false";
                    mandatory true;
                    type uint32;
                }
            }
            list binding-info {
                config "false";
                description "A list records a binding information for each DHCPv6 client that
                    has already been allocated IPv6 addresses.";
                key cli-duid;
                leaf cli-duid {
                    mandatory true;
                    type uint32;
                }
                list cli-ia {
                    key iaid;
                    leaf ia-type {
                        mandatory true;
                        type string;
                    }
                    leaf iaid {
                        mandatory true;
                        type uint8;
                    }
                    leaf-list cli-addr {
                        type inet:ipv6-address;
                    }
                    leaf pool-id {
                        type uint8;
                    }
                }
            }
        }
        container prefix-pools {
            description "If a server supports prefix delegation function, this container
                will be used to define the delegating router's refix pools.";
            list prefix-pool {
                description "Similar to server's address pools, a delegating router can also
                    be configured with multiple prefix pools specified by a list called
                    'prefix-pool'.";
                key pool-id;
                leaf pool-id {
                    mandatory true;
                    type uint8;
                }
                leaf prefix {
                    mandatory true;
                    type inet:ipv6-prefix;
                }
                leaf prefix-length {
                    mandatory true;
                    type uint8;
                }
                leaf preferred-lifetime {
                    mandatory true;
                    type yang:timeticks;
                }
                leaf valid-lifetime {
                    mandatory true;
                    type yang:timeticks;
                }
            }
            list binding-info {
                config "false";
                description "A list records a binding information for each DHCPv6 client that
                    has already been allocated IPv6 addresses.";
                key cli-duid;
                leaf cli-duid {
                    mandatory true;
                    type uint32;
                }
                list cli-iapd {
                    key iaid;
                    leaf iaid {
                        mandatory true;
                        type uint8;
                    }
                    leaf-list cli-prefix {
                        type inet:ipv6-prefix;
                    }
                    leaf-list cli-prefix-len {
                        type uint8;
                    }
                    leaf pool-id {
                        type uint8;
                    }
                }
            }
        }
        container other-paras {
            description "This container defines extra configuration parameters provided
                by the DHCPv6 server apart from the address and prefix information.
                Such parameters may include DNS servers, SIP servers, SNTP servers,
                etc.";
            list dns-server {
                key dns-serv-id;
                leaf dns-serv-id {
                    mandatory true;
                    type uint8;
                }
                leaf dns-serv-addr {
                    mandatory true;
                    type inet:ipv6-address;
                }
            }
            leaf domain-search-list {
                mandatory true;
                type string;
            }
            list sip-server {
                key sip-serv-id;
                leaf sip-serv-id {
                    mandatory true;
                    type uint8;
                }
                leaf sip-serv-domain-name {
                    mandatory true;
                    type string;
                }
                leaf sip-serv-addr {
                    mandatory true;
                    type inet:ipv6-address;
                }
            }
            list sntp-server {
                key sntp-serv-id;
                leaf sntp-serv-id {
                    mandatory true;
                    type uint8;
                }
                leaf sntp-serv-addr {
                    mandatory true;
                    type inet:ipv6-address;
                }
            }
            list ntp-serv-paras {
                key ntp-serv-id;
                leaf ntp-serv-id {
                    mandatory true;
                    type uint8;
                }
                leaf ntp-serv-addr {
                    mandatory true;
                    type inet:ipv6-address;
                }
                leaf ntp-serv-mul-addr {
                    mandatory true;
                    type inet:ipv6-address;
                }
                leaf ntp-serv-fqdn {
                    mandatory true;
                    type string;
                }
            }
            container nis-paras {
                leaf nis-serv-addr {
                    mandatory true;
                    type inet:ipv6-address;
                }
                list nis-cli-info {
                    key cli-duid;
                    leaf cli-duid {
                        mandatory true;
                        type uint32;
                    }
                    leaf cli-domain-name {
                        mandatory true;
                        type string;
                    }
                }
            }
            container nisp-paras {
                leaf nisp-serv-addr {
                    mandatory true;
                    type inet:ipv6-address;
                }
                list nisp-cli-info {
                    key cli-duid;
                    leaf cli-duid {
                        mandatory true;
                        type uint32;
                    }
                    leaf cli-domain-name {
                        mandatory true;
                        type string;
                    }
                }
            }
        }
        container relay-opaque-paras {
            description "This container contains some opaque values in Relay Agent options
                that need to be configured on the server side only for value match.
                Such Relay Agent options include Interface-Id option, Remote-Id
                option and Subscriber-Id option.";
            list relays {
                key relay-name;
                leaf relay-name {
                    mandatory true;
                    type string;
                }
                list interface-info {
                    key if-name;
                    leaf if-name {
                        mandatory true;
                        type string;
                    }
                    leaf interface-id {
                        mandatory true;
                        type string;
                    }
                }
                list subscribers {
                    key subscriber;
                    leaf subscriber {
                        mandatory true;
                        type string;
                    }
                    leaf subscriber-id {
                        mandatory true;
                        type string;
                    }
                }
                list remote-host {
                    key ent-num;
                    leaf ent-num {
                        mandatory true;
                        type uint8;
                    }
                    leaf remote-id {
                        mandatory true;
                        type string;
                    }
                }
            }
        }
        container packet-stats {
            config "false";
            description "A container presents the packet statistics related to the DHCPv6
                server.";
            leaf solicit-count {
                mandatory true;
                type uint32;
            }
            leaf request-count {
                mandatory true;
                type uint32;
            }
            leaf renew-count {
                mandatory true;
                type uint32;
            }
            leaf rebind-count {
                mandatory true;
                type uint32;
            }
            leaf decline-count {
                mandatory true;
                type uint32;
            }
            leaf release-count {
                mandatory true;
                type uint32;
            }
            leaf info-req-count {
                mandatory true;
                type uint32;
            }
            leaf advertise-count {
                mandatory true;
                type uint32;
            }
            leaf confirm-count {
                mandatory true;
                type uint32;
            }
            leaf reply-count {
                mandatory true;
                type uint32;
            }
            leaf reconfigure-count {
                mandatory true;
                type uint32;
            }
            leaf relay-forward-count {
                mandatory true;
                type uint32;
            }
            leaf relay-reply-count {
                mandatory true;
                type uint32;
            }
        }
    }

    container relay {
        if-feature dhcpv6-relay;
        container relay-attributes {
            description "A container describes some basic attributes of the relay agent
                including some relay agent specific options data that need to be configured
                previously. Such options include Remote-Id option and Subscriber-Id option.";
            leaf name {
                mandatory true;
                type string;
            }
            leaf enable {
                mandatory true;
                type boolean;
            }
            leaf-list dest-addrs {
                description "Each DHCPv6 relay agent may be configured with a list of destination
                    addresses. This node defines such a list of IPv6 addresses that
                    may include unicast addresses, multicast addresses or other addresses.";
                type inet:ipv6-address;
            }
            list subscribers {
                key subscriber;
                leaf subscriber {
                    mandatory true;
                    type string;
                }
                leaf subscriber-id {
                    mandatory true;
                    type string;
                }
            }
            list remote-host {
                key ent-num;
                leaf ent-num {
                    mandatory true;
                    type uint8;
                }
                leaf remote-id {
                    mandatory true;
                    type string;
                }
            }
            uses vendor-info;
            container relay-interfaces {
                description "It is a container that defines common configuration and state
                    parameters in the interfaces of a DHCPv6 relay agent. In this
                    YANG data model for DHCPv6 relay agent, the parameters are configured
                    in a per-interface manner.";
                list relay-if {
                    description "A list describes a specific interface and its corresponding parameters.
                        Here we use a string called 'ifName' as the key of list.";
                    key if-name;
                    leaf if-name {
                        mandatory true;
                        type string;
                    }
                    leaf enable {
                        mandatory true;
                        type boolean;
                    }
                    leaf interface-id {
                        type string;
                    }
                    list next-entity {
                        description "This node defines a list that is used to describe the next hop
                            entity of this relay distinguished by their addresses.";
                        key dest-addr;
                        leaf dest-addr {
                            mandatory true;
                            type inet:ipv6-address;
                        }
                        leaf available {
                            mandatory true;
                            type boolean;
                        }
                        leaf multicast {
                            mandatory true;
                            type boolean;
                        }
                        leaf server {
                            mandatory true;
                            type boolean;
                        }
                        container packet-stats {
                            config "false";
                            description "A container shows packet state information of a specific interface.
                                It is a sub-container of the 'relayInterfaces' container.";
                            leaf cli-packet-rvd-count {
                                mandatory true;
                                type uint32;
                            }
                            leaf solicit-rvd-count {
                                mandatory true;
                                type uint32;
                            }
                            leaf request-rvd-count {
                                mandatory true;
                                type uint32;
                            }
                            leaf renew-rvd-count {
                                mandatory true;
                                type uint32;
                            }
                            leaf rebind-rvd-count {
                                mandatory true;
                                type uint32;
                            }
                            leaf decline-rvd-count {
                                mandatory true;
                                type uint32;
                            }
                            leaf release-rvd-count {
                                mandatory true;
                                type uint32;
                            }
                            leaf info-req-rvd-count {
                                mandatory true;
                                type uint32;
                            }
                            leaf relay-for-rvd-count {
                                mandatory true;
                                type uint32;
                            }
                            leaf relay-rep-rvd-count {
                                mandatory true;
                                type uint32;
                            }
                            leaf pac-to-cli-count {
                                mandatory true;
                                type uint32;
                            }
                            leaf adver-sent-count {
                                mandatory true;
                                type uint32;
                            }
                            leaf confirm-sent-count {
                                mandatory true;
                                type uint32;
                            }
                            leaf reply-sent-count {
                                mandatory true;
                                type uint32;
                            }
                            leaf reconfig-sent-count {
                                mandatory true;
                                type uint32;
                            }
                            leaf relay-for-sent-count {
                                mandatory true;
                                type uint32;
                            }
                            leaf relay-rep-sent-count {
                                mandatory true;
                                type uint32;
                            }
                        }
                    }
                }
            }
        }
        container relay-stats {
            config "false";
            description "The container records and presents the overall packet statistics
                of the relay agent.";
            leaf cli-packet-rvd-count {
                mandatory true;
                type uint32;
            }
            leaf relay-for-rvd-count {
                mandatory true;
                type uint32;
            }
            leaf relay-rep-rvd-count {
                mandatory true;
                type uint32;
            }
            leaf packet-to-cli-count {
                mandatory true;
                type uint32;
            }
            leaf relay-for-sent-count {
                mandatory true;
                type uint32;
            }
            leaf relay-rep-sent-count {
                mandatory true;
                type uint32;
            }
            leaf discarded-packet-count {
                mandatory true;
                type uint32;
            }
        }
    }

    container client {
        if-feature dhcpv6-client;
        container client-interfaces {
            description "A client may have several interfaces, it is more reasonable to
                configure and manage parameters on the interface-level. This container
                includes configuration and state data of a DHCPv6 client in a
                per-interface manner.";
            list client-if {
                description "The list defines a specific client interface and its data. Different
                    interfaces are distinguished by the key which is a configurable string
                    value.";
                key if-name;
                leaf if-name {
                    mandatory true;
                    type string;
                }
                leaf duid {
                    config "false";
                    description "Each server and client has only one DUID (DHCP Unique Identifier).
                        The DUID here will be carried in the Client ID option to identify
                        a specific DHCPv6 client.";
                    mandatory true;
                    type uint32;
                }
                leaf enable {
                    mandatory true;
                    type boolean;
                }
                leaf cli-fqdn {
                    description "A DHCPv6 server needs to know the Fully Qualified Domain Name
                        (FQDN) of the client to achieve the DNS update.";
                    type string;
                }
                leaf pd-function {
                    description "Whether the client can act as a requesting router to request
                        prefixes using prefix delegation ([RFC3633]).";
                    mandatory true;
                    type boolean;
                }
                leaf rapid-commit {
                    description "'1' indicates a client can initiate a Solicit-Reply message exchange
                        by adding a Rapid Commit option in Solicit message. '0' means
                        the client is not allowed to add a Rapid Commit option to request
                        addresses in a two-message exchange pattern.";
                    mandatory true;
                    type boolean;
                }
                leaf dual-stack {
                    mandatory true;
                    type boolean;
                }
                container mo-tab {
                    description "The management tab label indicates the operation mode of the
                        DHCPv6 client. 'm'=1 and 'o'=1 indicate the client will use DHCPv6
                        to obtain all the configuration data. 'm'=1 and 'o'=0 are a meaningless
                        combination. 'm'=0 and 'o'=1 indicate the client will use stateless
                        DHCPv6 to obtain configuration data apart from addresses/prefixes
                        data. 'm'=0 and 'o'=0 represent the client will not use DHCPv6
                        but use SLAAC to achieve configuration.";
                    leaf m-tab {
                        mandatory true;
                        type boolean;
                    }
                    leaf o-tab {
                        mandatory true;
                        type boolean;
                    }
                }
                uses vendor-info;
                container identity-associations {
                    config "false";
                    description "IA is a construct through which a server and a client can identify,
                        group, and manage a set of related IPv6 addresses. The key of
                        the list is a 4-byte number IAID defined in [RFC3315] .";
                    list identity-association {
                        key iaid;
                        leaf iaid {
                            mandatory true;
                            type uint8;
                        }
                        leaf ia-type {
                            mandatory true;
                            type string;
                        }
                        leaf-list ipv6-addr {
                            type inet:ipv6-address;
                        }
                        leaf-list ipv6-prefix {
                            type inet:ipv6-prefix;
                        }
                        leaf-list prefix-length {
                            type uint8;
                        }
                        leaf t1-time {
                            mandatory true;
                            type yang:date-and-time;
                        }
                        leaf t2-time {
                            mandatory true;
                            type yang:date-and-time;
                        }
                        leaf preferred-lifetime {
                            mandatory true;
                            type yang:timeticks;
                        }
                        leaf valid-lifetime {
                            mandatory true;
                            type yang:timeticks;
                        }
                    }
                }
                container if-other-paras {
                    config "false";
                    description "A client can obtain extra configuration data other than address
                        and prefix information through DHCPv6. This container describes
                        such data the client was configured. The potential configuration
                        data may include DNS server addresses, SIP server domain names, etc.";
                    leaf-list dns-serv-addr {
                        type inet:ipv6-address;
                    }
                    leaf domain-search-list {
                        mandatory true;
                        type string;
                    }
                    leaf-list sip-serv-addr {
                        type inet:ipv6-address;
                    }
                    leaf sip-serv-domain-name-list {
                        mandatory true;
                        type string;
                    }
                    leaf uni-dhcpv6-serv-addr {
                        mandatory true;
                        type inet:ipv6-address;
                    }
                    leaf-list sntp-serv-addr {
                        type inet:ipv6-address;
                    }
                    container ntp-serv-paras {
                        leaf ntp-serv-addr {
                            mandatory true;
                            type inet:ipv6-address;
                        }
                        leaf ntp-serv-mul-addr {
                            mandatory true;
                            type inet:ipv6-address;
                        }
                        leaf ntp-serv-fqdn {
                            mandatory true;
                            type string;
                        }
                    }
                    container nis-paras {
                        leaf nis-serv-addr {
                            mandatory true;
                            type inet:ipv6-address;
                        }
                        leaf nis-cli-domain-name {
                            mandatory true;
                            type string;
                        }
                    }
                    container nisp-paras {
                        leaf nisp-serv-addr {
                            mandatory true;
                            type inet:ipv6-address;
                        }
                        leaf nisp-cli-domain-name {
                            mandatory true;
                            type string;
                        }
                    }
                }
                container packet-stats {
                    config "false";
                    description "A container records all the packet status information of a specific
                        interface.";
                    leaf solicit-count {
                        mandatory true;
                        type uint32;
                    }
                    leaf request-count {
                        mandatory true;
                        type uint32;
                    }
                    leaf renew-count {
                        mandatory true;
                        type uint32;
                    }
                    leaf rebind-count {
                        mandatory true;
                        type uint32;
                    }
                    leaf decline-count {
                        mandatory true;
                        type uint32;
                    }
                    leaf release-count {
                        mandatory true;
                        type uint32;
                    }
                    leaf info-req-count {
                        mandatory true;
                        type uint32;
                    }
                    leaf advertise-count {
                        mandatory true;
                        type uint32;
                    }
                    leaf confirm-count {
                        mandatory true;
                        type uint32;
                    }
                    leaf reply-count {
                        mandatory true;
                        type uint32;
                    }
                    leaf reconfigure-count {
                        mandatory true;
                        type uint32;
                    }
                }
            }
        }
    }

/*
 * Notifications
 */

    notification notifications {
        container dhcpv6-server-event {
            if-feature dhcpv6-server;
            container addr-used-up {
                leaf serv-duid {
                    mandatory true;
                    type uint32;
                }
                leaf serv-name {
                    type string;
                }
                leaf pool-name {
                    mandatory true;
                    type string;
                }
            }
            container prefix-used-up {
                leaf serv-duid {
                    mandatory true;
                    type uint32;
                }
                leaf serv-name {
                    type string;
                }
                leaf pool-name {
                    mandatory true;
                    type string;
                }
            }
            container invalid-client-detected {
                leaf cli-duid {
                    mandatory true;
                    type uint32;
                }
                leaf description {
                    type string;
                }
            }
        }
        container dhcpv6-relay-event {
            if-feature dhcpv6-relay;
            container topo-changed {
                leaf relay-if-name {
                    mandatory true;
                    type string;
                }
                leaf first-hop {
                    mandatory true;
                    type boolean;
                }
                leaf last-entity-addr {
                    mandatory true;
                    type inet:ipv6-address;
                }
            }
        }
        container dhcpv6-client-event {
            if-feature dhcpv6-client;
            container invalid-ia-detected {
                leaf cli-duid {
                    mandatory true;
                    type uint32;
                }
                leaf iaid {
                    mandatory true;
                    type uint8;
                }
                leaf serv-duid {
                    type uint32;
                }
                leaf description {
                    type string;
                }
            }
            container retransmission-failed {
                leaf cli-duid {
                    mandatory true;
                    type uint32;
                }
                leaf description {
                    mandatory true;
                    type enumeration {
                        enum "MRC failed";
                        enum "MRD failed";
                    }
                }
            }
            container failed-status-turn-up {
                leaf cli-duid {
                    mandatory true;
                    type uint32;
                }
                leaf status-code {
                    mandatory true;
                    type enumeration {
                        enum "1" {
                            description "UnspecFail";
                        }
                        enum "2" {
                            description "NoAddrAvail";
                        }
                        enum "3" {
                            description "NoBinding";
                        }
                        enum "4" {
                            description "NotOnLink";
                        }
                        enum "5" {
                            description "UseMulticast";
                        }
                    }
                }
            }
        }
    }
}
