module ietf-vbng-cp{
namespace "urn:ietf:params:xml:ns:yang:ietf-vbng-cp";
prefix "vbng-cp";

import ietf-inet-types {
   prefix "inet";
 }

import ietf-interfaces {
  prefix if;
 }

import ietf-logical-network-element {
  prefix lne;
}

organization
  "IETF NETCONF Working Group";

  contact
   "
     WG List:  <mailto:netconf@ietf.org>

     Editor:   Guangping Huang
               <mailto:huang.guangping@zte.com.cn>
    ";

description
   "The YANG module defines a generic configuration
     model for vbng-cp";

revision 2019-03-08{
  description "Initial a new vbng control and user plane separation
  yang data model, it includes ietf-vbng, ietf-vbng-cp,and ietf-vbng-up, this
  is ietf-vbng-cp";
  reference
     "draft-cuspdt-rtgwg-cu-separation-yang-model-02";
}

/* Typedefs  */

  typedef address-family-type {
    type enumeration {
      enum ipv4 {
        description
          "IPv4";
      }
      enum ipv6 {
        description
          "IPv6";
      }
    }
    description
      "Typedef for address family type.";
  }

 /* Configuration Data */

 augment /lne:logical-network-elements/lne:logical-network-element {
  container ietf-vbng-cp{
    leaf bng-cp-name  {
    type string;
    description "configure vbng-cp name";
  }
   leaf enable  {
    type boolean;
    description "'true' to support vbng separation";
   }
  container netconf-server {
     presence netconf-server ;
     list address-family {
        key "af";
        leaf af {
           type address-family-type;
           description
             "Address family type value.";
        }
        leaf ip {
         type inet:ip-address;
         mandatory true ;
         description 'Configure ip address of netconf server.';
        }
         description "address family list";
     }
     leaf user-name {
       type string {
         length 1..65 ;
       }
      description 'configure user name, default: "who".';
     }
     leaf password {
       type string {
        length 3..32 ;
       }
     description 'configure password, default: "who".';
     }

     leaf port {
       type uint32;
       description 'Configure port.';
     }
      description 'Configure netconf server.';
  }
  container vbng-pppoe {
   container pppoe-switch {
     leaf delay-time {
       type uint16 {
         range 1..300 ;
       }
       description 'Trigger user offline when VCC phys-interface down';
     }
     leaf keepalive-timer {
       type enumeration {
         enum start {
           value 1 ;
           description "start keepalive timer";
         }
         enum stop {
           value 0 ;
           description "stop keepalive timer";
         }
       }
       default start ;
       description 'Start or stop send keepalive packet';
     }
     leaf ppp-max-payload {
       type enumeration {
         enum disable {
           value 0 ;
           description "disable ppp max payload";
         }
         enum enable {
           value 1 ;
           description "enable ppp max payload";
         }
       }
       default disable ;
       description 'Enable or disable pppoe ppp-max-payload';
     }
     leaf service {
       type enumeration {
         enum advertise{
           value 1 ;
           description "enable ppp service!";
         }
         enum disable {
           value 0 ;
           description "disable ppp service!";
         }
       }
       default advertise ;
        description 'Open or close pppoe service';
     }
     leaf ppp-mru-verify {
       type enumeration {
         enum open {
           value 1 ;
           description "enable ppp mru verify!";
         }
         enum close {
           value 0 ;
           description "disable ppp mru!";
         }
       }
       default close ;
       description 'set ppp lcp mru verify when mru over 1492';
     }

     leaf keepalive-fast-reply {
       type enumeration {
         enum enable {
           value 1 ;
           description 'Enable keepalive fast reply!';
         }
         enum disable {
           value 0 ;
           description 'Disable keepalive fast reply!';
         }
       }
       description 'Set keepalive fast reply flag.';
     }
     description 'Configuration about pppoe switch.';
   }
   list pppoe-cfg {
     key template ;
     leaf template {
       type uint32 {
         range 1..1000 ;
       }
       description 'PPPoX template number';
     }
     leaf ppp-authentication {
       type enumeration {
         enum pap {
           value 1 ;
           description "configure pap authentication!";
         }
         enum chap {
           value 2 ;
           description "configure chap authentication!";
         }
         enum mschapv1 {
           value 6 ;
           description "configure mschapv1 authentication!";
         }
         enum mschapv2 {
           value 7 ;
           description "configure mschapv2 tication!";
         }
         enum pap-chap {
           value 21 ;
           description "configure pap-chap authentication!";
         }
       }
       default pap-chap ;
       description 'Set ppp authentication';
     }
     leaf ppp-check-magic-num {
       type enumeration {
         enum disable {
           value 0 ;
           description 'disable ppp magic check';
         }
         enum enable {
           value 1 ;
           description 'enable ppp magic check';
         }
       }
       default enable ;
       description 'Check magic number or not';
     }
     leaf ppp-mru {

       type uint32 {
         range 320..9000 ;
       }
       default 1492 ;
       description 'Set mru value';
     }
     leaf pppoe-ac-name {
       type string ;
       description 'Set ac-name';
     }
     leaf pppoe-service-name-omit {
       type enumeration {
         enum disable {
           value 0 ;
           description "disable pppoe service name omit";
         }
         enum enable {
           value 1 ;
           description "enable pppoe service name omit";
         }
       }
       default disable ;
       description 'Check service-name value';
     }
     leaf pppoe-ac-cookie-check {
       type enumeration {
         enum disable {
           value 0 ;
           description "disable pppoe ac cookie check";
         }
         enum enable {
           value 1 ;
           description "enable pppoe ac cookie check";
         }
       }
       default enable ;
       description 'Check options';
     }
     leaf pppoe-password-string {
       type string ;
       description 'Set authentication failure password string';
     }
     leaf pppoe-username-string {
       type string ;
       description 'Set authentication failure username error string';
     }

     choice ppp-quick-redial {
       case quick-redial-disable {
         leaf ppp-quick-redial-disable {
           type enumeration {
             enum disable {
               value 0 ;
               description "disable ppp quick redial";
             }
           }
           default disable ;
           description 'disable quick-redial';
         }
         description 'disable quick-redial';
       }
       case fast-response {
         leaf ppp-fast-response {
           type enumeration {
             enum diable {
               value 0 ;
                description "disable ppp fast response";
             }
             enum enable {
               value 1 ;
               description "enable ppp fast response";
             }
           }
           description 'set Response the access request immediately';
         }
         leaf ppp-quick-redial-enable {
           type enumeration {
             enum enable {
               value 1 ;
               description "enable ppp quick redial";
             }
           }
           default enable ;
           description 'Enable quick-redial';
         }
         description 'set quick-redial or Response the access request immediately';
       }
       default quick-redial-disable ;
       description 'Enable or disable quick-redial';
     }
     container ppp-keepalive {
       leaf ppp-keepalive-timer {
         type uint32 {
           range 10..14400 ;
         }
         default 60 ;
         description 'Set keepalive time(unit:seconds)';
       }
       leaf ppp-keepalive-count {
         type uint16 {
           range 1..10 ;
         }
         default 3 ;
         description 'Set keepalive counter';
       }
      description 'Set keepalive time and counter';
     }
     container ppp-timeout {
       leaf ppp-timeout-negtimeoutsec {
         type uint8 {
           range 1..10 ;
         }
         default 3 ;
         description 'Set ppp negtimeoutsec timeout(unit:seconds)';
       }
       leaf ppp-timeout-authentication {
         type uint8 {
           range 1..10 ;
         }
         default 3 ;
         description 'Set ppp authentication timeout(unit:seconds)';
       }
      description 'Set ppp negtimeoutsec and authentication timeout';
     }
     description 'Configuration pppoe template';
   }
   description 'Configuration vBRAS PPPoE.';
 }
  description "configure bng-cp";
}
description "augment lne model";
}
}
