module ietf-l2tp {
  yang-version "1";

  namespace "urn:ietf:params:xml:ns:yang:ietf-l2tp";

  prefix "l2tp";

  import ietf-inet-types {
    prefix "inet";
  }

  import ietf-yang-types {
    prefix yang;
  }

  organization
       "Ericsson (China) Communications Company Ltd.
        Ericsson Tower, No. 5 Lize East Street,
        Chaoyang District Beijing 100102, P.R. China";

  contact
       "Editor:   Yang Huang
                  <mailto:harry.huang@ericsson.com>";

  description
       "This YANG module defines the generic configuration and
        operational state for the L2TP protocol common to all
        vendor implementations. It is intended that the module
        will be extended by vendors to define vendor-specific
        L2TP configuration parameters and policies.";

  revision 2016-07-29 {
    description
      "Initial revision.";
    reference
         "RFC XXXX: A YANG Data Model for L2TP.";
  }

  typedef dnis-state-type {
     type enumeration {
      enum enable {
        description "enable dnis ";
      }
      enum disable {
        description "disable dnis ";
      }
    }
     description "Dnis state type";
  }

  typedef chap-state-type {
    type enumeration {
      enum enable {
        description "enable chap";
      }
      enum disable {
        description "disable chap";
      }
    }
     description "CHAP state";
  }

  typedef pap-state-type {
    type enumeration {
      enum enable {
        description "enable pap";
      }
      enum disable {
        description "disable pap";
      }
    }
     description "PAP state";
  }

  container l2tp {
    description
      "l2tp configuration parameters.";

   leaf accm {
     type empty;
     description "ACCM for LNS only";
   }
   leaf clear-radius-peer {
     type uint16 {
       range "5..300";
     }
     units minute;
     description
         "Time to cleanup RADIUS peers when no sessions are
         active";
    }

    leaf deadtime {
     type uint16 {
       range "1..100";
     }
      units minute;
     default 2;
      description "Time to ignore a non-responsive peer";
    }

    container fragment {
     description "Fragmentation algorithm";
     choice fragment-type {
       case l2tp-packet {
         leaf l2tp-packet {
           type empty;
           description "Fragment l2tp packet";
         }
       }
       case user-packet {
         leaf user-packet {
           type empty;
           description "Fragment user packet";
         }
       }

       default l2tp-packet;

       description "Fragmentation algorithm type";
     }
    }

    leaf proxy-auth {
      type empty;
       description "Enable proxy authentication";
    }
    container radius-peer {
       description "Radius attribute configurations";
       leaf use-server-auth-id {
         type empty;
        description
            "Use server-auth-id as peer name if assignment-id not
            present";
     }
    }

    leaf reconfig-ses {
       type empty;
       description
          "Enable reconfiguration of sessions on peer reconfig";
    }

    container renegotiate {
       description "LNS PPP renegotiation";
       leaf mru {
         type uint32 {
          range "256..12800";
       }
       description "Renegotiate MRU";
     }
     container lcp {
       description "LCP renegotiation";
       choice lcp {
         case always {
           leaf always {
             type empty;
             description "Always renegotiate LCP";
           }
         }
         case never {
           leaf never {
             type empty;
             description "Never renegotiate LCP";
           }
         }
         case on-mismatch {
           leaf on-mismatch {
             type empty;
             description "Renegotiate LCP only on mismatch";
           }
         }

         default on-mismatch;
            description "LCP renegotiation";
       }
     }
    }

    leaf strict-deadtime {
      type empty;
      description "If strict deadtime is enabled, no connection
         attempt is made until the deadtime for at least one
         candidate peer has expired, even if all L2TP peers
         are labeled dead.";
    }

    list l2tp-group {
     key name;
     description "Configure an L2TP group";

     leaf name {
       type string;
       description "L2TP group name";
     }

     choice algrithm {
       description
       "Algorithm for distributing sessions among peers";
       case load-balance {
         leaf load-balance {
           type empty;
           description
           "Distribute sessions among peers equally";
         }
       }
       case priority {
         leaf priority {
           type empty;
           description
           "Distribute sessions among peers by priority";
         }
       }
       case weighted-round-robin {
                              leaf weighted-round-robin {
           type empty;
           description
                  "Distribute sessions among peers by weighted
                  round robin";
         }
       }
     }

     leaf deadtime {
       type uint16 {
         range "1..300";
       }
        units minute;
       default 2;
        description
         "Time to ignore a peer that is not responding";
      }

      leaf description {
        type string;
        description "Add descriptive text for this group";
      }

      leaf domain {
        type string;
        description "L2TP group domain name";
      }

      list peers {
        key "peer-name";
        description "L2TP peers in this group";

        leaf peer-name {
         type leafref{
              path "../../../l2tp-peer/name";
            }
            description "L2TP peer name";
        }

        leaf preference {
         type uint16 {
          range "1..100";
        }
         description
               "Set the priority of the peer for priority
               algorithm";
        }

       leaf weight {
         type uint16 {
           range "1..100";
        }
         description
               "Set the weight of the peer for weighted round
               robin algorithm";
       }
      }

    }

    list l2tp-peer {
     key name;
     description "Configure an L2TP tunnel";

     leaf name {
       type string {
         length "1..64";
       }
       description "The remote peer name";
     }

     choice media {
       case udp-ip {
         description "Tunnel to peer via UDP";
         choice remote {
           description "Set the remote peer identity";
           case dns {
             leaf dns {
               type string;
               description
               "Set the DNS name of the remote peer";
             }
           }
           case ip {
             leaf ip {
               type inet:ipv4-address;
               description "Tunnel peer IP address";
             }
           }
         }
         leaf local-ip-addr {
           type inet:ipv4-address;
           description "Set the Tunnel local IP address";
         }
       }
       default udp-ip;
       description "Set the tunnel media";
     }
     leaf description {
       type string;
       description "Add descriptive text for this peer";
     }

     leaf cleanup-timer {
       type uint16 {
         range "1..28800";
       }
       units seconds;
       description "Clear tunnels when peer has no sessions";
     }
     leaf dnis {
         type dnis-state-type;
       default disable;
       description
            "Directs the Layer 2 Tunneling Protocol (L2TP) process
            to transmit the Calling-Number AVP (22) Incoming-Call-
            Requests (ICRQs).";

     }
     leaf domain {
       type string;
       description "Set tunnel domain name";
     }
     choice tunnel-type {
       case lac-only {
         description "LAC functionality only";
       }
       case lns-only {
         description "LNS functionality only";
       }
       default lac-only;
       description "Tunnel functionality";
     }

     leaf hello-timer {
       type uint16 {
         range "30..3600";
       }
        units seconds;
        description "Set hello control message timer";
     }

     leaf local-name {
       type string;
       description "Set tunnel local name";
     }
     leaf max-sessions {
       type uint16 {
         range "1..65535";
       }
       description "Set maximum number of sessions per tunnel";
     }

     leaf max-tunnels {
       type uint16 {
         range "1..64000";
       }
       description "Set maximum number of tunnels";
     }

     container message-reordering {
       description "Accept out of order control messages";
       leaf message-queue {
            type uint8 {
           range "1..32";
         }
         description
              "Queue size to store out-of-order control messages";
       }
     }

     leaf retry {
       type uint8 {
         range "1..100";
       }
       default 5;
       description
       "Set tunnel control message retransmit count";
     }

     container session-auth {
       description "PPP authentication type on LNS";

       leaf chap {
         type chap-state-type;
         default enable;
         description "Use CHAP authentication protocol";
       }

       leaf pap {
         type pap-state-type;
         default enable;
         description "Use PAP authentication protocol";
       }

       leaf timeout {
         type uint8 {
           range "1..30";
         }
         default 3;
         description "Set tunnel control message timeout";
       }

       leaf tunnel-auth {
            type string;
         description
               "Specify key (shared secret) to use with this
               peer";
       }

       leaf tunnel-window {
         type uint16 {
           range "1..2000";
         }
         default 8;
         description "Set tunnel control channel window size";
       }
     }
    }
  }

  container l2tp-state {
    config false;
    description
      "Data nodes for the operational state of L2TP.";

    list l2tp-summary {
     key peer-name;
     description "L2TP summary information";

     leaf peer-name {
       type string;
       description "The tunnel remote peer name";
     }

     leaf local-name {
       type string;
       description "The tunnel local name";
     }
     leaf tunnel-count {
       type uint16 {
        range "1..65534";
      }
       description "Number of active tunnel";
     }

     leaf session-count {
       type uint16 {
        range "1..65534";
      }
       description "Number of active session";
     }
    }

    list l2tp-group {
     key name;
     description "L2TP group status information";

     leaf name {
       type string;
       description "L2TP group name";
     }

     choice algrithm {
       description
       "Algorithm for distributing sessions among peers";
       case load-balance {
         leaf load-balance {
               type empty;
           description
                 "Distribute sessions among peers equally";
         }
       }
       case priority {
         leaf priority {
           type empty;
           description
                 "Distribute sessions among peers by priority";
         }
       }
       case weighted-round-robin {
         leaf weighted-round-robin {
           type empty;
           description
                 "Distribute sessions among peers by weighted
               round robin";
         }
       }
     }

     leaf deadtime {
        type uint16 {
          range "1..300";
        }
          units minute;
          description
       "Time to ignore a peer that is not responding";
    }

      leaf domain {
        type string;
        description "L2TP group domain name";
      }

      list peers {
          key "peer-name";
          description "L2TP peers in this group";

          leaf peer-name {
            type string;
            description "L2TP peer name";
          }

          leaf preference {
            type uint16 {
              range "1..100";
            }

            description
               "The priority of the peer for priority algorithm";
          }

          leaf weight {
         type uint16 {
          range "1..100";
        }
            description
               "The weight of the peer for weighted round robin
               algorithm";
          }

          leaf status {
         type enumeration {
            enum "PROBE" {
                description "PROBE";
              }
            enum "ALIVE" {
                description "ALIVE";
              }
            enum "DEAD"{
                description "DEAD";
              }
          }
         description "Status of this peer";
          }

          leaf session-count {
            type uint16 {
              range "1..65534";
            }
            description "Number of active session";
          }
      }

      leaf last-use {
        type union {
          type enumeration {
            enum "Never" {
                description "Never";
              }
            enum "Forever" {
                description "Forever";
              }
          }
         type yang:date-and-time;
        }

        description
               "The interval between now and last used time of
               this peer";
      }
    }

    list l2tp-peer {
      key remote-name;
      description "L2TP peer status information";

      leaf remote-name {
        type string {
          length "1..64";
        }
        description "The peer remote name";
      }

      leaf local-name {
        type string;
        description "The peer local name";
      }

      leaf admin-state {
        type enumeration {
         enum "Down" {
             description "Down";
           }
         enum "UP" {
             description "UP";
           }
       }
        description "The desired state of the peer";
      }

      leaf vendor {
       type string;
       description "The verdor of this peer";
      }

      leaf description {
       type string;
       description "Add descriptive text for this peer";
      }

      leaf cleanup-timer {
       type uint16 {
         range "1..28800";
       }
       units seconds;
       description "Clear tunnels when peer has no sessions";
      }
      leaf dnis {
       type dnis-state-type;
       default disable;

       description
               "Directs the Layer 2 Tunneling Protocol (L2TP)
               process to transmit the Calling-Number AVP (22) in
               Incoming-Call-Requests (ICRQs).";
      }
      leaf domain {
       type string;
       description "Tunnel domain name";
      }

      choice tunnel-type {
       case lac-only {
         description "LAC functionality only";
       }
       case lns-only {
         description "LNS functionality only";
       }
       default lac-only;
       description "Tunnel functionality";
      }

      leaf hello-timer {
       type uint16 {
         range "30..3600";
       }
        units seconds;
       description "Hello control message timer";
      }

      leaf max-sessions {
       type uint16 {
         range "1..65535";
       }
       description "Maximum number of sessions per tunnel";
      }

      leaf max-tunnels {
       type uint16 {
         range "1..64000";
       }
       description "Maximum number of tunnels";
      }

      container message-reordering {
       leaf message-queue {
            type uint8 {
           range "1..32";
         }
         description
               "Queue size to store out-of-order control
               messages";
       }
       description "Accept out of order control messages";
      }

      leaf retry {
       type uint8 {
         range "1..100";
       }
       default 5;
       description "Tunnel control message retransmit count";
      }

      leaf timeout {
       type uint8 {
        range "1..30";
      }
         units seconds;
       description
            "Tunnel control message timeout value in seconds";
      }

      list tunnel {

        key local-id;
        description "Tunnel status information";

        leaf local-id {
          type uint16;
          description "Tunnel local id";
        }

        leaf local-ip {
          type inet:ipv4-address;
          description "Tunnel local ip address";
        }

        leaf local-name {
          type string;
          description "Tunnel local name";
        }

        leaf remote-id {
          type uint16;
          description "Tunnel remote id";
        }

        leaf remote-ip {
          type inet:ipv4-address;
          description "Tunnel remote ip address";
        }

        leaf remote-port {
          type inet:port-number;
          description "Tunnel remote port";
        }

        leaf remote-name {
          type string;
          description "Tunnel remote name";
        }

        container window {
           description "Tunnel control window";
          leaf current-tx {
             type uint16 {
            range "1..2000";
          }
            description
               "Current tunnel control window for transmitting";
          }

          leaf max-tx {
          type uint16 {
            range "1..2000";
          }

            description
               "Maximum tunnel control window for transmitting";
          }

          leaf rx {
          type uint16 {
            range "1..2000";
          }

            description
               "Current tunnel control window for receiving";
          }
        }

        leaf active-sessions {
         type uint16 {
          range "1..65534";
        }
          description "Number of active sessions";
        }

        leaf state {
          type enumeration {
             enum "Deleted" {
                 description "Deleted";
               }
             enum "Idle" {
                 description "Idle";
               }
             enum "Created" {
                 description "Created";
               }
             enum "Wait-Open" {
                 description "Wait-Open";
               }
             enum "Wait-SCCRP" {
                 description "Wait-SCCRP";
               }
             enum "Wait-Route-Up" {
                 description "Wait-Route-Up";
               }
             enum "Wait-SCCCN" {
                 description "Wait-SCCCN";
               }
             enum "Established" {
                 description "Established";
               }
             enum "Unknown"{
                 description "Unknown";
               }
          }
          description "The operational state of the tunnel";
        }

        list session {
          key local-id;
          description "Session status information";

          leaf local-id {
            type uint16;
            description "Session local id";
          }

          leaf remote-id {
            type uint16;
            description "Session remote id";
          }

          leaf in-octets {
             type yang:counter64;

             description
               "The total number of octets received on the
               session.";
           }

           leaf in-pkts {
             type yang:counter64;

             description
               "The total number of packets received on the
               session.";
           }

           leaf out-octets {
             type yang:counter64;

             description
               "The total number of octets transmitted out of the
               session.";
           }

           leaf out-pkts {
             type yang:counter64;

             description
               "The total number of packets transmitted out of the
               session.";
           }

          leaf state {
            type enumeration {
               enum "Deleted" {
                   description "Deleted";
                 }
               enum "Idle" {
                   description "Idle";
                 }
               enum "Created" {
                   description "Created";
                 }
               enum "Wait-Tun" {
                   description "Wait-Tun";
                 }
               enum "Wait-LNS-Ready" {
                   description "Wait-LNS-Ready";
                 }
               enum "Wait-ICRP"{
                   description "Wait-ICRP";
                 }
               enum "Wait-LAC-Ready" {
                   description "Wait-LAC-Ready";
                 }
               enum "Wait-ICCN" {
                   description "Wait-ICCN";
                 }
               enum "Established"{
                   description "Established";
                 }
               enum "Unknown" {
                   description "Unknown";
                 }
           }
            description "The operational state of the session";
          }
        }
      }
     }
  }
}
