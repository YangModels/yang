module ietf-i2nsf-capability {
  namespace "urn:ietf:params:xml:ns:yang:ietf-i2nsf-capability";
 // replace with iana namespace when assigned
  prefix "i2nsf-capability";
  import ietf-pkt-eca-policy {
        prefix pkt-eca-policy;
   }
// meta

  organization "IETF I2NSF WG";

contact
   "email: Susan Hares: shares@ndzh.com
    email: Robert Moskowitz rgm@htt-consult.com;
        email: Frank Xia
        email: Aldo Basile cataldo.basile@polito.it";

description
  "This module describes a capability model
       for I2NSF devices .";

      revision "2016-06-26" {
         description "initial revision";
         reference "draft-hares-i2nsf-capability-dm-00.txt";
       }

   grouping ITResources {
        list ITResource {
          key ITResource-id;
              leaf ITResource-id {
                 type uint64;
                 description "ID for ITResource";
              }
              leaf ITResource-name {
                      type string;
                      description "ITResource name.";
              }
              description "list of IT Resources.";
         }
         description "IT Resource grouping.";
       }

       grouping cfg-sec-content-caps {
        list cfg-fcn-groups {     // functions in 2 lists:
          key "group-name";       // group and functions
              leaf group-name {
               type string;
               description " name of function
                group";
              }
              list group-fnc-list {
                key "fcn-name";
                leaf fcn-name {
                 type string;
                 description "security content
                  function name";
                }
                leaf fcn-order-id {
                 type uint64;
                 description "function order
                 in list of functions.";
                }
                leaf default-action-id {
                 type uint64;
                 description "default
                 extended action id";
                }
                leaf default-cr-resolve-id {
                 type uint32;
                 description "default
                 policy conflict resolution
                 policy identifier.";
                }
                description "list of
                functions per group.
                e.g. group A has
                5 functions.";
              }

         description "list of
         groups with associated
              security content functions.";
  }

    list cfg-sec-content-fcns {
      key "fcn-order-id function-name";
      leaf fcn-order-id {
        type uint64;
        description "order id for rule";
      }
      leaf function-name {
         type string;
          description "rule name";
       }
       list anti-virus {
          key "anti-virus-name";
          leaf anti-virus-name {
            type string;
            description "name of
            anti-virtus functionalty";
           }
          leaf anti-virus-supported {
              type boolean;
              description "anti-virus
             feature supported";
          }
        description "anti-virus functions";
      }
      list IPS {
         key "IPS-name";
         leaf IPS-name {
                 type string;
                 description "name of
                 anti-virtus functionalty";
                }
                leaf IPS-supported {
                 type boolean;
                 description "IPS
                 capability
                  supported";
                }
                description "IPS capability";
              }

              list IDS  {
                key "IDS-name";
                leaf IDS-name {
                 type string;
                 description "name of IDS";
                }
                leaf IDS-supported {
                 type boolean;
                 description "anti-virus
                  feature supported";
                }
                description "IDS
                  capabilities";
              }

      list url-filter  {
                key "url-filter-name";
                leaf url-filter-name {
                 type string;
                 description "name of IDS";
                }
                leaf url-filter-supported {
                 type boolean;
                 description "url filter
                  feature supported";
                }
                description "URL filter
                capabilities";
              }

              list file-block  {
                key "fblock-name";
                leaf fblock-name {
                 type string;
                 description "name of
                 file block function";
                }
                leaf fblock-supported {
                 type boolean;
                 description "anti-virus
                  feature supported";
                }
                description "file block
                capabilities";
              }

              list data-filter  {
                key "dfilter-name";
                leaf dfilter-name {
                 type string;
                 description "name of
                  data filer";
                }
                leaf dfilter-supported {
                 type boolean;
                 description "anti-virus
                  feature supported";
                }
                description "data filter
                 capabilities";
              }

              list app-behave  {
                key "app-behave-name";
                leaf app-behave-name {
                 type string;
                 description "name of
                  application behavior
                      control function.";
                }
                leaf app-behave-supported {
                 type boolean;
                 description "application
                  behavior control
                      security capability
                      supported.";
                }
                description "Application
                  behavior control security
                 capabilities";
              }

              list mail-filter  {
                key "mfilter-name";
                leaf mfilter-name {
                 type string;
                 description "name of
                  data filer";
                }
                leaf mfilter-supported {
                 type boolean;
                 description "mail filter
                 supported";
                }
                description "mail filter";
              }

              list pkt-capture  {
                key "pkt-capture-name";
                leaf pkt-capture-name {
                 type string;
                 description "name of
                  data filer";
                }
                leaf pkt-capture-supported {
                 type boolean;
                 description "pkt capture
                  facility supported";
                }
                description "packet capture
                 facility supported ";
              }

              list file-isolate  {
                key "f-isolate-name";
                leaf f-isolate-name {
                 type string;
                 description "name of
                  file isolate capability";
                }
                leaf f-isolate-supported {
                 type boolean;
                 description "file isolate
                 capability supported ";
                }
                description "file isolate
                capability ";
              }
          description "list of
              security content capabilities.";
         }
     description "configured
         security content capabilities";
  }

  grouping cfg-content-sec-actions {
   list content-sec-actions {
         key "action-name";
         leaf action-name {
          type string;
      description "name of extra
              content security action
              beyond function policy";
         }
     description "list
         of content security actions";
    }
        description "configure
        content security actions
        configured beyond capability
        function existance";
      }

       grouping cfg-attack-mitigate-caps {
        // group and then rules
        list cfg-mitigate-fncs-groups {
          key "group-name";
              leaf group-name {
               type string;
               description " name of function
                group";
              }
              list group-mitigate-fncs-list {
                key "fcn-name";
                leaf fcn-name {
                 type string;
                 description "security content
                  function name";
                }
                leaf fcn-order-id {
                 type uint64;
                 description "function order
                 in list of functions.";
                }
                leaf default-action-id {
                 type uint64;
                 description "default
                 extended action id";
                }
                leaf default-cr-resolve-id {
                 type uint32;
                 description "default
                 policy conflict resolution
                 policy identifier.";
                }
                description "list of
                functions per group.
                e.g. group A has
                5 functions.";
              }

         description "list of
         groups with associated
              attack mitigate functions.";
        }

    list cfg-attack-mitigate-rule {
          key "rule-order-id rule-name";
          leaf rule-order-id {
                type uint64;
                description "order id for
                configured mitigate
                function";
      }
      leaf rule-name {
               type string;
               description "mitigate
        rule name";
              }
              list cfg-sync-flood  {
                key sync-flood-fcn;
                leaf sync-flood-fcn {
                 type string;
                 description "name of
                 sync flood functionalty";
                }
                leaf sync-flood-fcn-supported {
                 type boolean;
                 description "sync-flood
                  mitigation fcn supported";
                }
                description "list of
                sync flood mitigation
                functions ";
              }
              list cfg-udp-flood {
                key "udp-flood-fcn";
                leaf udp-flood-fcn {
                 type string;
                 description "name of
                 udp flood mitigation function ";
                }
                leaf udp-flood-fcn-supported {
                 type boolean;
                 description "udp flood
                 prevent function
                 capability supported";
                }
                description "list of
                udp-flood mitigation
                functions node
                (configured capability).";
              }

              list cfg-icmp-flood  {
                key "icmp-flood-fcn";
                leaf icmp-flood-fcn {
                 type string;
                 description "name of
                 icmp flood prevention
                 function";
                }
                leaf icmp-flood-fcn-supported {
                 type boolean;
                 description "icmp
                  flood mitigation
                  feature supported";
                }
                description "list for
                icmp flood prevention
                functions part of
                attack mitigation
                  capabilities.";
              }

      list cfg-http-flood  {
                key "http-flood-fcn";
                leaf http-flood-fcn {
                 type string;
                 description "name of
                 http flood
                 mitigation function";
                }
                leaf http-flood-fcn-supported {
                 type boolean;
                 description "support
                 for http flood function
                 capability is active.";
                }
                description "list of
                http flood
                mitigation functions
                configured ";
              }

              list cfg-dns-flood  {
                key "dns-flood-fcn";
                leaf dns-flood-fcn {
                 type string;
                 description "name of
                 dns flood mitigation
                 function";
                }
                leaf dns-flood-fcn-supported {
                 type boolean;
                 description "dns flood
                 mitigation support is
                 active.";
                }
                description "list of
                dns flood
                mitigation functions
                configured.";
              }

              list cfg-dns-amplify {
                key "dns-amplify-fcn";
                leaf dns-amplify-fcn {
                 type string;
                 description "name of
                  dns amplify mitigation
                      function.";
                }
                leaf dfilter-supported {
                 type boolean;
                 description "dns
                 amplification mitigation
                 function is active.";
                }
                description "list of
                dns amplification
                mitigation functions
                configured.";
              }

              list SSL-DoS  {
                key "ssl-dos-fcn";
                leaf ssl-dos-fcn {
                 type string;
                 description "name of
                 SSL DoS mitigation
                 function";
                }
                leaf ssl-dos-supported {
                 type boolean;
                 description "SSL DoS
                 mitigation function is
                 active.";
                }
                description "List of
                SSL DoS functions configured.";
              }

              list cfg-IP-Sweep  {
                key "ipsweep-fcn";
                leaf ipsweep-fcn {
                 type string;
                 description "name of
                 ip sweep mitigation
                 function.";
                }
                leaf ipsweep-fcn-supported {
                 type boolean;
                 description "IP Sweep
                 mitigation function
                 active.";
                }
                description "list of
                IP Sweep mitigation
                functions in NSF device.";
              }

              list cfg-Port-scanning  {
                key "port-scan-fcn";
                leaf port-scan-fcn {
                 type string;
                 description "name of
                  port-scan mitigation
                      function.";
                }
                leaf port-scan-fcn-supported {
                 type boolean;
                 description "port scanning
                 mitigation fcn supported.";
                }
                description "List of
                port scanning mitigation
                functions. ";
              }

              list cfg-ping-of-death  {
                key "pingd-fcn";
                leaf pingd-fcn {
                 type string;
                 description "name of
                  ping of death
                      mitigation function";
                }
                leaf pingd-fcn-supported{
                 type boolean;
                 description "active support
         for this ping of death
         mitigation function";
                }
                description "List of ping of
                death mitigation
                functions.";
              }
          description "attack
              mitigation rule .";
       }  // rules
    description "configured
          attack mitigation functions.";

}   // cfg-attack-mitigate-policy-set

container i2nsf-capabilities {
    list capabilty {
          key "nsf-name";
      leaf nsf-name {
            type string;
            description "name of
            nsf or nsf group
            capabilities drawn from.";
       }
          container cfg-net-secctl-capabilities {
           uses pkt-eca-policy:pkt-eca-policy-set;
           description "network security
             control capabilities configured.";
          }
          container cfg-sec-content-capabilities {
            uses cfg-sec-content-caps;
            uses cfg-content-sec-actions;
                description "security content
                capabilities configured.";
          }
          container cfg-attack-mitigate-capabilites {
            uses cfg-attack-mitigate-caps;
                description "attack mitigation capabilities";
          }
      container cfg-ITResources {
            uses ITResources;
                description "IT Resources
                associated with NSF.";
          }
         description "List of NSF
         capabilities per nsf, nsf group
         or nsf application.";
    }  //end of list

   description "I2NSF capabilities";
  }  // end of container
}
