module ietf-rsvp-te {

    namespace "urn:ietf:params:xml:ns:yang:ietf-rsvp-te";

    prefix "rsvp-te";

    import ietf-rsvp {
        prefix rsvp;
    }

    /* Import TE packet specific types */
    import ietf-te-psc-types {
        prefix ietf-te-psc-types;
    }

    import ietf-te {
        prefix ietf-te;
    }

    import ietf-inet-types {
        prefix inet;
    }

    /* groupings for rsvp */
    grouping signaling {
        container signaling {
            description "Configure RSVP signaling properties.";
            leaf egress-label {
                type ietf-te-psc-types:egress-label;
            }
        }

    }

    grouping lsp-attributes {
        leaf end-to-end-routing {
            reference "RFC4920, RFC5420";
            type empty;
        }
        leaf boundary-rerouting {
            reference "RFC4920, RFC5420";
            type empty;
        }
        leaf segment-based-rerouting {
            reference "RFC4920, RFC5420";
            type empty;
        }
        leaf lsp-integrety-required {
            reference "RFC4875";
            type empty;
        }
        leaf contiguous-lsp {
            reference "RFC5151";
            type empty;
        }
        leaf lsp-stitching-desired {
            reference "RFC5150";
            type empty;
        }
        leaf preplanned-lsp {
            reference "RFC6001";
            type empty;
        }
        leaf non-php-desired {
            reference "RFC6511";
            type empty;
        }
        leaf oob-mapping {
            reference "RFC6511";
            type empty;
        }
        leaf entropy-label-cap {
            reference "RFC6790";
            type empty;
        }
        leaf oam-mep-entities-desired {
            reference "RFC7260";
            type empty;
        }
        leaf oam-mip-entities-desired {
            reference "RFC7260";
            type empty;
        }
    }

    grouping lsp-signaling-properties {
        description "LSP signaling properties.";
        uses lsp-attributes;
        leaf source {
            description
                "LSP source address.";
            type inet:ip-address;
        }
        container fast-reroute {
            presence "FRR local protection is desired.";
            reference
                "RFC4859: Registry for RSVP-TE Session Flags";
            leaf bandwidth-protection-desired {
                description
                    "Request FRR bandwidth protection on LSRs if
                    present.";
                type empty;
            }
            leaf node-protection-desired {
                description
                    "Request FRR node protection on LSRs if present.";
                type empty;
            }
        }
        leaf se-style-desired {
            description "SE Style desired";
            reference "RFC3209";
            type empty;
        }
        leaf soft-preemption-desired {
            description "Soft-preemption is desired";
            reference "RFC5712";
            type empty;
        }
        leaf record-route-desired {
            description "Path recording is desired.";
            reference "RFC3209";
            type empty;
        }
        leaf signaled-name {
            description
                "Sets the session name to use in the session attribute
                 object.";
            type string;
        }
        container priority {
            description
                "Sets the setup/hold priority to use in the session
                 attribute object.";
            leaf setup {
                type uint8 {
                     range "0..7";
                }
            }
            leaf hold {
                type uint8 {
                     range "0..7";
                }
            }
        }
        leaf soft-preemption {
            description
                "Requests soft-preemption in session
                 attributes object at
                 at traversed LSR(s).";
            type empty;
        }
    }

    /* RSVP-TE global propeerties */
    augment "/rsvp:rsvp/rsvp:globals" {
        container frr-local-revert {
            presence "Enable RSVP FRR local revertive recovery mode.";
            leaf frr-local-revert-delay {
                description
                    "Time to wait after primary link is restored
                    before node attempts local revertive procedures.";
                type uint32;
            }
        }
    }

    augment "/ietf-te:te/ietf-te:tunnels/ietf-te:tunnel" {
        uses lsp-signaling-properties;
    }

    /* Linkage to the base RSVP all links */
    augment "/rsvp:rsvp/rsvp:interfaces" {
        uses signaling;
    }

    /* Linkage to per RSVP link */
    augment "/rsvp:rsvp/rsvp:interfaces/rsvp:interface" {
        uses signaling;
    }

    /* TSAAD: add augmentation for sessions neighbors */
    augment "/rsvp:rsvp/rsvp:sessions" {
        /* To be added */
    }

    augment "/rsvp:rsvp/rsvp:neighbors" {
        /* To be added */
    }

    augment "/rsvp:rsvp/rsvp:sessions-state" {
        /* To be added */
    }

    augment "/rsvp:rsvp/rsvp:neighbors-state" {
        /* To be added */
    }
}
