module ietf-igmp-mld {
  yang-version 1.1;
  namespace "urn:ietf:params:xml:ns:yang:ietf-igmp-mld";
  prefix igmp-mld;

  import ietf-inet-types {
    prefix "inet";
    reference "RFC 6991: Common YANG Data Types";
  }

  import ietf-yang-types {
    prefix "yang";
    reference "RFC 6991: Common YANG Data Types";
  }

  import ietf-routing-types {
    prefix "rt-types";
    reference
      "RFC 8294: Common YANG Data Types for the Routing Area";
  }

  import ietf-access-control-list {
    prefix "acl";
    reference
      "RFC 8519: YANG Data Model for Network Access Control Lists
       (ACLs)";
  }

  import ietf-routing {
    prefix "rt";
    reference
      "RFC 8349: A YANG Data Model for Routing Management (NMDA
       Version)";
  }

  import ietf-interfaces {
    prefix "if";
    reference "RFC 8343: A YANG Data Model for Interface Management";
  }

  import ietf-ip {
    prefix ip;
    reference "RFC 8344: A YANG Data Model for IP Management";
  }

  organization
    "IETF PIM Working Group";
  contact
    "WG Web:   <http://tools.ietf.org/wg/pim/>
     WG List:  <mailto:pim@ietf.org>

     Editor:   Xufeng Liu
               <mailto:xufeng.liu.ietf@gmail.com>

     Editor:   Feng Guo
               <mailto:guofeng@huawei.com>

     Editor:   Mahesh Sivakumar
               <mailto:sivakumar.mahesh@gmail.com>

     Editor:   Pete McAllister
               <mailto:pete.mcallister@metaswitch.com>

     Editor:   Anish Peter
               <mailto:anish.ietf@gmail.com>";

  description
    "The module defines the configuration and operational state for
     the Internet Group Management Protocol (IGMP) and Multicast
     Listener Discovery (MLD) protocols.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  // RFC Ed.: replace XXXX with actual RFC number and remove
  // this note
  revision 2019-06-12 {
    description
      "Initial revision.";
    reference
      "RFC XXXX: A YANG Data Model for IGMP and MLD";
  }

  /*
   * Features
   */
  feature feature-igmp {
    description
      "Support IGMP protocol for IPv4 group membership record.";
  }

  feature feature-mld {
    description
      "Support MLD protocol for IPv6 group membership record.";
  }

  feature global-admin-enable {
    description
      "Support global configuration to enable or disable protocol.";
  }

  feature global-max-entries {
    description
      "Support configuration of global max-entries.";
  }

  feature global-max-groups {
    description
      "Support configuration of global max-groups.";
  }

  feature interface-global-config {
    description
      "Support global configuration applied for all interfaces.";
  }

  feature intf-admin-enable {
    description
      "Support configuration of interface administrative enabling.";
  }

  feature intf-immediate-leave {
    description
      "Support configuration of interface immediate-leave.";
  }

  feature intf-join-group {
    description
      "Support configuration of interface join-group.";
  }

  feature intf-max-groups {
    description
      "Support configuration of interface max-groups.";
  }
  feature intf-max-group-sources {
    description
      "Support configuration of interface max-group-sources.";
  }

  feature intf-require-router-alert {
    description
      "Support configuration of interface require-router-alert.";
  }

  feature intf-source-policy {
    description
      "Support configuration of interface source policy.";
  }

  feature intf-ssm-map {
    description
      "Support configuration of interface ssm-map.";
  }

  feature intf-static-group {
    description
      "Support configuration of interface static-group.";
  }

  feature intf-verify-source-subnet {
    description
      "Support configuration of interface verify-source-subnet.";
  }

  feature intf-explicit-tracking {
    description
      "Support configuration of interface explicit-tracking hosts.";
  }

  feature intf-lite-exclude-filter {
    description
      "Support configuration of interface lite-exclude-filter.";
  }

  feature per-interface-config {
    description
      "Support per interface configuration.";
  }

  feature action-clear-groups {
    description
      "Support actions to clear groups.";
  }

  /*
   * Typedefs
   */
  typedef ssm-map-ipv4-addr-type {
    type union {
      type enumeration {
        enum 'policy' {
          description
            "Source address is specified in SSM map policy.";
        }
      }
      type inet:ipv4-address;
    }
    description
      "Multicast source IP address type for SSM map.";
  } // source-ipv4-addr-type

  typedef ssm-map-ipv6-addr-type {
    type union {
      type enumeration {
        enum 'policy' {
          description
            "Source address is specified in SSM map policy.";
        }
      }
      type inet:ipv6-address;
    }
    description
      "Multicast source IP address type for SSM map.";
  } // source-ipv6-addr-type

  /*
   * Identities
   */
  identity igmp {
    base "rt:control-plane-protocol";
    description "IGMP protocol.";
    reference
      "RFC 3376: Internet Group Management Protocol, Version 3.";
  }

  identity mld {
    base "rt:control-plane-protocol";
    description "MLD protocol.";
    reference
      "RFC 3810: Multicast Listener Discovery Version 2 (MLDv2) for
       IPv6.";
  }

  /*
   * Groupings
   */
  grouping global-config-attributes {
    description
      "This grouping is used in either IGMP schema or MLD schema.
       When used in IGMP schema, this grouping contains the global
       configuration for IGMP;
       when used in MLD schema, this grouping contains the global
       configuration for MLD.";

    leaf enable {
      if-feature global-admin-enable;
      type boolean;
      default true;
      description
        "When this grouping is used for IGMP, this leaf indicates
         whether IGMP is enabled ('true') or disabled ('false')
         in the routing instance.
         When this grouping is used for MLD, this leaf indicates
         whether MLD is enabled ('true') or disabled ('false')
         in the routing instance.";
    }
    leaf max-entries {
      if-feature global-max-entries;
      type uint32;
      description
        "When this grouping is used for IGMP, this leaf indicates
         the maximum number of entries in the IGMP instance.
         When this grouping is used for MLD, this leaf indicates
         the maximum number of entries in the MLD instance.
         If this leaf is not specified, the number of entries is not
         limited.";
    }
    leaf max-groups {
      if-feature global-max-groups;
      type uint32;
      description
        "When this grouping is used for IGMP, this leaf indicates
         the maximum number of groups in the IGMP instance.
         When this grouping is used for MLD, this leaf indicates
         the maximum number of groups in the MLD instance.
         If this leaf is not specified, the number of groups is not
         limited.";
    }
  } // global-config-attributes
  grouping global-state-attributes {
    description
      "This grouping is used in either IGMP schema or MLD schema.
       When used in IGMP schema, this grouping contains the global
       IGMP state attributes;
       when used in MLD schema, this grouping contains the global
       MLD state attributes;";

    leaf entries-count {
      type uint32;
      config false;
      description
        "When this grouping is used for IGMP, this leaf indicates
         the number of entries in the IGMP instance.
         When this grouping is used for MLD, this leaf indicates
         the number of entries in the MLD instance.";
    }
    leaf groups-count {
      type uint32;
      config false;
      description
        "When this grouping is used for IGMP, this leaf indicates
         the number of existing groups in the IGMP instance.
         When this grouping is used for MLD, this leaf indicates
         the number of existing groups in the MLD instance.";
    }

    container statistics {
      config false;
      description
        "When this grouping is used for IGMP, this container contains
         the statistics for the IGMP instance.
         When this grouping is used for MLD, this leaf indicates
         the statistics for the MLD instance.";

      leaf discontinuity-time {
        type yang:date-and-time;
        description
          "The time on the most recent occasion at which any one
           or more of the statistic counters suffered a
           discontinuity. If no such discontinuities have occurred
           since the last re-initialization of the local
           management subsystem, then this node contains the time
           the local management subsystem re-initialized itself.";
      }
      container error {
        description "Statistics of errors.";
        uses global-statistics-error;
      }
      container received {
        description "Statistics of received messages.";
        uses global-statistics-sent-received;
      }
      container sent {
        description "Statistics of sent messages.";
        uses global-statistics-sent-received;
      }
    } // statistics
  } // global-state-attributes

  grouping global-statistics-error {
    description
      "A grouping defining statistics attributes for errors.";

    uses global-statistics-sent-received;
    leaf checksum {
      type yang:counter64;
      description
        "The number of checksum errors.";
    }
    leaf too-short {
      type yang:counter64;
      description
        "The number of messages that are too short.";
    }
  } // global-statistics-error

  grouping global-statistics-sent-received {
    description
      "A grouping defining statistics attributes.";

    leaf total {
      type yang:counter64;
      description
        "The number of total messages.";
    }
    leaf query {
      type yang:counter64;
      description
        "The number of query messages.";
    }
    leaf report {
      type yang:counter64;
      description
        "The number of report messages.";
    }
    leaf leave {
      type yang:counter64;
      description
        "The number of leave messages.";
    }
  } // global-statistics-sent-received

  grouping interface-global-config-attributes {
    description
      "Configuration attributes applied to the interface-global level
       whose per interface attributes are not configured.";

    leaf max-groups-per-interface {
      if-feature intf-max-groups;
      type uint32;
      description
        "The maximum number of groups associated with each interface.
         If this leaf is not specified, the number of groups is not
         limited.";
    }
  } //interface-global-config-attributes

  grouping interface-common-config-attributes {
    description
      "Configuration attributes applied to both the interface-global
       level and interface level.";

    leaf last-member-query-interval {
      type uint16 {
        range "1..1023";
      }
      units seconds;
      description
        "When used in IGMP schema, this leaf indicates the Last
         Member Query Interval, which may be tuned to modify the
         leave latency of the network;
         when used in MLD schema, this leaf indicates the Last
         Listener Query Interval, which may be tuned to modify the
         leave latency of the network.
         This leaf is not applicable for version 1 of the IGMP. For
         version 2 and version 3 of the IGMP, and for all versions of
         the MLD, the default value of this leaf is 1.
         This leaf may be configured at the interface level or the
         interface-global level, with precedence given to the value
         at the interface level. If the leaf is not configured at
         either level, the default value is used.";
      reference
        "RFC 2236. Sec. 8.8. RFC 3376. Sec. 8.8.
         RFC 2710. Sec. 7.8. RFC 3810. Sec. 9.8.";
    }
    leaf query-interval {
      type uint16 {
        range "1..31744";
      }
      units seconds;
      description
        "The Query Interval is the interval between General Queries
         sent by the Querier. In RFC 3376, the Querier's Query
         Interval(QQI) is represented from the Querier's Query
         Interval Code in query message as follows:
         If QQIC < 128, QQI = QQIC.
         If QQIC >= 128, QQIC represents a floating-point value as
         follows:
          0 1 2 3 4 5 6 7
         +-+-+-+-+-+-+-+-+
         |1| exp | mant  |
         +-+-+-+-+-+-+-+-+
         QQI = (mant | 0x10) << (exp + 3).
         The maximum value of QQI is 31744.
         The default value is 125.
         This leaf may be configured at the interface level or the
         interface-global level, with precedence given to the value
         at the interface level. If the leaf is not configured at
         either level, the default value is used.";
      reference "RFC 3376. Sec. 4.1.7, 8.2, 8.14.2.";
    }
    leaf query-max-response-time {
      type uint16 {
        range "1..1023";
      }
      units seconds;
      description
        "Query maximum response time specifies the maximum time
         allowed before sending a responding report.
         The default value is 10.
         This leaf may be configured at the interface level or the
         interface-global level, with precedence given to the value
         at the interface level. If the leaf is not configured at
         either level, the default value is used.";
      reference "RFC 3376. Sec. 4.1.1, 8.3, 8.14.3.";
    }
    leaf require-router-alert {
      if-feature intf-require-router-alert;
      type boolean;
      description
        "Protocol packets should contain router alert IP option.
         When this leaf is not configured, the server uses the
         following rules to determine the operational value of this
         leaf:
         if this grouping is used in IGMP schema and the value of the
         leaf 'version' is 1, the value 'false' is operationally used
         by the server;
         if this grouping is used in IGMP schema and the value of the
         leaf 'version' is 2 or 3, the value 'true' is operationally
         used by the server;
         if this grouping is used in MLD schema, the value 'true' is
         operationally used by the server.
         This leaf may be configured at the interface level or the
         interface-global level, with precedence given to the value
         at the interface level. If the leaf is not configured at
         either level, the default value is used.";
    }
    leaf robustness-variable {
      type uint8 {
        range "1..7";
      }
      description
        "Querier's Robustness Variable allows tuning for the
         expected packet loss on a network.
         The default value is 2.
         This leaf may be configured at the interface level or the
         interface-global level, with precedence given to the value
         at the interface level. If the leaf is not configured at
         either level, the default value is used.";
      reference "RFC 3376. Sec. 4.1.6, 8.1, 8.14.1.";
    }
  } // interface-common-config-attributes

  grouping interface-common-config-attributes-igmp {
    description
      "Configuration attributes applied to both the interface-global
       level and interface level for IGMP.";

    uses interface-common-config-attributes;
    leaf version {
      type uint8 {
        range "1..3";
      }
      description
        "IGMP version.
         The default value is 2.
         This leaf may be configured at the interface level or the
         interface-global level, with precedence given to the value
         at the interface level. If the leaf is not configured at
         either level, the default value is used.";
      reference "RFC 1112, RFC 2236, RFC 3376.";
    }
  }
  grouping interface-common-config-attributes-mld {
    description
      "Configuration attributes applied to both the interface-global
       level and interface level for MLD.";

    uses interface-common-config-attributes;
    leaf version {
      type uint8 {
        range "1..2";
      }
      description
        "MLD version.
         The default value is 2.
         This leaf may be configured at the interface level or the
         interface-global level, with precedence given to the value
         at the interface level. If the leaf is not configured at
         either level, the default value is used.";
      reference "RFC 2710, RFC 3810.";
    }
  }

  grouping interfaces-config-attributes-igmp {
    description
      "Configuration attributes applied to the interface-global
       level for IGMP.";

    uses interface-common-config-attributes-igmp;
    uses interface-global-config-attributes;
  }

  grouping interfaces-config-attributes-mld {
    description
      "Configuration attributes applied to the interface-global
       level for MLD.";

    uses interface-common-config-attributes-mld;
    uses interface-global-config-attributes;
  }

  grouping interface-level-config-attributes {
    description
      "This grouping is used in either IGMP schema or MLD schema.
       When used in IGMP schema, this grouping contains the IGMP
       configuration attributes that are defined at the interface
       level but are not defined at the interface-global level;
       when used in MLD schema, this grouping contains the MLD
       configuration attributes that are defined at the interface
       level but are not defined at the interface-global level.";
    leaf enable {
      if-feature intf-admin-enable;
      type boolean;
      default true;
      description
        "When this grouping is used for IGMP, this leaf indicates
         whether IGMP is enabled ('true') or disabled ('false')
         on the interface.
         When this grouping is used for MLD, this leaf indicates
         whether MLD is enabled ('true') or disabled ('false')
         on the interface.";
    }
    leaf group-policy {
      type leafref {
        path "/acl:acls/acl:acl/acl:name";
      }
      description
        "When this grouping is used for IGMP, this leaf specifies
         the name of the access policy used to filter the
         IGMP membership.
         When this grouping is used for MLD, this leaf specifies
         the name of the access policy used to filter the
         MLD membership.
         The value space of this leaf is restricted to the existing
         policy instances defined by the referenced schema RFC 8519.
         As specified by RFC 8519, the length of the name is between
         1 and 64; a device MAY further restrict the length of this
         name; space and special characters are not allowed.
         If this leaf is not specified, no policy is applied, and
         all packets received from this interface are accepted.";
      reference
        "RFC 8519: YANG Data Model for Network Access Control Lists
         (ACLs)";
    }
    leaf immediate-leave {
      if-feature intf-immediate-leave;
      type empty;
      description
        "When this grouping is used for IGMP, the presence of this
         leaf requests IGMP to perform an immediate leave upon
         receiving an IGMPv2 leave message.
         If the router is IGMP-enabled, it sends an IGMP last member
         query with a last member query response time. However, the
         router does not wait for the response time before it prunes
         the group.
         When this grouping is used for MLD, the presence of this
         leaf requests MLD to perform an immediate leave upon
         receiving an MLDv1 leave message.
         If the router is MLD-enabled, it sends an MLD last member
         query with a last member query response time. However, the
         router does not wait for the response time before it prunes
         the group.";
    }
    leaf max-groups {
      if-feature intf-max-groups;
      type uint32;
      description
        "When this grouping is used for IGMP, this leaf indicates
         the maximum number of groups associated with the IGMP
         interface.
         When this grouping is used for MLD, this leaf indicates
         the maximum number of groups associated with the MLD
         interface.
         If this leaf is not specified, the number of groups is not
         limited.";
    }
    leaf max-group-sources {
      if-feature intf-max-group-sources;
      type uint32;
      description
        "The maximum number of group sources.
         If this leaf is not specified, the number of group sources
         is not limited.";
    }
    leaf source-policy {
      if-feature intf-source-policy;
      type leafref {
        path "/acl:acls/acl:acl/acl:name";
      }
      description
        "Name of the access policy used to filter sources.
         The value space of this leaf is restricted to the existing
         policy instances defined by the referenced schema RFC 8519.
         As specified by RFC 8519, the length of the name is between
         1 and 64; a device MAY further restrict the length of this
         name; space and special characters are not allowed.
         If this leaf is not specified, no policy is applied, and
         all packets received from this interface are accepted.";
    }
    leaf verify-source-subnet {
      if-feature intf-verify-source-subnet;
      type empty;
      description
        "If present, the interface accepts packets with matching
         source IP subnet only.";
    }
    leaf explicit-tracking {
      if-feature intf-explicit-tracking;
      type empty;
      description
        "When this grouping is used for IGMP, the presence of this
         leaf enables IGMP-based explicit membership tracking
         function for multicast routers and IGMP proxy devices
         supporting IGMPv3.
         When this grouping is used for MLD, the presence of this
         leaf enables MLD-based explicit membership tracking
         function for multicast routers and MLD proxy devices
         supporting MLDv2.
         The explicit membership tracking function contributes to
         saving network resources and shortening leave latency.";
      reference
        "RFC 6636. Sec 3.";
    }
    leaf lite-exclude-filter {
      if-feature intf-lite-exclude-filter;
      type empty;
      description
        "When this grouping is used for IGMP, the presence of this
         leaf enables the support of the simplified EXCLUDE filter
         in the Lightweight IGMPv3 protocol, which simplifies the
         standard versions of IGMPv3.
         When this grouping is used for MLD, the presence of this
         leaf enables the support of the simplified EXCLUDE filter
         in the Lightweight MLDv2 protocol, which simplifies the
         standard versions of MLDv2.";
      reference "RFC 5790";
    }
  } // interface-level-config-attributes

  grouping interface-config-attributes-igmp {
    description
      "Per interface configuration attributes for IGMP.";

    uses interface-common-config-attributes-igmp;
    uses interface-level-config-attributes;
    leaf-list join-group {
      if-feature intf-join-group;
      type rt-types:ipv4-multicast-group-address;
      description
        "The router joins this multicast group on the interface.";
    }
    list ssm-map {
      if-feature intf-ssm-map;
      key "ssm-map-source-addr ssm-map-group-policy";
      description "The policy for (*,G) mapping to (S,G).";

      leaf ssm-map-source-addr {
        type ssm-map-ipv4-addr-type;
        description
          "Multicast source IPv4 address.";
      }
      leaf ssm-map-group-policy {
        type string;
        description
          "Name of the policy used to define ssm-map rules.
           A device can restrict the length
           and value of this name, possibly space and special
           characters are not allowed. ";
      }
    }
    list static-group {
      if-feature intf-static-group;
      key "group-addr source-addr";
      description
        "A static multicast route, (*,G) or (S,G).
         The version of IGMP must be 3 to support (S,G).";

      leaf group-addr {
        type rt-types:ipv4-multicast-group-address;
        description
          "Multicast group IPv4 address.";
      }
      leaf source-addr {
        type rt-types:ipv4-multicast-source-address;
        description
          "Multicast source IPv4 address.";
      }
    }
  } // interface-config-attributes-igmp

  grouping interface-config-attributes-mld {
    description
      "Per interface configuration attributes for MLD.";

    uses interface-common-config-attributes-mld;
    uses interface-level-config-attributes;
    leaf-list join-group {
      if-feature intf-join-group;
      type rt-types:ipv6-multicast-group-address;
      description
        "The router joins this multicast group on the interface.";
    }
    list ssm-map {
      if-feature intf-ssm-map;
      key "ssm-map-source-addr ssm-map-group-policy";
      description "The policy for (*,G) mapping to (S,G).";
      leaf ssm-map-source-addr {
        type ssm-map-ipv6-addr-type;
        description
          "Multicast source IPv6 address.";
      }
      leaf ssm-map-group-policy {
        type string;
        description
          "Name of the policy used to define ssm-map rules.
           A device can restrict the length
           and value of this name, possibly space and special
           characters are not allowed.";
      }
    }
    list static-group {
      if-feature intf-static-group;
      key "group-addr source-addr";
      description
        "A static multicast route, (*,G) or (S,G).
         The version of MLD must be 2 to support (S,G).";

      leaf group-addr {
        type rt-types:ipv6-multicast-group-address;
        description
          "Multicast group IPv6 address.";
      }
      leaf source-addr {
        type rt-types:ipv6-multicast-source-address;
        description
          "Multicast source IPv6 address.";
      }
    }
  } // interface-config-attributes-mld

  grouping interface-state-attributes {
    description
      "Per interface state attributes for both IGMP and MLD.";

    leaf oper-status {
      type enumeration {
        enum up {
          description
            "Ready to pass packets.";
        }
        enum down {
          description
            "The interface does not pass any packets.";
        }
      }
      config false;
      mandatory true;
      description
        "Indicates whether the operational state of the interface
         is up or down.";
    }
  } // interface-state-attributes

  grouping interface-state-attributes-igmp {
    description
      "Per interface state attributes for IGMP.";

    uses interface-state-attributes;
    leaf querier {
      type inet:ipv4-address;
      config false;
      mandatory true;
      description "The querier address in the subnet";
    }
    leaf-list joined-group {
      if-feature intf-join-group;
      type rt-types:ipv4-multicast-group-address;
      config false;
      description
        "The routers that joined this multicast group.";
    }
    list group {
      key "group-address";
      config false;
      description
        "Multicast group membership information
         that joined on the interface.";

      leaf group-address {
        type rt-types:ipv4-multicast-group-address;
        description
          "Multicast group address.";
      }
      uses interface-state-group-attributes;
      leaf last-reporter {
        type inet:ipv4-address;
        description
          "The IPv4 address of the last host which has sent the
           report to join the multicast group.";
      }
      list source {
        key "source-address";
        description
          "List of multicast source information
           of the multicast group.";

        leaf source-address {
          type inet:ipv4-address;
          description
            "Multicast source address in group record.";
        }
        uses interface-state-source-attributes;
        leaf last-reporter {
          type inet:ipv4-address;
          description
            "The IPv4 address of the last host which has sent the
             report to join the multicast source and group.";
        }
        list host {
          if-feature intf-explicit-tracking;
          key "host-address";
          description
            "List of hosts with the membership for the specific
             multicast source-group.";

          leaf host-address {
            type inet:ipv4-address;
            description
              "The IPv4 address of the host.";
          }
          uses interface-state-host-attributes;
        }// list host
      } // list source
    } // list group
  } // interface-state-attributes-igmp

  grouping interface-state-attributes-mld {
    description
      "Per interface state attributes for MLD.";

    uses interface-state-attributes;
    leaf querier {
      type inet:ipv6-address;
      config false;
      mandatory true;
      description
        "The querier address in the subnet.";
    }
    leaf-list joined-group {
      if-feature intf-join-group;
      type rt-types:ipv6-multicast-group-address;
      config false;
      description
        "The routers that joined this multicast group.";
    }
    list group {
      key "group-address";
      config false;
      description
        "Multicast group membership information
         that joined on the interface.";

      leaf group-address {
        type rt-types:ipv6-multicast-group-address;
        description
          "Multicast group address.";
      }
      uses interface-state-group-attributes;
      leaf last-reporter {
        type inet:ipv6-address;
        description
          "The IPv6 address of the last host which has sent the
           report to join the multicast group.";
      }
      list source {
        key "source-address";
        description
          "List of multicast sources of the multicast group.";

        leaf source-address {
          type inet:ipv6-address;
          description
            "Multicast source address in group record";
        }
        uses interface-state-source-attributes;
        leaf last-reporter {
          type inet:ipv6-address;
          description
            "The IPv6 address of the last host which has sent the
             report to join the multicast source and group.";
        }
        list host {
          if-feature intf-explicit-tracking;
          key "host-address";
          description
            "List of hosts with the membership for the specific
             multicast source-group.";

          leaf host-address {
            type inet:ipv6-address;
            description
              "The IPv6 address of the host.";
          }
          uses interface-state-host-attributes;
        }// list host
      } // list source
    } // list group
  } // interface-state-attributes-mld

  grouping interface-state-group-attributes {
    description
      "Per interface state attributes for both IGMP and MLD
       groups.";

    leaf expire {
      type uint32;
      units seconds;
      mandatory true;
      description
        "The time left before multicast group state expires.";
    }
    leaf filter-mode {
      type enumeration {
        enum "include" {
          description
            "In include mode, reception of packets sent
             to the specified multicast address is requested
             only from those IP source addresses listed in the
             source-list parameter";
        }
        enum "exclude" {
          description
            "In exclude mode, reception of packets sent
             to the given multicast address is requested
             from all IP source addresses except those
             listed in the source-list parameter.";
        }
      }
      mandatory true;
      description
        "Filter mode for a multicast group,
         may be either include or exclude.";
    }
    leaf up-time {
      type uint32;
      units seconds;
      mandatory true;
      description
        "The elapsed time since the device created multicast group
         record.";
    }
  } // interface-state-group-attributes

  grouping interface-state-source-attributes {
    description
      "Per interface state attributes for both IGMP and MLD
       source-group records.";

    leaf expire {
      type uint32;
      units seconds;
      mandatory true;
      description
        "The time left before multicast source-group state expires.";
    }
    leaf up-time {
      type uint32;
      units seconds;
      mandatory true;
      description
        "The elapsed time since the device created multicast
         source-group record.";
    }
    leaf host-count {
      if-feature intf-explicit-tracking;
      type uint32;
      description
        "The number of host addresses.";
    }
  } // interface-state-source-attributes

  grouping interface-state-host-attributes {
    description
      "Per interface state attributes for both IGMP and MLD
       hosts of source-group records.";

    leaf host-filter-mode {
      type enumeration {
        enum "include" {
          description
            "In include mode";
        }
        enum "exclude" {
          description
            "In exclude mode.";
        }
      }
      mandatory true;
      description
        "Filter mode for a multicast membership
         host may be either include or exclude.";
    }
  } // interface-state-host-attributes

  /*
   * Configuration and Operational state data nodes (NMDA version)
   */
  augment "/rt:routing/rt:control-plane-protocols/"
    + "rt:control-plane-protocol" {
    when "derived-from-or-self(rt:type, 'igmp-mld:igmp')" {
      description
        "This augmentation is only valid for a control-plane
         protocol instance of IGMP (type 'igmp').";
    }
    description
      "IGMP augmentation to routing control plane protocol
       configuration and state.";

    container igmp {
      if-feature feature-igmp;
      description
        "IGMP configuration and operational state data.";

      container global {
        description
          "Global attributes.";

        uses global-config-attributes;
        uses global-state-attributes;
      }
      container interfaces {
        description
          "Containing a list of interfaces.";

        uses interfaces-config-attributes-igmp {
          if-feature interface-global-config;
          refine query-interval {
            default 125;
          }
          refine query-max-response-time {
            default 10;
          }
          refine robustness-variable {
            default 2;
          }
          refine version {
            default 2;
          }
        }
        list interface {
          key "interface-name";
          description
            "List of IGMP interfaces.";

          leaf interface-name {
            type if:interface-ref;
            must "/if:interfaces/if:interface[if:name = current()]/"
              + "ip:ipv4" {
              error-message
                "The interface must have IPv4 configured, either "
                + "enabled or disabled.";
            }
            description
              "Reference to an entry in the global interface list.";
          }
          uses interface-config-attributes-igmp {
            if-feature per-interface-config;
            refine last-member-query-interval {
              must "../version != 1 or "
                + "(not(../version) and "
                + "(../../version != 1 or not(../../version)))" {
                error-message
                  "IGMPv1 does not support "
                  + "last-member-query-interval.";
              }
            }
            refine max-group-sources {
              must "../version = 3 or "
                + "(not(../version) and (../../version = 3))" {
                error-message
                  "The version of IGMP must be 3 to support the "
                  + "source specific parameters.";
              }
            }
            refine source-policy {
              must "../version = 3 or "
                + "(not(../version) and (../../version = 3))" {
                error-message
                  "The version of IGMP must be 3 to support the "
                  + "source specific parameters.";
              }
            }
            refine explicit-tracking {
              must "../version = 3 or "
                + "(not(../version) and (../../version = 3))" {
                error-message
                  "The version of IGMP must be 3 to support the "
                  + "explicit tracking function.";
              }
            }
            refine lite-exclude-filter {
              must "../version = 3 or "
                + "(not(../version) and (../../version = 3))" {
                error-message
                  "The version of IGMP must be 3 to support the "
                  + "simplified EXCLUDE filter in the Lightweight "
                  + "IGMPv3 protocol.";
              }
            }
          }
          uses interface-state-attributes-igmp;
        } // interface
      } // interfaces

      /*
       * Actions
       */
      action clear-groups {
        if-feature action-clear-groups;
        description
          "Clears the specified IGMP cache entries.";

        input {
          choice interface {
            mandatory true;
            description
              "Indicates the interface(s) from which the cache
               entries are cleared.";
            case name {
              leaf interface-name {
                type leafref {
                  path "/rt:routing/rt:control-plane-protocols/"
                    + "rt:control-plane-protocol/"
                    + "igmp-mld:igmp/igmp-mld:interfaces/"
                    + "igmp-mld:interface/igmp-mld:interface-name";
                }
                description
                  "Name of the IGMP interface.";
              }
            }
            case all {
              leaf all-interfaces {
                type empty;
                description
                  "IGMP groups from all interfaces are cleared.";
              }
            }
          }
          leaf group-address {
            type union {
              type enumeration {
                enum '*' {
                  description
                    "Any group address.";
                }
              }
              type rt-types:ipv4-multicast-group-address;
            }
            mandatory true;
            description
              "Multicast group IPv4 address.
               If the value '*' is specified, all IGMP group entries
               are cleared.";
          }
          leaf source-address {
            type rt-types:ipv4-multicast-source-address;
            mandatory true;
            description
              "Multicast source IPv4 address.
               If the value '*' is specified, all IGMP source-group
               entries are cleared.";
          }
        }
      } // action clear-groups
    } // igmp
  } //augment

  augment "/rt:routing/rt:control-plane-protocols/"
    + "rt:control-plane-protocol" {
    when "derived-from-or-self(rt:type, 'igmp-mld:mld')" {
      description
        "This augmentation is only valid for a control-plane
         protocol instance of IGMP (type 'mld').";
    }
    description
      "MLD augmentation to routing control plane protocol
       configuration and state.";

    container mld {
      if-feature feature-mld;
      description
        "MLD configuration and operational state data.";

      container global {
        description
          "Global attributes.";

        uses global-config-attributes;
        uses global-state-attributes;
      }
      container interfaces {
        description
          "Containing a list of interfaces.";

        uses interfaces-config-attributes-mld {
          if-feature interface-global-config;
          refine last-member-query-interval {
            default 1;
          }
          refine query-interval {
            default 125;
          }
          refine query-max-response-time {
            default 10;
          }
          refine require-router-alert {
            default true;
          }
          refine robustness-variable {
            default 2;
          }
          refine version {
            default 2;
          }
        }
        list interface {
          key "interface-name";
          description
            "List of MLD interfaces.";

          leaf interface-name {
            type if:interface-ref;
            must "/if:interfaces/if:interface[if:name = current()]/"
              + "ip:ipv6" {
              error-message
                "The interface must have IPv6 configured, either "
                + "enabled or disabled.";
            }
            description
              "Reference to an entry in the global interface list.";
          }
          uses interface-config-attributes-mld {
            if-feature per-interface-config;
            refine max-group-sources {
              must "../version = 2 or "
                + "(not(../version) and "
                + "(../../version = 2 or not(../../version)))" {
                error-message
                  "The version of MLD must be 2 to support the "
                  + "source specific parameters.";
              }
            }
            refine source-policy {
              must "../version = 2 or "
                + "(not(../version) and "
                + "(../../version = 2 or not(../../version)))" {
                error-message
                  "The version of MLD must be 2 to support the "
                  + "source specific parameters.";
              }
            }
            refine explicit-tracking {
              must "../version = 2 or "
                + "(not(../version) and "
                + "(../../version = 2 or not(../../version)))" {
                error-message
                  "The version of MLD must be 2 to support the "
                  + "explicit tracking function.";
              }
            }
            refine lite-exclude-filter {
              must "../version = 2 or "
                + "(not(../version) and "
                + "(../../version = 2 or not(../../version)))" {
                error-message
                  "The version of MLD must be 2 to support the "
                  + "simplified EXCLUDE filter in the Lightweight "
                  + "MLDv2 protocol.";
              }
            }
          }
          uses interface-state-attributes-mld;
        } // interface
      } // interfaces

      /*
       * Actions
       */
      action clear-groups {
        if-feature action-clear-groups;
        description
          "Clears the specified MLD cache entries.";
        input {
          choice interface {
            mandatory true;
            description
              "Indicates the interface(s) from which the cache
               entries are cleared.";
            case name {
              leaf interface-name {
                type leafref {
                  path "/rt:routing/rt:control-plane-protocols/"
                    + "rt:control-plane-protocol/"
                    + "igmp-mld:mld/igmp-mld:interfaces/"
                    + "igmp-mld:interface/igmp-mld:interface-name";
                }
                description
                  "Name of the MLD interface.";
              }
            }
            case all {
              leaf all-interfaces {
                type empty;
                description
                  "MLD groups from all interfaces are cleared.";
              }
            }
          }
          leaf group-address {
            type union {
              type enumeration {
                enum '*' {
                  description
                    "Any group address.";
                }
              }
              type rt-types:ipv6-multicast-group-address;
            }
            description
              "Multicast group IPv6 address.
               If the value '*' is specified, all MLD group entries
               are cleared.";
          }
          leaf source-address {
            type rt-types:ipv6-multicast-source-address;
            description
              "Multicast source IPv6 address.
               If the value '*' is specified, all MLD source-group
               entries are cleared.";
          }
        }
      } // action clear-mld-groups
    } // mld
  } // augment
}
