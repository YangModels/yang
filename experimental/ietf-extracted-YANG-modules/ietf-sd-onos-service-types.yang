module ietf-sd-onos-service-types { 
    namespace "urn:ietf:params:xml:ns:yang:ietf-sd-onos-service-types"; 
    prefix service-types ; 

    import ietf-inet-types {prefix inet; } 
    import ietf-sd-onos-common-types {prefix  types; revision-date "2015-10-
14";}
