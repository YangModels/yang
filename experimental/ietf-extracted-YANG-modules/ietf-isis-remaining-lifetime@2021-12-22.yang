module ietf-isis-remaining-lifetime {
  yang-version 1.1;
  namespace "urn:ietf:params:xml:ns:yang:ietf-isis-remaining-lifetime";

  prefix isis-remaining-lifetime;

  import ietf-isis {
    prefix "isis";
  }

  organization
    "IETF LSR - Link State Routing Working Group";

  contact
     "WG Web:   <http://tools.ietf.org/wg/lsr>
      WG List:  <mailto:lsr@ietf.org>
      Author:   Yingzhen Qu
                <mailto:yqu@futurewei.com>
      Author:   Acee Lindem
                <mailto:acee@cisco.com>
      Author:   Stephane Litkowski
                <mailto:slitkows.ietf@gmail.com>";

  description
    "This YANG module defines the configuration and operational
     state for IS-IS Minimum Remaining Lifetime feature as defined
     in RFC 7987.

     Copyright (c) 2021 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (http://trustee.ietf.org/license-info).

     This version of this YANG module is part of RFC XXXX;
     see the RFC itself for full legal notices.";

  reference "RFC XXXX";

  revision 2021-12-22 {
    description
      "Initial version";
    reference
      "RFC XXXX: A YANG Data Model for IS-IS Minimum Remaining
                 Lifetime";
  }

  notification corrupt-remaining-lifetime {
    uses isis:notification-instance-hdr;
    leaf lsp-id {
      type isis:lsp-id;
      description "LSP ID";
    }
    description
      "This notification is sent when the system
       detects corrupted lifetime of an LSP.";
    reference "RFC 7987: IS-IS Minimum Remaining Lifetime";
  }
}
