module ietf-bmp-telemetry-message {
  yang-version 1.1;
  namespace "urn:ietf:params:xml:ns:yang:ietf-bmp-telemetry-message";
  prefix bmp-tm;

  import ietf-telemetry-message {
    prefix tm;
    reference
      "I-D.ietf-nmop-message-broker-telemetry-message: Extensible
       YANG Model for Network Telemetry Messages";
  }
  import ietf-bmp {
    prefix bmp;
    reference
      "I-D.ietf-grow-bmp-yang: A YANG Data Model for BMP";
  }
  import ietf-inet-types {
    prefix inet;
    reference "RFC 6991: Common YANG Data Types";
  }
  import ietf-yang-types {
    prefix yang;
    reference "RFC 6991: Common YANG Data Types";
  }
  import ietf-routing-types {
    prefix rt-types;
    reference "RFC 8294: Common YANG Data Types for the Routing
               Area";
  }
  import ietf-yang-structure-ext {
    prefix sx;
    reference "RFC 8791: YANG Data Structure Extensions";
  }

  organization "IETF NMOP Working Group (proposed)";
  contact
    "Author: Saumya Dikshit
             <mailto:saumya.dikshit@hpe.com>
     Author: Mukul Srivastava
             <mailto:mukul.srivastava@hpe.com>
     Author: Changwang Lin
             <mailto:linchangwang@h3c.com>";
  description
    "This module augments the 'ietf-telemetry-message' envelope
     defined in I-D.ietf-nmop-message-broker-telemetry-message
     with provenance metadata specific to data collected via the
     BGP Monitoring Protocol (BMP), RFC 7854.

     Copyright (c) 2026 IETF Trust and the persons identified as
     authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).";

  revision 2026-07-25 {
    description
      "Initial revision.";
    reference
      "RFC XXXX";
  }

  identity bmp {
    base tm:session-protocol;
    description
      "BGP Monitoring Protocol (BMP) as defined in RFC 7854.";
    reference
      "RFC 7854: BGP Monitoring Protocol (BMP).";
  }

  identity bmp-message-type {
    description
      "Base identity for BMP message types, RFC 7854 Section 4.";
  }
  identity route-monitoring {
    base bmp-message-type;
    description "Route Monitoring message.";
  }
  identity statistics-report {
    base bmp-message-type;
    description "Statistics Report message.";
  }
  identity peer-down {
    base bmp-message-type;
    description "Peer Down Notification.";
  }
  identity peer-up {
    base bmp-message-type;
    description "Peer Up Notification.";
  }
  identity initiation {
    base bmp-message-type;
    description "Initiation Message.";
  }
  identity termination {
    base bmp-message-type;
    description "Termination Message.";
  }
  identity route-mirroring {
    base bmp-message-type;
    description "Route Mirroring Message.";
  }

  identity bmp-stat-extension {
    description
      "Base identity for BMP Statistics Report Stat Type
       registries/extensions.";
  }
  identity base-rfc7854 {
    base bmp-stat-extension;
    description "Base Stat Types defined in RFC 7854 Section 4.8.";
  }
  identity rfc9972-bgp-rib-stats {
    base bmp-stat-extension;
    description "Per-AFI/SAFI BGP RIB statistics, RFC 9972.";
  }
  identity informational-tlv {
    base bmp-stat-extension;
    description
      "Min/max/avg/median informational TLV extension,
       I-D.ietf-grow-bmp-stats-informational-tlv.";
  }
  identity afi-safi-evpn {
    base bmp-stat-extension;
    description
      "Per-EVI EVPN BMP RIB statistics,
       I-D.saum-grow-bmp-afi-safi-evpn.";
  }
  identity route-change-stats {
    base bmp-stat-extension;
    description
      "Per-peer route-attribute-change statistics,
       I-D.smc-grow-bmp-route-change-stats.";
  }
  identity rd-scoped-rib-stats {
    base bmp-stat-extension;
    description
      "Address-family-agnostic RD-scoped statistics container,
       I-D.dikshit-grow-bmp-rd-scoped-rib-stats.";
  }

  sx:augment-structure "/tm:message/tm:telemetry-message-metadata" {
    description
      "Augments telemetry-message-metadata with BMP-specific
       provenance metadata.";
    container bmp-session {
      when "../session-protocol = 'bmp-tm:bmp'";
      description
        "BMP-specific provenance for this telemetry message.";
      leaf monitoring-station-id {
        type string;
        description
          "Identifier of the BMP monitoring station configuration
           (RFC 7854 Section 3.1; see also the 'monitoring-station'
           list in I-D.ietf-grow-bmp-yang) under which this message
           was collected.";
      }
      leaf message-type {
        type identityref {
          base bmp-message-type;
        }
        mandatory true;
        description
          "BMP message type of the payload carried in this
           telemetry message.";
        reference "RFC 7854 Section 4.";
      }
      container peer-header {
        description
          "Fields from the BMP Per-Peer Header, RFC 7854
           Section 4.2, relevant to routing/filtering telemetry
           messages without payload inspection.";
        leaf peer-type {
          type identityref {
            base bmp:peer-type;
          }
          description "BMP peer type.";
        }
        leaf peer-distinguisher {
          type rt-types:route-distinguisher;
          description
            "Route Distinguisher, present when the peer type
             indicates an L3VPN peer.";
        }
        leaf peer-address {
          type inet:ip-address;
          description "BMP peer IP address.";
        }
        leaf peer-as {
          type inet:as-number;
          description "BMP peer Autonomous System number.";
        }
        leaf peer-bgp-id {
          type yang:dotted-quad;
          description "BMP peer BGP Identifier.";
        }
      }
      container route-monitoring-scope {
        description
          "Scope of a Route Monitoring or Statistics Report
           message, mirroring the network-instance / RIB-type /
           address-family hierarchy of I-D.ietf-grow-bmp-yang.";
        leaf network-instance {
          type string;
          description "Network instance name.";
        }
        leaf rib-type {
          type identityref {
            base bmp:afi-safi-type;
          }
          description
            "Address family of the RIB this message concerns.";
        }
        leaf route-distinguisher {
          type rt-types:route-distinguisher;
          description
            "Route Distinguisher, when this message is scoped to
             a specific VRF/EVI/MVPN instance (see
             I-D.saum-grow-bmp-afi-safi-evpn and
             I-D.dikshit-grow-bmp-rd-scoped-rib-stats).";
        }
      }
      leaf stat-extension {
        type identityref {
          base bmp-stat-extension;
        }
        description
          "For Statistics Report messages, identifies which Stat
           Type registry/extension the payload's Stat Data belongs
           to, without requiring payload inspection.";
      }
    }
  }
}
