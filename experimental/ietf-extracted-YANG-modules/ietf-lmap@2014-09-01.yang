module ietf-lmap {

  namespace "urn:ietf:params:xml:ns:yang:ietf-lmap";
  prefix "lmap";

  import ietf-yang-types {
    prefix yang;
  }

  import ietf-inet-types {
    prefix inet;
  }
  import ietf-interfaces {
    prefix if;
  }

  organization
    "IETF Large-Scale Measurement Platforms Working Group";

  contact
    "WG Web:   <http://tools.ietf.org/wg/lmap/>
     WG List:  <mailto:lmap@ietf.org>

     Editor:   Juergen Schoenwaelder
               <j.schoenwaelder@jacobs-university.de>

     Editor:   Vaibhav Bajpai
               <v.bajpai@jacobs-university.de>";

  description
    "This module defines a data model for Large-Scale Measurement
     Platforms (LMAP).";

  revision "2014-09-01" {
    description
     "Initial version";
    reference
     "RFC XXX: A YANG Data Model for LMAP Measurement Agents";
  }

  /*
   * Typedefs
   */

  typedef weekday {
    type enumeration {
      enum sunday {
        description "Sunday of the week";
      }
      enum monday {
        description "Monday of the week";
      }
      enum tuesday {
        description "Tuesday of the week";
      }
      enum wednesday {
        description "Wednesday of the week";
      }
      enum thursday {
        description "Thursday of the week";
      }
      enum friday {
        description "Friday of the week";
      }
      enum saturdary {
        description "Saturday of the week";
      }
    }
    description
     "A type modeling the weekdays in the Greco-Roman
      tradition.";
  }

  typedef month {
    type enumeration {
      enum january {
        description "January of the Julian and Gregorian calendar";
      }
      enum february {
        description "February of the Julian and Gregorian calendar";
      }
      enum march {
        description "March of the Julian and Gregorian calendar";
      }
      enum april {
        description "April of the Julian and Gregorian calendar";
      }
      enum may {
        description "May of the Julian and Gregorian calendar";
      }
      enum june {
        description "June of the Julian and Gregorian calendar";
      }
      enum july {
        description "July of the Julian and Gregorian calendar";
      }
      enum august {
        description "August of the Julian and Gregorian calendar";
      }
      enum september {
        description "September of the Julian and Gregorian calendar";
      }
      enum october {
        description "October of the Julian and Gregorian calendar";
      }
      enum november {
        description "November of the Julian and Gregorian calendar";
      }
      enum december {
        description "December of the Julian and Gregorian calendar";
      }
    }
    description
      "A type modeling the month in the Julian and Gregorian
       tradition.";
  }

  typedef timezone-offset {
    type string {
      pattern 'Z|[\+\-]\d{2}:\d{2}';
    }
    description
      "A timezone-offset as it is use in the yang:date-and-time
       type. The value Z is equivalent to +00:00. The value -00:00
       indicates and unknown time-offset.";
  }

  /*
   * Groupings
   */

  grouping timing-start-end-grouping {
    description
      "A grouping that provides start and end times for
       timing objects.";
    leaf start {
      type yang:date-and-time;
      description
        "The date and time when the timing object
         starts to create triggers.";
    }
    leaf end {
      type yang:date-and-time;
      description
        "The date and time when the timing object
         stops to create triggers.

         It is generally a good idea to always configure
         an end time and to refresh the configuration
         of timing object as needed to ensure that agents
         that loose connectivity to their controller
         do not continue their tasks forever.";
    }
  }

  grouping task-grouping {
    description
      "A grouping that defines the configuration of a task.";

    list task {
      key name;
      description
        "The list of tasks configured on the LMAP agent.";

      leaf name {
        type string;
        description
          "The unique name of a task.";
      }

      choice task-identification {
        mandatory true;
        description
          "Information that identifies the task.";

        leaf registry {
          type inet:uri;
          description
            "The registry entry identifying the configured task.";
        }

        leaf program {
          type string;
          description
            "The (local) program to invoke in order to execute
               the task.";
        }
      }

      list option {
        key "name";
        ordered-by user;

        description
          "The options passed to the task. This is a list of key /
           value pairs and may be used to model command line
           options and to identify the role.";

        leaf name {
          type string;
          description
            "The name of the option.";
        }

        leaf value {
          type string;
          description
            "The value of the option.";
        }
      }

      leaf-list tag {
        type string;
        description
          "A tag contains additional information that is passed
           with the result record to the collector. A tag can be
           used to carry the Measurement Cycle ID.";
      }

      leaf suppress-by-default {
        type boolean;
        default true;
        description
          "Indicates whether the task will be suppressed by
           a default supression.";
      }
    }
  }

  /*
   * Configuration data nodes
   */

  container lmap {
    description
      "Configuration of the LMAP agent.";

    /*
     *
     */

    container agent {
      description
        "Configuration of parameters affecting the whole
         measurement agent.";

      leaf agent-id {
        type yang:uuid;
        description
          "The agent-id identifies a measurement agent with
           a very low probability of collision. In certain
           deployments, the agent-id may be considered
           sensitive and hence this object is optional.";
      }

      leaf device-id {
        type inet:uri;
        description
          "The device-id identifies a property of the
           device running the measurement agent. In certain
           deployments, the device-id may be considered
           sensitive and hence this object is optional.";
      }

      leaf credentials {
        type string;
        description
          "The credentials of the agent.";
        // XXX: This is way too simplistic. Credentials are
        //      specific to the authentication mechanism used
        //      by a protocol. Hence, this needs to be a far
        //      more complex and extensible choice or it might
        //      not be needed since the protocol data models
        //      already cover it.
      }

      leaf group-id {
        type string;
        description
          "The group-id identifies a group of measurement
           agents. In certain deployments, the group-id
           may be considered less sensitive than the
           agent-id.";
      }

      leaf report-agent-id {
        type boolean;
        default false;
        // XXX: write a must expression that requires
        // group-id to be configured when this is true?
        description
          "The 'report-agent-id' controls whether the
           'agent-id' is reported to collectors if the
           'group-id' is configured. If the 'group-id'
           is not configured, the agent-id is always
           reported.";
      }
    }

    /*
     * Common Information Objects: Schedules
     */

    container schedules {
      description
        "Configuration of LMAP schedules. Schedules control with
         tasks are executed by the LMAP implementation.";

      list schedule {
        key name;
        description
          "Configuration of a particular schedule.";

        leaf name {
          type string;
          description
            "The locally-unique, administratively assigned name for
             this scheduled task.";
        }

        container action {
          description
            "An action describes the tasks started by the schedule.";

          leaf-list task {
            type leafref {
              path "/lmap/tasks/task/name";
            }
            description
              "The tasks invoked by this schedule.";
          }

          // XXX: the name 'downstream-task' should be improved
          leaf-list downstream-task {
            type leafref {
              path "/lmap/tasks/task/name";
            }
            description
              "The downstream tasks that receive input from all the
               tasks invoked by this schedule. Implementation have
               to ensure that task / downstream task relationships
               are cycle-free.";
          }
          leaf-list channel {
            type leafref {
              path "/lmap/channels/channel/name";
            }
            description
              "The channel used by the task (e.g., the channel used
               by a reporting task). The channel may be ignored by
               the task does not use channels.";
          }
        }

        leaf timing {
          type leafref {
            path "/lmap/timings/timing/name";
          }
          description
            "The timing source controlling the start of the scheduled
             tasks.";
        }
      }
    }

    /*
     * Suppression
     */

    container suppression {
      description
        "Suppression information to prevent schedules to start
         certain tasks.";

      leaf enabled {
        type boolean;
        default false;
        description
          "Setting 'enabled' to true will suppress all tasks that
           where suppress-by-default is true.";
      }

      leaf stop-ongoing-tasks {
        type boolean;
        default false;
        description
          "Setting 'stop-ongoing-tasks' to true will cause
           running tasks to be terminated if 'enabled' is set
           to true. Otherwise, running tasks will not be
           affected.";
      }

      leaf start {
        type yang:date-and-time;
        description
          "The date and time when supression starts to
           become effective. If not present, supression
           becomes effective immeditately when 'enabled'
           is set to true.";
      }

      leaf end {
        type yang:date-and-time;
        description
          "The date and time when supression stops to
           be effective. If not present, supression
           continues indefinite until 'enabled' is set
           to false.";
      }

      leaf-list task {
        type leafref {
          path "/lmap/tasks/task/name";
        }
        description
          "A specific task to suppress. If no tasks are
           listed, then all tasks will be suppressed.";
      }

      leaf-list schedule {
        type leafref {
          path "/lmap/schedules/schedule/name";
        }
        description
          "A specific schedule to suppress. If no schedules
           are listed, then all schedules will be suppressed.";
      }

    }

    /*
     * Common Information Objects: Channels
     */

    container channels {
      description
        "A channel describes properties of an LMAP control or
         reporting channel.";

      list channel {
        key name;
        description
          "The list of channels configured on the LMAP agent.";

        leaf name {
          type string;
          description
            "The unique name of a channel.";
        }

        leaf url {
          type inet:uri;
          description
            "The remote endpoint of the channel.";
        }

        leaf credentials {
          type string;
          description
            "The credentials of the channel.";
          // XXX: This is way too simplistic. Credentials are
          //      specific to the authentication mechanism used
          //      by a protocol. Hence, this needs to be a far
          //      more complex and extensible choice.
        }

        leaf interface {
          type leafref {
            path "/if:interfaces/if:interface/if:name";
          }
          description
            "The local interface to use for reaching the remote
             endpoint of the channel.";
        }
      }
    }

    /*
     * Common Information Objects: Task Configurations
     */

    container tasks {
      description
        "Configuration of LMAP tasks.";

      uses task-grouping;
    }

    /*
     * Common Information Objects: Timing Information
     */

    container timings {
      description
        "Configuration of LMAP timings.

         Implementations may be forced to delay acting
         upon triggers in the face of local constraints.
         A task triggered therefore not rely on the accuracy
         provided by the scheduler implementation.";

      list timing {
        key name;
        description
          "The list of timings configured on the LMAP agent.";

        leaf name {
          type string;
          description
            "The unique name of a timing.";
        }

        choice timing-type {
          description
            "Different types of timing objects are handled by
             different branches of this choices.";

          case periodic {
            container periodic {
              description
                "A periodic timing object triggers periodically
                 driven by a regular interval.";

              leaf interval {
                type uint32;
                units "milliseconds";
                mandatory true;
                description
                  "The number of milliseconds between two triggers
                    generated by this periodic timing object.

                    The execution system must not generate triggers
                    for periodic timing objects that have a interval
                    value of 0. A timing object with an interval of
                    0 milliseconds will therefore never trigger.";
              }
              uses timing-start-end-grouping;
            }
          }
          case calendar {
            container calendar {
              description
                "A calendar timing object trigger based on the
                 current calendar date and time.";

              leaf-list month {
                type month;
                description
                  "A month at which this calendar timing will
                   trigger.";
              }
              leaf-list weekday {
                type weekday;
                description
                  "A weekday at which this calendar timing will
                   trigger.";
              }
              leaf-list day-of-months {
                type int8 {
                  range "-31..-1 | 1..31";
                }
                description
                  "A day in the months at which this calendar
                   timing will trigger. Negative numbers indicate
                   days counted backwards from the end of the
                   months.";
              }
              leaf-list hour {
                type int8 {
                  range "0..23";
                }
                description
                  "An hour at which this calendar timing will
                   trigger.";
              }
              leaf-list minute {
                type int8 {
                  range "0..59";
                }
                description
                  "A minute at which this calendar timing will
                   trigger.";
              }
              leaf-list second {
                type int8 {
                  range "0..59";
                }
                description
                  "A second at which this calendar timing will
                   trigger.";
              }
              leaf timezone-offset {
                type timezone-offset;
                description
                  "The timezone in which this calendar timing
                   object will be evaluated.";
              }
              uses timing-start-end-grouping;
            }
          }
          case one-off {
            leaf one-off-time {
              type yang:date-and-time;
              mandatory true;
              description
                "This one-off timing object triggers once at the
                 configured one-off-time.";
            }
          }
          case immediate {
            leaf immediate {
              type empty;
              mandatory true;
              description
                "This immediate timing object triggers immediately
                 when it is configured.";
            }
          }
          case startup {
            leaf startup {
              type empty;
              mandatory true;
              description
                "This startup timing object triggers whenever the
                 LMAP agent (re)starts.";
            }
          }
        }

        leaf random-spread {
          type int32;
          units milliseconds;
          description
            "This optional leaf adds a random spread to the
           computation of the trigger.";
        }
      }
    }
  }

  container lmap-state {
    config false;
    description
      "A tree exporting state information about the LMAP agent.";

    container agent {
      description
        "Operations state of the measurement agent.";

      leaf agent-id {
        type yang:uuid;
        mandatory true;
        description
          "The agent-id identifies a measurement agent with
           a very low probability of collision. In certain
           deployments, the agent-id may be considered
           sensitive and hence this object is optional.";
      }

      leaf device-id {
        type inet:uri;
        mandatory true;
        description
          "The device-id identifies a property of the
           device running the measurement agent. In certain
           deployments, the device-id may be considered
           sensitive and hence this object is optional.";
      }
      leaf hardware {
        type string;
        mandatory true;
        description
          "A short description of the hardware the measurement
           agent is running on. This should include the version
           number of the hardware";
      }
      leaf firmware {
        type string;
        mandatory true;
        description
          "A short description of the firmware the measurement
           agent is running on. This should include the version
           number of the firmware.";
      }
      leaf version {
        type string;
        mandatory true;
        description
          "A short description of the software implementing the
           measurement agent. This should include the version
           number of the measurement agent software.";
      }
    }

    container capabilities {
      description
        "The capabilities of the measurement agent.";

      container tasks {
        description
          "Available LMAP tasks.";

        list task {
          key name;
          description
            "The list of tasks available on the LMAP agent.";

          leaf name {
            type string;
            description
              "The unique name of a task.";
          }

          choice task-identification {
            mandatory true;
            description
              "Information that identifies the task.";

            leaf registry {
              type inet:uri;
              description
                "The registry entry identifying the configured task.";
            }

            leaf program {
              type string;
              description
                "The (local) program to invoke in order to execute
               the task.";
            }
          }
        }
      }
    }

    container status {
      description
        "The status of the measurement agent.";

      leaf last-measurement {
        type yang:date-and-time;
        mandatory true;
        description
          "The date and time of the last invocation of a
           measurement task.";
      }

      leaf last-report {
        type yang:date-and-time;
        mandatory true;
        description
          "The date and time of the last invocation of a
           reporting task.";
      }

      leaf last-configuration {
        type yang:date-and-time;
        mandatory true;
        description
          "The date and time the lmap configuration was
           last updated.";
      }

      leaf failures {
        type yang:counter32;
        mandatory true;
        description
          "The number of failures that occurred while invoking
            scheduled tasks.";
      }

      leaf last-failed {
        type yang:date-and-time;
        mandatory true;
        description
          "The date and time when the most recent failure
           occurred.";
      }
    }
  }

  notification report {
    description
      "The result record produced by a certain task.";

    leaf date {
      type yang:date-and-time;
      mandatory true;
      description
        "The date and time when this report was sent.";
    }

    leaf agent-id {
      type yang:uuid;
      description
        "The agent-id of the agent from which this
         report originates.";
    }

    leaf group-id {
      type string;
      description
        "The group-id of the agent from which this
         report originates.";
    }

    uses task-grouping;

    container header {
      description
        "The header of the result records.";

      leaf-list column {
        type string;
        description
          "A header of a column in the result rows.";
      }
    }

    list row {
      description
        "The rows of the result record.";

      leaf start {
        type yang:date-and-time;
        mandatory true;
        description
          "The date and time when the measurement producing
           this result row started.";
      }

      leaf end {
        type yang:date-and-time;
        description
          "The date and time when the measurement producing
           this result row stopped.";
      }

      leaf-list conflict {
        // XXX: Unclear what this string contains since tasks
        // lifetime in config is different from result record
        // lifetime (buffering).
        type string;
        description
          "The name of a task overlapping with the execution
           of the task that has produced this result record.";
      }

      leaf cross-traffic {
        type uint64;
        description
          "The number of bytes of non-measurement traffic on
           the measurement interface(s) during the measurement
           period.";
      }

      leaf-list value {
        // XXX: Should this be a union? At the end, all is
        // a string.
        type string;
        description
          "The value of a cell in the result.";
      }
    }
  }
}
