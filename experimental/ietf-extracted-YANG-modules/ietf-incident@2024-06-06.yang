module ietf-incident {
  yang-version 1.1;
  namespace "urn:ietf:params:xml:ns:yang:ietf-incident";
  prefix inc;

  import ietf-yang-types {
    prefix yang;
    reference
      "RFC 6991: Common YANG Data Types";
  }
  import ietf-alarms {
    prefix al;
    reference
      "RFC 8632: A YANG Data Model for Alarm Management";
  }
  import ietf-network {
    prefix nw;
    reference
      "RFC 8345: A YANG Data Model for Network Topologies";
  }
  import ietf-yang-structure-ext {
    prefix sx;
  }
  organization
    "IETF NMOP Working Group";
  contact
    "WG Web:   <https://datatracker.ietf.org/wg/nmop/>;
     WG List:  <mailto:nmop@ietf.org>

     Author:   Chong Feng
               <mailto:frank.fengchong@huawei.com>
     Author:   Tong Hu
               <mailto:hutong@cmhi.chinamobile.com>
     Author:   Luis Miguel Contreras Murillo
               <mailto:luismiguel.contrerasmurillo@telefonica.com>
     Author :  Qin Wu
               <mailto:bill.wu@huawei.com>
     Author:   Chaode Yu
               <mailto:yuchaode@huawei.com>
     Author:   Nigel Davis
               <mailto:ndavis@ciena.com>";
  description
    "This module defines the interfaces for incident management
     lifecycle.

     This module is intended for the following use cases:
     * incident lifecycle management:
       - incident report: report incident instance to client
                          when an incident instance is detected.
       - incident acknowledge: acknowledge an incident instance.
       - incident diagnose: diagnose an incident instance.
       - incident resolve: resolve an incident instance.

     Copyright (c) 2024 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); ; see the RFC
     itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here. ";

  revision 2024-06-06 {
    description
      "Merge incident yang with incident type yang
       and fix broken ref.";
    reference
      "RFC XXX: YANG module for network incident management.";
  }

  // Identities

  identity incident-domain {
    description
      "The abstract identity to indicate the domain of
       an incident.";
  }

  identity single-domain {
    base incident-domain;
    description
      "single domain.";
  }

  identity access {
    base single-domain;
    description
      "access domain.";
  }

  identity ran {
    base access;
    description
      "radio access network domain.";
  }

  identity transport {
    base single-domain;
    description
      "transport domain.";
  }

  identity otn {
    base transport;
    description
      "optical transport network domain.";
  }

  identity ip {
    base single-domain;
    description
      "ip domain.";
  }

  identity ptn {
    base ip;
    description
      "packet transport network domain.";
  }

  identity cross-domain {
    base incident-domain;
    description
      "cross domain.";
  }

  identity incident-category {
    description
      "The abstract identity for incident category.";
  }

  identity device {
    base incident-category;
    description
      "device category.";
  }

  identity power-environment {
    base device;
    description
      "power environment category.";
  }

  identity device-hardware {
    base device;
    description
      "hardware of device category.";
  }

  identity device-software {
    base device;
    description
      "software of device category";
  }

  identity line {
    base device-hardware;
    description
      "line card category.";
  }

  identity maintenance {
    base incident-category;
    description
      "maintenance category.";
  }

  identity network {
    base incident-category;
    description
      "network category.";
  }

  identity protocol {
    base incident-category;
    description
      "protocol category.";
  }

  identity overlay {
    base incident-category;
    description
      "overlay category";
  }

  identity vm {
    base incident-category;
    description
      "vm category.";
  }

  identity event-type {
    description
      "The abstract identity for Event type";
  }

  identity alarm {
    base event-type;
    description
      "alarm event type.";
  }

  identity notif {
    base event-type;
    description
      "Notification event type.";
  }

  identity log {
    base event-type;
    description
      "Log event type.";
  }

  identity KPI {
    base event-type;
    description
      "KPI event type.";
  }

  identity unknown {
    base event-type;
    description
      "Unknown event type.";
  }

  identity incident-class {
    description
      "The abstract identity for Incident category.";
  }

  identity problem {
    base incident-class;
    description
      "It indicates the class of the incident is a problem
             (i.e.,cause of the incident) for example an interface
             fails to work.";
  }

  identity sla-violation {
    base incident-class;
    description
      "It indicates the class of the incident is a sla
       violation, for example high CPU rate may cause
       a fault in the future.";
  }

  identity acknowledge-error {
    description
      "Base identity for the problem found while attempting
       to fulfill an 'incident-acknowledge' RPC request.";
  }

  identity diagnose-error {
    description
      "Base identity for the problem found while attempting
       to fulfill an 'incident-diagnose' RPC request.";
  }

  identity resolve-error {
    description
      "Base identity for the problem found while attempting
       to fulfill an 'incident-resolve' RPC request.";
  }

  identity repeated-acknowledge {
    base acknowledge-error;
    description
      "The incident referred to has already been acknowledged.";
  }

  identity probable-cause-unlocated {
    base diagnose-error;
    description
      "Fails to locate the probable causes when performing the
       diagnosis operation. The detailed reason MUST be included
       in the 'description'.";
  }

  identity probable-cause-unresolved {
    base resolve-error;
    description
      "Fails to resolve the probable causes when performing the
       resolution operation. The detailed reason MUST be included
       in the 'description'";
  }

  identity permission-denied {
    base diagnose-error;
    base resolve-error;
    description
      "The permission required for performing specific
       detection/resolution task is not granted.";
  }

  identity operation-timeout {
    base diagnose-error;
    base resolve-error;
    description
      "The diagnosis/resolution time exceeds the preset time.";
  }

  identity resource-unavailable {
    base diagnose-error;
    base resolve-error;
    description
      "The resource is unavailable to perform
       the diagnosis/resolution operation.";
  }

  identity cause-name {
    description
      "Base identity for the cause name.";
  }

  // Typedefs

  typedef incident-priority {
    type enumeration {
      enum critical {
        description
          "the incident MUST be handled immediately.";
      }
      enum high {
        description
          "the incident should be handled as soon as
           possible.";
      }
      enum medium {
        description
          "network services are not affected, or the
           services are slightly affected,but corrective
           measures need to be taken.";
      }
      enum low {
        description
          "potential or imminent service-affecting
           incidents are detected,but services are
           not affected currently.";
      }
    }
    description
      "define the priority of incident.";
  }

  typedef incident-ref {
    type leafref {
      path "/inc:incidents/inc:incident/inc:incident-no";
    }
    description
      "reference a network incident.";
  }

  // Groupings

  grouping probable-cause-info {
    description
      "The information of probable cause.";
    leaf cause-name {
      type identityref {
        base cause-name;
      }
      description
        "the name of cause.";
    }
    leaf detail {
      type string;
      description
        "the detail information of the cause.";
    }
  }

  grouping resources-info {
    description
      "the grouping which defines the network
       resources of a node.";
    uses nw:node-ref;
    list resource {
      key "name";
      description
        "the resources of a network node.";
      leaf name {
        type al:resource;
        description
          "network resource name.";
      }
    }
  }

  grouping incident-time-info {
    description
      "the grouping defines incident time information.";
    leaf raise-time {
      type yang:date-and-time;
      description
        "the time when an incident instance is raised.";
    }
    leaf occur-time {
      type yang:date-and-time;
      description
        "the time when an incident instance occurs.
         It's the occur time of the first event during
         incident detection.";
    }
    leaf clear-time {
      type yang:date-and-time;
      description
        "the time when an incident instance is
         resolved.";
    }
    leaf ack-time {
      type yang:date-and-time;
      description
        "the time when an incident instance is
         acknowledged.";
    }
    leaf last-updated {
      type yang:date-and-time;
      description
        "the latest time when an incident instance is
         updated";
    }
  }

  grouping incident-info {
    description
      "the grouping defines the information of an
       incident.";
    leaf name {
      type string;
      mandatory true;
      description
        "the name of an incident.";
    }
    leaf type {
      type identityref {
        base incident-class;
      }
      mandatory true;
      description
        "The type of an incident.";
    }
    leaf incident-id {
      type string;
      description
        "The unique qualifier of an incident instance type.
        This leaf is used when the 'type' leaf cannot
        uniquely identify the incident instance type.  Normally,
        this is not the case, and this leaf is the empty string.";
    }
    leaf-list service-instance {
      type string;
      description
        "the related network service instances of
         the incident instance.";
    }
    leaf domain {
      type identityref {
        base incident-domain;
      }
      mandatory true;
      description
        "the domain of an incident.";
    }
    leaf priority {
      type incident-priority;
      mandatory true;
      description
        "the priority of an incident instance.";
    }
    leaf status {
      type enumeration {
        enum raised {
          description
            "an incident instance is raised.";
        }
        enum updated {
          description
            "the information of an incident instance
             is updated.";
        }
        enum cleared {
          description
            "an incident is cleared.";
        }
      }
      default "raised";
      description
        "The status of an incident instance.";
    }
    leaf ack-status {
      type enumeration {
        enum acknowledged {
          description
            "The incident has been acknowledged by user.";
        }
        enum unacknowledged {
          description
            "The incident hasn't been acknowledged.";
        }
      }
      default "unacknowledged";
      description
        "the acknowledge status of an incident.";
    }
    leaf category {
      type identityref {
        base incident-category;
      }
      mandatory true;
      description
        "The category of an incident.";
    }
    leaf detail {
      type string;
      description
        "detail information of this incident.";
    }
    leaf resolve-advice {
      type string;
      description
        "The advice to resolve this incident.";
    }
    container sources {
      description
        "The source components.";
      list source {
        key "node-ref";
        min-elements 1;
        description
          "The source components of incident.";
        uses resources-info;
      }
    }
    container probable-causes {
      description
        "The probable cause objects.";
      list probable-cause {
        key "node-ref";
        description
          "the probable causes of incident.";
        uses resources-info {
          augment "resource" {
            description
              "augment probable cause information.";
            //if probable cause object is a resource of a node
            uses probable-cause-info;
          }
        }
        //if probable cause object is a node
        uses probable-cause-info;
      }
    }
    container probable-events {
      description
        "the probable cause related events of the incident.";
      list probable-event {
        key "type event-id";
        description
          "the probable cause related event of the incident.";
        leaf type {
          type leafref {
            path "../../../events/event/type";
          }
          description
            "the event type.";
        }
        leaf event-id {
          type leafref {
            path "../../../events/event[type = current()/../type]"
               + "/event-id";
          }
          description
            "the event identifier, such as uuid,
             sequence number, etc.";
        }
      }
    }
    container events {
      description
        "related events.";
      list event {
        key "type event-id";
        description
          "related events.";
        leaf type {
          type identityref {
            base event-type;
          }
          description
            "event type.";
        }
        leaf event-id {
          type string;
          description
            "the event identifier, such as uuid,
             sequence number, etc.";
        }
        choice event-type-info {
          description
            "event type information.";
          case alarm {
            when "derived-from-or-self(type, 'alarm')" {
              description
                "Only applies when type is alarm.";
            }
            container alarm {
              description
                "alarm type event.";
              leaf resource {
                type leafref {
                  path "/al:alarms/al:alarm-list/al:alarm"
                     + "/al:resource";
                }
                description
                  "network resource.";
                reference
                  "RFC 8632: A YANG Data Model for Alarm
                   Management";
              }
              leaf alarm-type-id {
                type leafref {
                  path "/al:alarms/al:alarm-list/al:alarm"
                     + "[al:resource = current()/../resource]"
                     + "/al:alarm-type-id";
                }
                description
                  "alarm type id";
                reference
                  "RFC 8632: A YANG Data Model for Alarm
                    Management";
              }
              leaf alarm-type-qualifier {
                type leafref {
                  path "/al:alarms/al:alarm-list/al:alarm"
                     + "[al:resource = current()/../resource]"
                     + "[al:alarm-type-id = current()/.."
                     + "/alarm-type-id]/al:alarm-type-qualifier";
                }
                description
                  "alarm type qualitifier";
                reference
                  "RFC 8632: A YANG Data Model for Alarm
                   Management";
              }
            }
          }
        }
      }
    }
  }

  // RPCs

  rpc incident-acknowledge {
    description
      "This rpc can be used to acknowledge the specified
       incidents.";
    input {
      leaf-list incident-no {
        type incident-ref;
        description
          "the identifier of an incident instance.";
      }
    }
  }

  rpc incident-diagnose {
    description
      "This rpc can be used to diagnose the specified
       incidents. The result of diagnosis will be reported
       by incident notification.";
    input {
      leaf-list incident-no {
        type incident-ref;
        description
          "the identifier of an incident instance.";
      }
    }
  }

  rpc incident-resolve {
    description
      "This rpc can be used to resolve the specified
       incidents. The result of resolution will be reported
       by incident notification.";
    input {
      leaf-list incident-no {
        type incident-ref;
        description
          "the identifier of an incident instance.";
      }
    }
  }

  sx:structure incident-acknowledge-error-info {
    container incident-acknowledge-error-info {
      description
        "This structure data MAY be inserted in the RPC error
         response to indicate the reason for the
         incident acknowledge failure.";
      leaf incident-no {
        type incident-ref;
        description
          "Indicates the incident identifier that
           fails the operation.";
      }
      leaf reason {
        type identityref {
          base acknowledge-error;
        }
        description
          "Indicates the reason why the operation is failed.";
      }
      leaf description {
        type string;
        description
          "Indicates the detailed description about the failure.";
      }
    }
  }
  sx:structure incident-diagnose-error-info {
    container incident-diagnose-error-info {
      description
        "This structure data MAY be inserted in the RPC error
         response to indicate the reason for the
         incident diagnose failure.";
      leaf incident-no {
        type incident-ref;
        description
          "Indicates the incident identifier that
           fails the operation.";
      }
      leaf reason {
        type identityref {
          base diagnose-error;
        }
        description
          "Indicates the reason why the operation is failed.";
      }
      leaf description {
        type string;
        description
          "Indicates the detailed description about the failure.";
      }
    }
  }
  sx:structure incident-resolve-error-info {
    container incident-resolve-error-info {
      description
        "This structure data MAY be inserted in the RPC error
         response to indicate the reason for the
         incident resolution failure.";
      leaf incident-no {
        type incident-ref;
        description
          "Indicates the incident identifier that
           fails the operation.";
      }
      leaf reason {
        type identityref {
          base resolve-error;
        }
        description
          "Indicates the reason why the operation is failed.";
      }
      leaf description {
        type string;
        description
          "Indicates the detailed description about the failure.";
      }
    }
  }

  // Notifications

  notification incident-notification {
    description
      "incident notification. It will be triggered when
       the incident is raised, updated or cleared.";
    leaf incident-no {
      type incident-ref;
      description
        "the identifier of an incident instance.";
    }
    uses incident-info;
    leaf time {
      type yang:date-and-time;
      description
        "occur time of an incident instance.";
    }
  }

  // Data definitions

  container incidents {
    config false;
    description
      "the information of incidents.";
    list incident {
      key "name type incident-id";
      description
        "the information of incident.";
      leaf incident-no {
        type uint64;
        mandatory true;
        description
        "The unique sequence number of the incident instance.";
      }
      uses incident-info;
      uses incident-time-info;
    }
  }
}
