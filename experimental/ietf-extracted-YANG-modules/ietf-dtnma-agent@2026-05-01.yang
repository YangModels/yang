module ietf-dtnma-agent {
  yang-version 1.1;
  namespace "ari://ietf/dtnma-agent/";
  prefix da;

  import ietf-amm {
    prefix amm;
  }
  import ietf-amm-semtype {
    prefix amm-semtype;
  }
  import ietf-amm-base {
    prefix amm-base;
  }
  import ietf-network-base {
    prefix network-base;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module implements the DTN Management Architecture (DTNMA)
     Agent core functionality.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2026-05-01 {
    description
      "Updated for latest ADM document.";
    reference
      "draft-ietf-dtn-adm-yang";
  }

  feature rules {
    description
      "Conforming to this feature enables time-based and
       state-based autonomy rules.
       A basic implementation can omit these and only allow
       direct manager execution without rules.
       Even without rules, an application can choose to
       generate and send reports at-will using internal
       Agent--application API.";
  }

  feature exec-control {
    description
      "Conforming to this feature enables controls which
       allow advanced sequencing of execution flows
       in an Agent.
       A basic implementation can omit these controls and
       allow only straightforward linear execution sequences
       with no waiting and no conditional branching.";
  }

  grouping obj-list-params {
    description
      "Common parameters for object listing";
    amm:parameter include-adm {
      description
        "If true, listings will include objects from ADMs";
      amm:default "false";
      amm:type "/aritype/BOOL";
    }
  }

  grouping ensure-object-id {
    description
      "Common parameters for providing object reference to
       ensure an object exists in an ODM.

       When this grouping is used, the logic operates according
       to the following in order to succeed.
       The parent 'namespace' SHALL refer to an existing ODM.
       Both the text 'obj-name' and integer 'obj-enum' SHALL
       either both not exist, in which case the object will be
       created, or both are allocated to the same object, in
       which case the object will be modified as needed.";
    amm:parameter namespace {
      description
        "The parent ODM namespace.";
      amm:type "/aritype/namespace";
    }
    amm:parameter obj-name {
      description
        "Text name for the desired object.";
      amm:type "//ietf/amm-base/typedef/id-text";
    }
    amm:parameter obj-enum {
      description
        "Integer enumeration for the desired object.";
      amm:type "//ietf/amm-base/typedef/id-int";
    }
  }

  grouping ensure-object-params {
    description
      "Common parameter for providing formal parameter
       definitions to ensure an object exists in an ODM.

       When this grouping is used it should be after all of
       the mandatory parameters (those with no default value)
       to allow the default no-formal-parameters to be used.";
    amm:parameter formal-params {
      description
        "An optional list of formal parameters for the object.";
      amm:default "/tbl/c=3;";
      amm:type "./typedef/formal-params-tbl";
    }
  }

  grouping any-binary-operands {
    description
      "Any-value binary operands";
    amm:operand left {
      description
        "The left-side operand.";
      amm:type "//ietf/amm-base/typedef/any";
    }
    amm:operand right {
      description
        "The left-side operand.";
      amm:type "//ietf/amm-base/typedef/any";
    }
  }

  grouping any-unary-result {
    description
      "Any-value result";
    amm:result result {
      description
        "The single value.";
      amm:type "//ietf/amm-base/typedef/any";
    }
  }

  grouping numeric-time-binary-operands {
    description
      "Numeric or time binary operands";
    amm:operand left {
      description
        "The left-side operand.";
      amm:type "//ietf/amm-base/typedef/numeric-or-time";
    }
    amm:operand right {
      description
        "The left-side operand.";
      amm:type "//ietf/amm-base/typedef/numeric-or-time";
    }
  }

  grouping numeric-binary-operands {
    description
      "Numeric binary operands";
    amm:operand left {
      description
        "The left-side operand.";
      amm:type "//ietf/amm-base/typedef/NUMERIC";
    }
    amm:operand right {
      description
        "The left-side operand.";
      amm:type "//ietf/amm-base/typedef/NUMERIC";
    }
  }

  grouping numeric-unary-result {
    description
      "Numeric result";
    amm:result result {
      description
        "The single value.";
      amm:type "//ietf/amm-base/typedef/NUMERIC";
    }
  }

  grouping integer-unary-operands {
    description
      "Integer unary operand";
    amm:operand val {
      description
        "The single value.";
      amm:type "//ietf/amm-base/typedef/INTEGER";
    }
  }

  grouping integer-binary-operands {
    description
      "Integer binary operands";
    amm:operand left {
      description
        "The left-side operand.";
      amm:type "//ietf/amm-base/typedef/INTEGER";
    }
    amm:operand right {
      description
        "The left-side operand.";
      amm:type "//ietf/amm-base/typedef/INTEGER";
    }
  }

  grouping integer-unary-result {
    description
      "Integer result";
    amm:result result {
      description
        "The single value.";
      amm:type "//ietf/amm-base/typedef/INTEGER";
    }
  }

  grouping bool-unary-operands {
    description
      "Boolean unary operand";
    amm:operand val {
      description
        "The single value.";
      amm:type "/aritype/BOOL";
    }
  }

  grouping bool-binary-operands {
    description
      "Boolean binary operands";
    amm:operand left {
      description
        "The left-side operand.";
      amm:type "/aritype/BOOL";
    }
    amm:operand right {
      description
        "The left-side operand.";
      amm:type "/aritype/BOOL";
    }
  }

  grouping bool-unary-result {
    description
      "Boolean result";
    amm:result result {
      description
        "The single value.";
      amm:type "/aritype/BOOL";
    }
  }

  grouping predicate-compose-interface {
    description
      "A common interface for all predicate composition
       operators below.";
    amm:parameter operators {
      description
        "The list of other predicate operators to evaluate and
         combine their results.";
      amm:ulist {
        amm:type "/aritype/oper";
      }
    }
    amm:operand value {
      description
        "The value to pass-through and evaluate with each of the
         subordinate operators.";
      amm:type "//ietf/amm-base/typedef/any";
    }
    amm:result combined {
      description
        "The combined boolean result.";
      amm:type "/aritype/bool";
    }
  }

  amm:enum 1;
  amm:edd sw-vendor {
    amm:enum 0;
    description
      "The vendor for this Agent implementation.";
    amm:type "/aritype/TEXTSTR";
  }
  amm:edd sw-version {
    amm:enum 1;
    description
      "The version for this Agent implementation.";
    amm:type "/aritype/TEXTSTR";
  }
  amm:edd capability {
    amm:enum 2;
    description
      "A table to indicate the ADM capability of the sending agent.";
    amm:tblt {
      amm:key "org-name adm-name";
      amm:column org-name {
        description
          "The organization name containing the ADM";
        amm:type "/aritype/TEXTSTR";
      }
      amm:column org-enum {
        description
          "The organization enumeration containing the ADM";
        amm:type "/aritype/VAST";
      }
      amm:column model-name {
        description
          "The model name of the ADM";
        amm:type "/aritype/TEXTSTR";
      }
      amm:column model-enum {
        description
          "The model enumeration of the ADM";
        amm:type "/aritype/VAST";
      }
      amm:column revision {
        description
          "The specific revision the agent supports.";
        amm:type "/aritype/TEXTSTR";
      }
      amm:column features {
        description
          "The features of the ADM which the agent supports.";
        amm:ulist {
          amm:type "/aritype/TEXTSTR";
        }
      }
    }
  }
  amm:const hello {
    amm:enum 0;
    description
      "A report template to indicate the presence of an agent
       on a network.";
    amm:init-value "/AC/(./EDD/sw-vendor,./EDD/sw-version,"
                 + "./EDD/capability)";
    amm:type "//ietf/amm-base/typedef/RPTT";
  }

  // Messaging counters
  amm:edd num-msg-rx {
    amm:enum 3;
    description
      "Counter of the number of AMP messages of any type received
       from any manager.";
    amm:type "//ietf/amm-base/typedef/counter64";
  }
  amm:edd num-msg-rx-failed {
    amm:enum 4;
    description
      "Counter of received EXECSET values that failed to be decoded
       and processed.";
    amm:type "//ietf/amm-base/typedef/counter64";
  }
  amm:edd num-msg-tx {
    amm:enum 5;
    description
      "Counter of the number of AMP messages of any type transmitted
       to any manager.";
    amm:type "//ietf/amm-base/typedef/counter64";
  }
  amm:edd num-msg-tx-failed {
    amm:enum 15;
    description
      "Counter of RPTSET values that encoded but failed to be sent.";
    amm:type "//ietf/amm-base/typedef/counter64";
  }
  amm:edd last-msg-rx-time {
    amm:enum 17;
    description
      "A timestamp on the Agent when the latest AMP message was
       received from any manager.";
    amm:type "/aritype/TP";
  }

  // Execution counters and states
  amm:edd num-exec-started {
    amm:enum 6;
    description
      "Number of CTRL executions started.
       This does not include EXECSETs which have been received and
       are still queued for execution.
       See <./edd/exec-running> table for those details.";
    amm:type "//ietf/amm-base/typedef/counter64";
  }
  amm:edd num-exec-succeeded {
    amm:enum 7;
    description
      "Number of successful CTRL executions.
       This means the CTRL result was not undefined.";
    amm:type "//ietf/amm-base/typedef/counter64";
  }
  amm:edd num-exec-failed {
    amm:enum 8;
    description
      "Number of failed CTRL executions.
       This means the CTRL result was undefined.";
    amm:type "//ietf/amm-base/typedef/counter64";
  }
  amm:edd exec-running {
    amm:enum 9;
    description
      "Information on controls currently being executed.
       This represents tracking of execution requests from
       received EXECSET values until the entire execution is
       finished (successfully or not).
       Once finished, the Agent SHALL remove the associated row
       from this table and never re-use its 'pid' value.";
    amm:tblt {
      amm:key "pid";
      amm:column pid {
        description
          "An identifier internal to an Agent used to correlate
           table rows over time.
           An implementation MAY assign values from a smaller
           domain than this column can represent.";
        amm:type "/aritype/UVAST";
      }
      amm:column target {
        description
          "The original, full target of the execution.
           This can be an inline MAC or a CTRL reference.";
        amm:type "//ietf/amm-base/typedef/exec-tgt";
      }
      amm:column state {
        description
          "The state of executing the target within the Agent.";
        amm:type "/aritype/BYTE" {
          amm:int-labels {
            enum waiting {
              value 0;
              description
                "The execution is waiting on a condition or timer
                 to continue.
                 This includes waiting on Agent resources for the
                 execution itself.";
            }
            enum running {
              value 1;
              description
                "The execution is currently running.";
            }
          }
        }
      }
    }
  }

  // MAC helper controls
  amm:ctrl if-then-else {
    if-feature "exec-control";
    amm:enum 0;
    description
      "Evaluate an expression and follow one of two branches of
       further evaluation.";
    amm:parameter condition {
      description
        "The condition (inline or reference) to evaluate and
         convert to BOOL type.";
      amm:type "//ietf/amm-base/typedef/eval-tgt";
    }
    amm:parameter on-truthy {
      description
        "The target to execute when the condition is truthy.";
      amm:default "null";
      amm:union {
        amm:type "//ietf/amm-base/typedef/exec-tgt";
        amm:type "/aritype/NULL";
      }
    }
    amm:parameter on-falsy {
      description
        "An optional target to execute when the condition is
         not truthy (including if evaluates to undefined).";
      amm:default "null";
      amm:union {
        amm:type "//ietf/amm-base/typedef/exec-tgt";
        amm:type "/aritype/NULL";
      }
    }
    amm:result branch {
      description
        "Indication of which branch was executed.";
      amm:type "/aritype/BOOL";
    }
  }
  amm:ctrl catch {
    if-feature "exec-control";
    amm:enum 1;
    description
      "Attempt to execute a target, and if there is some failure
       catch it and execute an alternative target.";
    amm:parameter try {
      description
        "The target to execute.";
      amm:type "//ietf/amm-base/typedef/exec-tgt";
    }
    amm:parameter on-failure {
      description
        "An optional target to execute after failure.";
      amm:default "null";
      amm:union {
        amm:type "//ietf/amm-base/typedef/exec-tgt";
        amm:type "/aritype/NULL";
      }
    }
    amm:result try-success {
      description
        "True if the try target succeeded without exception.";
      amm:type "/aritype/BOOL";
    }
  }
  amm:ctrl exec-deadline {
    amm:enum 22;
    description
      "Execute a desired target and wait for it to finish before
       a relative time deadline.
       If it does not finish, it is terminated and an alternative
       timeout target is executed.
       If the target experiences a failure executing before the
       deadline, then this control will also fail.";
    amm:parameter target {
      description
        "The target to execute.";
      amm:type "//ietf/amm-base/typedef/exec-tgt";
    }
    amm:parameter deadline {
      description
        "The relative of time on the Agent to wait for
         the target to finish executing.";
      amm:type "/aritype/TD";
    }
    amm:parameter on-timeout {
      description
        "An optional target to execute after a timeout.";
      amm:default "null";
      amm:union {
        amm:type "//ietf/amm-base/typedef/exec-tgt";
        amm:type "/aritype/NULL";
      }
    }
    amm:result success {
      description
        "True if the target sub-execution succeeded before the
         deadline, false if the execution did not finish before,
         and undefined if the execution failed before the
         deadline.";
      amm:type "/aritype/BOOL";
    }
  }
  amm:ctrl wait-for {
    if-feature "exec-control";
    amm:enum 2;
    description
      "This control causes the execution to pause for a given
       amount of time.
       This is intended to be used within a macro to separate
       controls in time.";
    amm:parameter duration {
      description
        "The relative of time on the Agent to wait for.";
      amm:type "/aritype/TD";
    }
  }
  amm:ctrl wait-until {
    if-feature "exec-control";
    amm:enum 3;
    description
      "This control causes the execution to pause until a specific
       absolute time point.
       This is intended to be used within a macro to separate
       controls in time or as a first macro item to delay execution
       after the time of reception.";
    amm:parameter time {
      description
        "The absolute Agent time at which to stop waiting.";
      amm:type "/aritype/TP";
    }
  }
  amm:ctrl wait-cond {
    if-feature "exec-control";
    amm:enum 4;
    description
      "This control causes the execution to pause until a condition
       expression evaluates to truthy.
       This is intended to be used within a macro to separate
       controls in time or as a first macro item to delay execution
       until the condition is met.";
    amm:parameter condition {
      description
        "The condition (inline or reference) to evaluate and
         convert to BOOL type.";
      amm:type "//ietf/amm-base/typedef/eval-tgt";
    }
    amm:parameter min-interval {
      description
        "An optional hint used by an Agent to limit how frequently
         the condition is evaluated.
         If this is null, an implementation-defined default will
         be used.";
      amm:default "null";
      amm:union {
        amm:type "/aritype/TD";
        amm:type "/aritype/NULL";
      }
    }
  }

  // Value production and reporting
  amm:ctrl inspect {
    amm:enum 5;
    description
      "Produce a result value to inspect the agent state.
       This does not perform any EXPR evaluation or RPTT handling.";
    amm:parameter ref {
      description
        "An object to produce a value from.";
      amm:type "//ietf/amm-base/typedef/VALUE-OBJ";
    }
    amm:result val {
      description
        "The produced value.";
      amm:type "//ietf/amm-base/typedef/any";
    }
  }
  amm:ctrl report-on {
    amm:enum 6;
    description
      "Agent-wide control to generate a report from a report
       template (RPTT) value.
       The parameter is a single RPTT list that would be produced
       by an object.
       If used for more than one-shot diagnostics, defining a RPTT
       (e.g. in a CONST within an ODM) is more efficient because
       the RPTT value would not need be present in the EXECSET or
       corresponding RPTSET.";
    amm:parameter template {
      description
        "The reporting template, either as a RPTT value directly or
         as a reference to a value-producing object (possibly
         parameterized) which itself produces an RPTT value.";
      amm:type "//ietf/amm-base/typedef/rpt-tgt";
    }
    amm:parameter destinations {
      description
        "Destinations for the resulting report.
         If given an empty list (the default) reports will be sent
         to the manager executing this CTRL.
         When executed as a rule action, the destinations list is
         mandatory.

         It is possible that each destination has different access
         limitations so each destination might see different report
         contents.";
      amm:default "/ac/()";
      amm:ulist {
        amm:type "//ietf/network-base/typedef/endpoint-or-uri";
      }
    }
  }

  // Objects related to ODM handling
  amm:edd odm-list {
    amm:enum 16;
    description
      "A table of ODM within the agent.";
    amm:tblt {
      amm:key "org-name odm-name";
      amm:column org-name {
        description
          "The organization name containing the ODM";
        amm:type "//ietf/amm-base/typedef/id-text";
      }
      amm:column org-enum {
        description
          "The organization enumeration containing the ODM";
        amm:type "//ietf/amm-base/typedef/id-int";
      }
      amm:column model-name {
        description
          "The model name of the ODM";
        amm:type "//ietf/amm-base/typedef/id-text";
      }
      amm:column model-enum {
        description
          "The model enumeration of the ODM";
        amm:type "//ietf/amm-base/typedef/id-int";
      }
      amm:column revision {
        description
          "The specific revision the agent supports.";
        amm:type "/aritype/TEXTSTR";
      }
    }
  }
  amm:ctrl ensure-odm {
    amm:enum 18;
    description
      "Ensure a specific ODM is present.
       The referenced organization and model identifiers SHALL either
       not already exist or exist with the exact combination given by
       these parameters";
    amm:parameter org-name {
      description
        "The organization name containing the ODM";
      amm:type "//ietf/amm-base/typedef/id-text";
    }
    amm:parameter org-id {
      description
        "The organization enumeration ID containing the ODM";
      amm:type "//ietf/amm-base/typedef/id-int";
    }
    amm:parameter model-name {
      description
        "The model name containing the ODM.
         This value SHALL have a leading bang to indicate that it
         is an ODM.";
      amm:type "//ietf/amm-base/typedef/id-text" {
        pattern '!.+';
      }
    }
    amm:parameter model-id {
      description
        "The model enumeration ID containing the ODM.
         This value SHALL be negative to indicate that it is
         an ODM.";
      amm:type "//ietf/amm-base/typedef/id-int" {
        range "min..-1";
      }
    }
  }
  amm:ctrl obsolete-odm {
    amm:enum 19;
    description
      "Mark a specific ODM as obsolete if it is present.";
    amm:parameter odm-ns {
      description
        "Namespace of the ODM";
      amm:type "/aritype/namespace";
    }
  }

  // Helpers for VAR
  amm:ctrl var-reset {
    amm:enum 7;
    description
      "Modify a VAR state to its default value.";
    amm:parameter target {
      description
        "The VAR object to affect.";
      amm:type "/aritype/VAR";
    }
  }
  amm:ctrl var-store {
    amm:enum 8;
    description
      "Modify a VAR state to a specific value.";
    amm:parameter target {
      description
        "The VAR object to affect.";
      amm:type "/aritype/VAR";
    }
    amm:parameter value {
      description
        "The exact value to store in the VAR.";
      amm:type "//ietf/amm-base/typedef/any";
    }
  }

  // Objects related to IDENT handling
  amm:edd ident-list {
    amm:enum 18;
    description
      "Inspect the set of (possibly filtered) IDENT objects known
       to the Agent.
       One possible filter is provided by the 'base' parameter to
       limit to a specific subtree of objects. Another is whether
       or not to include abstract objects in the list.";
    uses obj-list-params;
    amm:parameter include-abstract {
      description
        "Determine whether abstract objects are included in the
         list (when true), or only non-abstract objects (when
         false).";
      amm:default "false";
      amm:type "/aritype/bool";
    }
    amm:parameter base {
      description
        "The optional base object from which to traverse derived
         objects. If this does not reference a known object the
         produced list SHALL be empty.
         The base object is not considered to be derived from
         itself, so it SHALL NOT be present in the produced list.";
      amm:default "null";
      amm:union {
        amm:type "/aritype/ident";
        amm:type "/aritype/null";
      }
    }
    amm:tblt {
      amm:key "obj";
      amm:column obj {
        amm:type "/aritype/ident";
      }
      amm:column is-abstract {
        amm:type "/aritype/bool";
      }
    }
  }
  amm:ctrl ensure-ident {
    amm:enum 20;
    description
      "Ensure a specific IDENT is present in an ODM.
       If an object already exists with the same identifiers,
       parameters, and bases this control will do nothing
       and succeed.
       If an object already exists in the same namespace with either
       of the object identifiers this control will fail.";
    uses ensure-object-id;
    amm:parameter abstract {
      description
        "If true the object is abstract and SHALL NOT contain any
         formal parameters.";
      amm:type "/aritype/bool";
    }
    amm:parameter bases {
      description
        "The set of base objects for this object.";
      amm:ulist {
        amm:type "/aritype/ident";
      }
    }
    uses ensure-object-params;
  }
  amm:ctrl obsolete-ident {
    amm:enum 21;
    description
      "Mark a specific IDENT as obsolete if it is present in an
       ODM.";
    amm:parameter obj {
      description
        "A reference to a IDENT within an ODM only.";
      amm:type "/aritype/IDENT";
    }
  }

  // Objects related to TYPEDEF handling
  amm:edd typedef-list {
    amm:enum 10;
    description
      "A table of TYPEDEF within the agent.";
    uses obj-list-params;
    amm:tblt {
      amm:key "obj";
      amm:column obj {
        amm:type "/aritype/typedef";
      }
    }
  }

  // Objects related to CONST handling
  amm:edd const-list {
    amm:enum 14;
    description
      "A table of CONST within the agent.";
    uses obj-list-params;
    amm:tblt {
      amm:key "obj";
      amm:column obj {
        amm:type "/aritype/CONST";
      }
      amm:column type {
        amm:type "//ietf/amm-semtype/typedef/semtype";
      }
    }
  }
  amm:ctrl ensure-const {
    amm:enum 11;
    description
      "Ensure a specific CONST is present in an ODM.
       If an object already exists with the same identifiers,
       parameters, type, and value this control will do nothing
       and succeed.
       If an object already exists in the same namespace with either
       of the object identifiers this control will fail.";
    uses ensure-object-id;
    amm:parameter type {
      description
        "The type for the CONST object.";
      amm:type "//ietf/amm-semtype/typedef/semtype";
    }
    amm:parameter value {
      description
        "A required constant value.
         This value SHALL match the type given for this object.";
      amm:type "//ietf/amm-base/typedef/any";
    }
    uses ensure-object-params;
  }
  amm:typedef formal-params-tbl {
    amm:enum 1;
    description
      "Introspection on formal parameters of an object which
       can be parameterized.
       The order of rows of the table is significant and
       corresponds with the index of each parameter.";
    amm:tblt {
      amm:key "name";
      amm:column name {
        description
          "The name of the parameter.
           This is unique among all rows.";
        amm:type "//ietf/amm-base/typedef/id-text";
      }
      amm:column type {
        description
          "The type for values of the parameter.";
        amm:type "//ietf/amm-semtype/typedef/semtype";
      }
      amm:column default {
        description
          "An optional default value.
           When there is no default, the undefined value is
           used here.";
        amm:type "//ietf/amm-base/typedef/any";
      }
    }
  }
  amm:ctrl obsolete-const {
    amm:enum 12;
    description
      "Mark a specific CONST as obsolete if it is present in an
       ODM.";
    amm:parameter obj {
      description
        "A reference to a CONST within an ODM only.";
      amm:type "/aritype/CONST";
    }
  }

  // Objects related to VAR handling
  amm:edd var-list {
    amm:enum 11;
    description
      "A table of VAR within the agent.";
    uses obj-list-params;
    amm:tblt {
      amm:key "obj";
      amm:column obj {
        amm:type "/aritype/VAR";
      }
      amm:column type {
        amm:type "//ietf/amm-semtype/typedef/semtype";
      }
    }
  }
  amm:ctrl ensure-var {
    amm:enum 9;
    description
      "Ensure a specific VAR is present in an ODM.
       If an object already exists with the same identifiers,
       parameters, type, and init-value this control will do
       nothing and succeed.
       If an object already exists in the same namespace with either
       of the object identifiers (but not both), or the type or
       is different, this control will fail.
       That means that this control can change only the initial value
       of a pre-existing VAR object.";
    uses ensure-object-id;
    amm:parameter type {
      description
        "The type for the VAR object.";
      amm:type "//ietf/amm-semtype/typedef/semtype";
    }
    amm:parameter init-value {
      description
        "The exact value to use as the initial value of
         the new object and to store as the initial state
         of the object if created.
         This value SHALL match the type given for this object.";
      amm:type "//ietf/amm-base/typedef/any";
    }
    uses ensure-object-params;
  }
  amm:ctrl obsolete-var {
    amm:enum 10;
    description
      "Mark a specific VAR as obsolete if it is present in an ODM.";
    amm:parameter obj {
      description
        "A reference to a VAR within an ODM only.";
      amm:type "/aritype/VAR";
    }
  }

  // Objects related to SBR handling
  amm:edd sbr-list {
    if-feature "rules";
    amm:enum 12;
    description
      "A table of SBR within the agent.";
    uses obj-list-params;
    amm:tblt {
      amm:key "obj";
      amm:column obj {
        amm:type "/aritype/SBR";
      }
      amm:column action {
        description
          "The action (inline MAC or CTRL reference) to execute when
           this rule triggers.";
        amm:type "//ietf/amm-base/typedef/exec-tgt";
      }
      amm:column condition {
        description
          "The condition (inline or reference) to periodically
           evaluate and convert to BOOL type.";
        amm:type "//ietf/amm-base/typedef/eval-tgt";
      }
      amm:column min-interval {
        description
          "The minimum interval of Agent time between executions of
           the action.
           This can also be used by an Agent to limit how frequently
           the condition is evaluated.";
        amm:type "/aritype/TD";
      }
      amm:column max-count {
        description
          "Number of executions of the action, after being enabled,
           when the rule is disabled.";
        amm:type "/aritype/UVAST";
      }
      amm:column init-enabled {
        description
          "Whether the rule is enabled at Agent initialization.";
        amm:type "/ARITYPE/BOOL";
      }
      amm:column enabled {
        description
          "The current enabled state of the rule.";
        amm:type "/ARITYPE/BOOL";
      }
    }
  }
  amm:edd tbr-list {
    if-feature "rules";
    amm:enum 13;
    description
      "A table of TBR within the agent.";
    uses obj-list-params;
    amm:tblt {
      amm:key "obj";
      amm:column obj {
        amm:type "/aritype/TBR";
      }
      amm:column action {
        description
          "The action (inline MAC or CTRL reference) to execute when
           this rule triggers.";
        amm:type "//ietf/amm-base/typedef/exec-tgt";
      }
      amm:column start-time {
        description
          "The earliest time (absolute or init-relative) at which
           the action is executed.";
        amm:type "//ietf/amm-base/typedef/TIME";
      }
      amm:column period {
        description
          "How often the action is executed.";
        amm:type "/aritype/TD";
      }
      amm:column max-count {
        description
          "Number of executions of the action, after being enabled,
           when the rule is disabled.";
        amm:type "/aritype/UVAST";
      }
      amm:column init-enabled {
        description
          "Whether the rule is enabled at Agent initialization.";
        amm:type "/ARITYPE/BOOL";
      }
      amm:column enabled {
        description
          "The current enabled state of the rule.";
        amm:type "/ARITYPE/BOOL";
      }
    }
  }

  // CTRLs related to rules
  amm:ctrl ensure-sbr {
    if-feature "rules";
    amm:enum 13;
    description
      "Ensure that a state-based rule with the given identifiers
       exists within an ODM.";
    uses ensure-object-id;
    amm:parameter action {
      description
        "The action (inline MAC or CTRL reference) to execute when
         this rule triggers.";
      amm:type "//ietf/amm-base/typedef/exec-tgt";
    }
    amm:parameter condition {
      description
        "The condition (inline or reference) to periodically
         evaluate and convert to BOOL type.";
      amm:type "//ietf/amm-base/typedef/eval-tgt";
    }
    amm:parameter min-interval {
      description
        "The minimum interval of Agent time between executions of
         the action.
         This can also be used by an Agent to limit how frequently
         the condition is evaluated.";
      amm:type "/ARITYPE/TD";
    }
    amm:parameter max-count {
      description
        "Number of executions of the action, after being enabled,
         when the rule is disabled.";
      amm:type "/ARITYPE/UVAST";
    }
    amm:parameter init-enabled {
      description
        "Whether the rule is enabled at Agent initialization.";
      amm:type "/ARITYPE/BOOL";
    }
  }
  amm:ctrl ensure-tbr {
    if-feature "rules";
    amm:enum 14;
    description
      "Ensure that a time-based rule with the given identifiers
       exists within an ODM.";
    uses ensure-object-id;
    amm:parameter action {
      description
        "The action (inline MAC or CTRL reference) to execute when
         this rule triggers.";
      amm:type "//ietf/amm-base/typedef/exec-tgt";
    }
    amm:parameter start-time {
      description
        "The earliest time (absolute or init-relative) at which
         the action is executed.";
      amm:type "//ietf/amm-base/typedef/TIME";
    }
    amm:parameter period {
      description
        "How often the action is executed.";
      amm:type "/ARITYPE/TD";
    }
    amm:parameter max-count {
      description
        "Number of executions of the action, after being enabled,
         when the rule is disabled.";
      amm:type "/ARITYPE/UVAST";
    }
    amm:parameter init-enabled {
      description
        "Whether the rule is enabled at Agent initialization.";
      amm:type "/ARITYPE/BOOL";
    }
  }
  amm:ctrl ensure-rule-enabled {
    if-feature "rules";
    amm:enum 15;
    description
      "Ensure a specific rule is enabled or disabled.";
    amm:parameter obj-id {
      description
        "The rule of which to ensure the enabled state.";
      amm:union {
        amm:type "/ARITYPE/SBR";
        amm:type "/ARITYPE/TBR";
      }
    }
    amm:parameter enabled {
      description
        "The desired enabled state of the rule.";
      amm:type "/ARITYPE/BOOL";
    }
  }
  amm:ctrl reset-rule-enabled {
    if-feature "rules";
    amm:enum 16;
    description
      "Reset rule enabled to initial setting.";
    amm:parameter obj-id {
      description
        "The rule of which to reset the enabled state.";
      amm:union {
        amm:type "/ARITYPE/SBR";
        amm:type "/ARITYPE/TBR";
      }
    }
  }
  amm:ctrl obsolete-rule {
    if-feature "rules";
    amm:enum 17;
    description
      "Mark a specific SBR or TBR as obsolete if it is present in
       an ODM.";
    amm:parameter obj-id {
      description
        "A reference to a rule within an ODM only.";
      amm:union {
        amm:type "/ARITYPE/SBR";
        amm:type "/ARITYPE/TBR";
      }
    }
    amm:result success {
      description
        "Boolean indicating whether the rule was marked obsolete";
      amm:type "/ARITYPE/BOOL";
    }
  }

  // Numeric operators
  amm:oper negate {
    amm:enum 0;
    description
      "Negate a value, numeric or TD.
       This is equivalent to multiplying by -1 but a shorter
       expression.";
    amm:operand val {
      description
        "The single value.";
      amm:type "//ietf/amm-base/typedef/numeric-or-time";
    }
    uses numeric-unary-result;
  }
  amm:oper add {
    amm:enum 1;
    description
      "Add two numeric values or a TP and TD value (in either order).
       The operands are cast to the least compatible numeric type
       before the arithmetic.";
    uses numeric-time-binary-operands;
    uses any-unary-result;
  }
  amm:oper sub {
    amm:enum 2;
    description
      "Subtract two numeric values or a TP less a TD value.
       The left (second) operand is the minuend and the right (first)
       operand is the subtrahend; this means that the EXPR
       </AC/(10, 2, ./OPER/sub)> behaves as the infix '10 - 2'.
       The operands are cast to the least compatible numeric type
       before the arithmetic.";
    uses numeric-time-binary-operands;
    uses any-unary-result;
  }
  amm:oper multiply {
    amm:enum 3;
    description
      "Multiply two numeric values or a TD value (in either order).
       The operands are cast to the least compatible numeric type
       before the arithmetic.";
    uses numeric-time-binary-operands;
    uses any-unary-result;
  }
  amm:oper divide {
    amm:enum 4;
    description
      "Divide two numeric values or a TD value (as numerator).
       The left (second) operand is the numerator and the right
       (first) operand is the divisor; this means that the EXPR
       </AC/(10, 2, ./OPER/divide)> behaves as the infix '10 / 2'.
       The operands are cast to the least compatible numeric type
       before the arithmetic.";
    uses numeric-time-binary-operands;
    uses any-unary-result;
  }
  amm:oper remainder {
    amm:enum 5;
    description
      "Find the remainder of a numeric operation.
       The left (second) operand is the numerator and the right
       (first) operand is the divisor; this means that the EXPR
       </AC/(10, 2, ./OPER/divide)> behaves as the infix '10 % 2'.
       The operands are cast to the least compatible numeric type
       before the arithmetic.";
    uses numeric-binary-operands;
    uses numeric-unary-result;
  }

  // Bitwise operators
  amm:oper bit-not {
    amm:enum 6;
    description
      "Perform a bitwise NOT on an integer value.";
    uses integer-unary-operands;
    uses integer-unary-result;
  }
  amm:oper bit-and {
    amm:enum 7;
    description
      "Perform a bitwise AND between two integer values.";
    uses integer-binary-operands;
    uses integer-unary-result;
  }
  amm:oper bit-or {
    amm:enum 8;
    description
      "Perform a bitwise OR between two integer values.";
    uses integer-binary-operands;
    uses integer-unary-result;
  }
  amm:oper bit-xor {
    amm:enum 9;
    description
      "Perform a bitwise exclusive or (XOR) between two integer
       values.";
    uses integer-binary-operands;
    uses integer-unary-result;
  }

  // Boolean operators
  amm:oper bool-not {
    amm:enum 10;
    description
      "Perform a boolean NOT on a boolean value.";
    uses bool-unary-operands;
    uses bool-unary-result;
  }
  amm:oper bool-and {
    amm:enum 11;
    description
      "Perform a boolean AND between two boolean values.";
    uses bool-binary-operands;
    uses bool-unary-result;
  }
  amm:oper bool-or {
    amm:enum 12;
    description
      "Perform a boolean OR between two boolean values.";
    uses bool-binary-operands;
    uses bool-unary-result;
  }
  amm:oper bool-xor {
    amm:enum 13;
    description
      "Perform a boolean XOR between two boolean values.";
    uses bool-binary-operands;
    uses bool-unary-result;
  }

  // Strict value comparison
  amm:oper strict-eq {
    amm:enum 33;
    description
      "Compare two values for strict equality as defined by
       Section 6.12.1 of the AMM.";
    uses any-binary-operands;
    uses bool-unary-result;
  }
  amm:oper strict-ne {
    amm:enum 34;
    description
      "Compare two values for strict inequality as defined by
       Section 6.12.1 of the AMM.";
    uses any-binary-operands;
    uses bool-unary-result;
  }

  // Loose value comparison
  amm:oper compare-eq {
    amm:enum 14;
    description
      "Compare two values for loose equality as defined by
       Section 6.12.1 of the AMM.
       Numeric operands MAY be converted to a least compatible
       numeric type for the comparison.";
    uses any-binary-operands;
    uses bool-unary-result;
  }
  amm:oper compare-ne {
    amm:enum 15;
    description
      "Compare two values for loose equality as defined by
       Section 6.12.1 of the AMM.
       Numeric operands MAY be converted to a least compatible
       numeric type for the comparison.";
    uses any-binary-operands;
    uses bool-unary-result;
  }

  // Numeric (or time-as-numeric) comparison
  amm:oper compare-gt {
    amm:enum 16;
    description
      "Compare two numbers by value.
       The result is true if the left value is greater than the
       right value.
       The operands are cast to the least compatible numeric type
       before the comparison.";
    uses any-binary-operands;
    uses bool-unary-result;
  }
  amm:oper compare-ge {
    amm:enum 17;
    description
      "Compare two numbers by value.
       The result is true if the left value is greater than or equal
       to the right.
       The operands are cast to the least compatible numeric type
       before the comparison.";
    uses any-binary-operands;
    uses bool-unary-result;
  }
  amm:oper compare-lt {
    amm:enum 18;
    description
      "Compare two operands by value.
       The result is true if the left value is less than the right.
       The operands are cast to the least compatible numeric type
       before the comparison.";
    uses any-binary-operands;
    uses bool-unary-result;
  }
  amm:oper compare-le {
    amm:enum 19;
    description
      "Compare two operands by value.
       The result is true if the left value is less than or
       equal to the right.
       The operands are cast to the least compatible numeric type
       before the comparison.";
    uses any-binary-operands;
    uses bool-unary-result;
  }

  // Unary predicate (match) operators
  amm:oper is-undefined {
    amm:enum 29;
    description
      "Predicate to check for the undefined value.";
    amm:operand value {
      description
        "The value to check.";
      amm:type "//ietf/amm-base/typedef/any";
    }
    amm:result match {
      description
        "True if and only if the value is the undefined value.";
      amm:type "/aritype/bool";
    }
  }
  amm:oper is-not-undefined {
    amm:enum 30;
    description
      "Predicate to check for the undefined value.";
    amm:operand value {
      description
        "The value to check.";
      amm:type "//ietf/amm-base/typedef/any";
    }
    amm:result match {
      description
        "False if and only if the value is the undefined value.";
      amm:type "/aritype/bool";
    }
  }
  amm:oper is-truthy {
    amm:enum 35;
    description
      "Predicate to convert to bool type.
       This operator will specifically consider the undefined value
       as not-truthy with a match result of false.
       This logic is the same as what is used internal to the Agent
       for conditional expressions and filters.";
    amm:operand value {
      description
        "The value to check.";
      amm:type "//ietf/amm-base/typedef/any";
    }
    amm:result match {
      description
        "True if and only if the value is truthy.";
      amm:type "/aritype/bool";
    }
  }
  amm:oper match-type {
    amm:enum 45;
    description
      "Predicate to match against any built-in type or named typedef
       based on the procedures of Section 6.10 of the AMM.
       If the desired type is not known to the agent the result SHALL
       be undefined.";
    reference
      "draft-ietf-dtn-amm";
    amm:parameter desired {
      description
        "The desired type to match against.";
      amm:union {
        amm:type "/aritype/aritype";
        amm:type "/aritype/typedef";
      }
    }
    amm:operand value {
      description
        "The value to check.";
      amm:type "//ietf/amm-base/typedef/any";
    }
    amm:result match {
      description
        "True if and only if the value matches the desired type.";
      amm:type "/aritype/bool";
    }
  }
  amm:oper convert-type {
    amm:enum 46;
    description
      "Type conversion operator to any built-in type or named typedef
       based on the procedures of Section 6.11 of the AMM.
       If the desired type is not known to the agent the result SHALL
       be undefined.
       If the conversion fails the result SHALL be undefined.";
    reference
      "draft-ietf-dtn-amm";
    amm:parameter desired {
      description
        "The desired type to convert to.";
      amm:union {
        amm:type "/aritype/aritype";
        amm:type "/aritype/typedef";
      }
    }
    amm:operand value {
      description
        "The value to convert.";
      amm:type "//ietf/amm-base/typedef/any";
    }
    amm:result converted {
      description
        "The result of conversion, which can be undefined.";
      amm:type "//ietf/amm-base/typedef/any";
    }
  }
  amm:oper match-regexp {
    amm:enum 23;
    description
      "This is a unary predicate operator which will compare
       a text value to a regular expression pattern.
       The regular expression is limited to I-Regexp compatibility.";
    reference
      "RFC 9485: I-Regexp: An Interoperable Regular Expression
       Format";
    amm:parameter regexp {
      description
        "The I-Regexp text pattern to match.
         In accordance with that definition, this pattern is
         implicitly anchored to the start and end of the text being
         matched (i.e. it is always a full match).";
      amm:type "/aritype/textstr";
    }
    amm:operand value {
      description
        "The value to check for a match.";
      amm:type "/aritype/textstr";
    }
    amm:result is-match {
      description
        "The result is true if the value matches the given pattern.";
      amm:type "/aritype/bool";
    }
  }
  amm:oper is-org-private {
    amm:enum 36;
    description
      "Predicate to determine if an object or
       namespace reference value has a namespace which
       is private (i.e. has an org-id which is a negative
       integer or text with a leading bang).";
    amm:operand value {
      description
        "The reference value to check.
         This value SHOULD NOT be de-referenced.";
      amm:union {
        amm:type "/aritype/object";
        amm:type "/aritype/namespace";
      }
    }
    amm:result match {
      description
        "True if and only if the org-id is private.";
      amm:type "/aritype/bool";
    }
  }
  amm:oper match-org-int-range {
    amm:enum 37;
    description
      "Predicate to determine if a de-referenced object or
       namespace reference value has a namespace which
       has an org-id which is within a specific integer range.";
    amm:parameter min-value {
      description
        "The minimum org-id value to match.";
      amm:type "//ietf/amm-base/typedef/id-int";
    }
    amm:parameter max-value {
      description
        "The maximum org-id value to match.";
      amm:type "//ietf/amm-base/typedef/id-int";
    }
    amm:operand value {
      description
        "The reference value to check.
         If the reference does not use integer form of org-id,
         it SHALL be dereferenced and translated to integer form.";
      amm:union {
        amm:type "/aritype/object";
        amm:type "/aritype/namespace";
      }
    }
    amm:result match {
      description
        "True if and only if the org-id is within the
         desired inclusive range.";
      amm:type "/aritype/bool";
    }
  }
  amm:oper is-model-odm {
    amm:enum 38;
    description
      "Predicate to determine if an object or
       namespace reference value has a namespace which
       is is an ODM (i.e. has an model-id which is a negative
       integer or text with a leading bang).";
    amm:operand value {
      description
        "The reference value to check.
         This value SHOULD NOT be de-referenced.";
      amm:union {
        amm:type "/aritype/object";
        amm:type "/aritype/namespace";
      }
    }
    amm:result match {
      description
        "True if and only if the model is an ODM.";
      amm:type "/aritype/bool";
    }
  }
  amm:oper match-model-int-range {
    amm:enum 39;
    description
      "Predicate to determine if a de-referenced object or
       namespace reference value has a namespace which
       has a model-id which is within a specific integer range.";
    amm:parameter min-value {
      description
        "The minimum model-id value to match.";
      amm:type "//ietf/amm-base/typedef/id-int";
    }
    amm:parameter max-value {
      description
        "The maximum model-id value to match.";
      amm:type "//ietf/amm-base/typedef/id-int";
    }
    amm:operand value {
      description
        "The reference value to check.
         If the reference does not use integer form of model-id,
         it SHALL be dereferenced and translated to integer form.";
      amm:union {
        amm:type "/aritype/object";
        amm:type "/aritype/namespace";
      }
    }
    amm:result match {
      description
        "True if and only if the model-id is within the
         desired inclusive range.";
      amm:type "/aritype/bool";
    }
  }
  amm:oper is-same-ns {
    amm:enum 40;
    description
      "Predicate to determine if a de-referenced object or
       namespace reference value matches a desired namespace
       from a parameter.
       The comparison is on the actual namespace, regardless
       of whether integer or text IDs are used in either.";
    amm:parameter desired {
      description
        "A reference to the desired namespace to compare with.
         If this de-reference fails the result SHALL be undefined.";
      amm:type "/aritype/namespace";
    }
    amm:operand value {
      description
        "The reference value to compare with the desired
         namespace.
         If the value is an object reference, it SHOULD only have
         its namespace portion (org-id and model-id) dereferenced
         and compared with the desired namespace.";
      amm:union {
        amm:type "/aritype/object";
        amm:type "/aritype/namespace";
      }
    }
    amm:result match {
      description
        "True if and only if the value references the same
         namespace as the desired.";
      amm:type "/aritype/bool";
    }
  }
  amm:oper match-object-type {
    amm:enum 42;
    description
      "Predicate to determine if a de-referenced object reference
       value has a specific object type.";
    amm:parameter desired {
      description
        "The desired object type, either by built-in type reference,
         primitive integer enumeration, or text name.
         If the desired type is unknown to the Agent the result
         SHALL be undefined.";
      amm:type "/aritype/aritype";
    }
    amm:operand value {
      description
        "The object reference value to check.
         If the de-reference itself fails the result SHALL be
         false.";
      amm:type "/aritype/object";
    }
    amm:result match {
      description
        "True if and only if the type-id matches the desired
         object type.";
      amm:type "/aritype/bool";
    }
  }
  amm:oper match-object-int-range {
    amm:enum 44;
    description
      "Predicate to determine if a de-referenced object reference
       value has an obj-id which is within a specific integer
       range.";
    amm:parameter min-value {
      description
        "The minimum obj-id value to match.";
      amm:type "//ietf/amm-base/typedef/id-int";
    }
    amm:parameter max-value {
      description
        "The maximum obj-id value to match.";
      amm:type "//ietf/amm-base/typedef/id-int";
    }
    amm:operand value {
      description
        "The reference value to check.
         If the reference does not use integer form of obj-id,
         it SHALL be dereferenced and translated to integer form.";
      amm:type "/aritype/object";
    }
    amm:result match {
      description
        "True if and only if the obj-id is within the
         desired inclusive range.";
      amm:type "/aritype/bool";
    }
  }
  amm:oper is-same-object {
    amm:enum 41;
    description
      "Predicate to determine if a de-referenced object
       reference value matches a desired object
       from a parameter.
       The comparison is on the actual object instance, regardless
       of whether integer or text IDs are used in either.";
    amm:parameter desired {
      description
        "A reference to the desired object to compare with.
         If this de-reference fails the result SHALL be undefined.";
      amm:type "/aritype/object";
    }
    amm:operand value {
      description
        "The reference value to compare with the desired object.
         If this de-reference fails the result SHALL be false.";
      amm:type "/aritype/object";
    }
    amm:result match {
      description
        "True if and only if the value references the same object
         as the desired.";
      amm:type "/aritype/bool";
    }
  }
  amm:oper ref {
    amm:enum 43;
    description
      "A zero-ary operator to copy a reference value parameter
       into its result.
       This is a work-around for <//ietf/amm-base/typedef/expr-item>
       permitting only literal or OPER references.";
    amm:parameter ref {
      description
        "The input reference value.";
      amm:union {
        amm:type "/aritype/object";
        amm:type "/aritype/namespace";
      }
    }
    amm:result ref {
      description
        "The output reference value.";
      amm:union {
        amm:type "/aritype/object";
        amm:type "/aritype/namespace";
      }
    }
  }

  // Unary predicate function composition
  amm:oper predicate-all {
    amm:enum 24;
    description
      "Compose unary predicate operators with a result that is true
       only when all of the subordinate operators evaluate to a
       truthy result.
       If any operator evaluates to the undefined value it is
       considered not truthy and this result will be false.";
    uses predicate-compose-interface;
  }
  amm:oper predicate-any {
    amm:enum 25;
    description
      "Compose unary predicate operators with a result that is true
       when any of the subordinate operators evaluate to a
       truthy result.
       If any operator evaluates to the undefined value it is
       considered not truthy, so other operators are still
       part of the result which may be true.";
    uses predicate-compose-interface;
  }
  amm:oper predicate-none {
    amm:enum 26;
    description
      "Compose unary predicate operators with a result that is true
       when all of the subordinate operators do not evaluate to a
       truthy result.
       If any operator evaluates to the undefined value it is
       considered not truthy, so other operators are still
       part of the result which may be true.";
    uses predicate-compose-interface;
  }

  // sub-expression evaluation operators
  amm:oper eval {
    amm:enum 28;
    description
      "A zero-ary operator which functions by evaluating a target
       sub-expression using the following phases:
         1. If the target is a reference, it is used to produce
            a value which SHALL be an expression.
            Otherwise, the target SHALL itself be an expression.
         2. Evaluate the expression and consider the evaluation
            result as this operator result.";
    amm:parameter target {
      description
        "Either an inline sub-expression or a reference to an
         object which produces an expression.";
      amm:type "//ietf/amm-base/typedef/eval-tgt";
    }
    amm:result sub-result {
      description
        "The result of the sub-expression evaluation.";
      amm:type "//ietf/amm-base/typedef/any";
    }
  }
  amm:oper unary-eval {
    amm:enum 27;
    description
      "A unary operator which functions by evaluating a target
       sub-expression using the following phases:
         1. Substitute the bind-value actual parameter for
            </label/0> items within the target value
            (literal expression or object reference).
         2. If the target is a reference, it is used to produce
            a value which SHALL be an expression.
            Otherwise, the target SHALL itself be an expression.
         3. Evaluate the expression and consider the evaluation
            result as this operator result.
       This is similar to the <./oper/eval> object with the
       addition of the unary operand binding.";
    amm:parameter target {
      description
        "Either an inline sub-expression or a reference to an
         object which produces an expression.";
      amm:type "//ietf/amm-base/typedef/eval-tgt";
    }
    amm:operand bind-value {
      description
        "The value to pass-through as </label/0> during
         the substitution phase of evaluation with each of the
         subordinate operators.
         The label does not need to be present in this
         target, the operand can simply be ignored.
         Any label values of 1 or larger present
         will cause the evaluation to fail and result in
         the undefined value.";
      amm:type "//ietf/amm-base/typedef/any";
    }
    amm:result sub-result {
      description
        "The result of the sub-expression evaluation.";
      amm:type "//ietf/amm-base/typedef/any";
    }
  }
  amm:oper nary-eval {
    amm:enum 31;
    description
      "An N-ary operator which functions by evaluating a target
       sub-expression using the following phases:
         1. Substitute the bind-values actual parameter for
            LABEL items with integer primitive (e.g. </label/0>)
            within the target value
            (literal expression or object reference).
            The number of bind-able operands is given by the
            _operand-count_ parameter.
         2. If the target is a reference, it is used to produce
            a value which SHALL be an expression.
            Otherwise, the target SHALL itself be an expression.
         3. Evaluate the expression and consider the evaluation
            result as this operator result.
       This is similar to the <./oper/eval> object with the
       addition of the unary operand binding.";
    amm:parameter operand-count {
      description
        "The number of operands to pop from the evaluation stack
         and use as bind-values for the target parameter.
         This is limited to signed int length because LABEL
         values are also limited to signed int.";
      amm:type "/aritype/int" {
        range "0..max";
      }
    }
    amm:parameter target {
      description
        "Either an inline sub-expression or a reference to an
         object which produces an expression.
         Not all valid labels, 0 through (_operand-count_ - 1),
         need to be present in this target, some operands can
         simply be popped and ignored.
         Any label values of _operand-count_ or larger present
         will cause the evaluation to fail and result in
         the undefined value.";
      amm:type "//ietf/amm-base/typedef/eval-tgt";
    }
    amm:operand bind-values {
      description
        "The evaluation stack values to substitute for LABEL values
         during the substitution phase of evaluation.
         A total of _operand-count_ values will be popped for this
         sequence.
         Label 0 refers to the bottom-most popped value from
         the stack and label (_operand-count_ - 1) refers to the
         top of the stack.";
      amm:seq {
        amm:type "//ietf/amm-base/typedef/any";
      }
    }
    amm:result sub-result {
      description
        "The result of the sub-expression evaluation.";
      amm:type "//ietf/amm-base/typedef/any";
    }
  }

  // Table (TBL) filtering
  amm:typedef tbl-row-filter {
    amm:enum 0;
    description
      "A table filter applied using two phases for each row:
         1. Substitute row values for LABEL items within EXPR.
            This does not apply recursively to VALUE-OBJ within
            the expression.
         2. Evaluate the expression and consider the row matched
            if the result is a truthy value.
       Each LABEL item refers to the value at a column index
       within the context of the input row. Label substitution
       is performed as described in the value production section
       of the DTNMA AMM document.";
    reference
      "draft-ietf-dtn-amm";
    amm:type "//ietf/amm-base/typedef/EXPR";
  }
  amm:oper tbl-filter {
    amm:enum 20;
    description
      "Filter a table first by rows (using an expression) and then
       by columns (using identifiers).";
    amm:parameter rows {
      description
        "A filter for each row.";
      amm:type "./typedef/tbl-row-filter";
    }
    amm:parameter columns {
      description
        "A filter to restrict output to only the listed columns.
         The order of columns in the filtered result table SHALL
         correspond with the order of columns in this list.";
      amm:ulist {
        amm:type "/aritype/UVAST";
      }
    }
    amm:operand in {
      description
        "Table to filter.";
      amm:type "/aritype/TBL";
    }
    amm:result out {
      description
        "The filtered table.";
      amm:type "/aritype/TBL";
    }
  }
  amm:oper tbl-get {
    amm:enum 32;
    description
      "Retrieve an item from the given table.";
    amm:parameter row {
      description
        "Index of the row (major axis) of the item.";
      amm:type "/aritype/uint";
    }
    amm:parameter column {
      description
        "Index of the column (minor axis) of the item.";
      amm:type "/aritype/uint";
    }
    amm:operand in {
      description
        "List to retrieve a value from.";
      amm:type "/aritype/TBL";
    }
    amm:result out {
      description
        "The retrieved value or undefined if the index is not
         valid.";
      amm:type "//ietf/amm-base/typedef/any";
    }
  }

  // List (AC) filtering
  amm:oper list-get {
    amm:enum 21;
    description
      "Retrieve an item from the given list.";
    amm:parameter index {
      description
        "Index of the value to retrieve from the list.";
      amm:type "/aritype/uint";
    }
    amm:operand in {
      description
        "List to retrieve a value from.";
      amm:type "/aritype/AC";
    }
    amm:result out {
      description
        "The retrieved value or undefined if the index is not
         valid.";
      amm:type "//ietf/amm-base/typedef/any";
    }
  }

  // Map (AM) filtering
  amm:oper map-get {
    amm:enum 22;
    description
      "Retrieve an item from the given map.";
    amm:parameter key {
      description
        "Key of the value to retrieve from the map.";
      amm:type "//ietf/amm-base/typedef/primitive";
    }
    amm:operand in {
      description
        "Map to retrieve a value from.";
      amm:type "/aritype/AM";
    }
    amm:result out {
      description
        "The retrieved value or undefined if the key is not valid.";
      amm:type "//ietf/amm-base/typedef/any";
    }
  }
}
