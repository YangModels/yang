module ietf-restconf-client {
  yang-version 1.1;

  namespace "urn:ietf:params:xml:ns:yang:ietf-restconf-client";
  prefix "rcc";

  import ietf-inet-types {
    prefix inet;
    reference
      "RFC 6991: Common YANG Data Types";
  }

  import ietf-tls-client {
    prefix ts;
    revision-date 2017-03-13; // stable grouping definitions
    reference
      "RFC ZZZZ: TLS Client and Server Models";
  }

  organization
   "IETF NETCONF (Network Configuration) Working Group";

  contact
   "WG Web:   <http://tools.ietf.org/wg/restconf/>
    WG List:  <mailto:restconf@ietf.org>

    Author:   Kent Watsen
              <mailto:kwatsen@juniper.net>

    Author:   Gary Wu
              <mailto:garywu@cisco.com>";

  description
   "This module contains a collection of YANG definitions for
    configuring RESTCONF clients.

    Copyright (c) 2014 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2017-03-13" {
    description
     "Initial version";
    reference
     "RFC XXXX: RESTCONF Client and Server Models";
  }

  // Features

  feature initiate {
    description
     "The 'initiate' feature indicates that the RESTCONF client
      supports initiating RESTCONF connections to RESTCONF servers
      using at least one transport (e.g., TLS, etc.).";
  }

  feature tls-initiate {
    description
     "The 'tls-initiate' feature indicates that the RESTCONF client
      supports initiating TLS connections to RESTCONF servers.";
    reference
     "RFC 8040: RESTCONF Protocol";
  }

  feature listen {
    description
     "The 'listen' feature indicates that the RESTCONF client
      supports opening a port to accept RESTCONF server call
      home connections using at least one transport (e.g.,
      TLS, etc.).";
  }

  feature tls-listen {
    description
     "The 'tls-listen' feature indicates that the RESTCONF client
      supports opening a port to listen for incoming RESTCONF
      server call-home TLS connections.";
    reference
     "RFC 8071: NETCONF Call Home and RESTCONF Call Home";
  }

  container restconf-client {
    description
      "Top-level container for RESTCONF client configuration.";

    container initiate {
      if-feature initiate;
      description
        "Configures client initiating underlying TCP connections.";
      list restconf-server {
        key name;
        description
          "List of RESTCONF servers the RESTCONF client is to initiate
           connections to.";
        leaf name {
          type string;
          description
            "An arbitrary name for the RESTCONF server.";
        }
        choice transport {
          mandatory true;
          description
            "Selects between available transports.";

          case tls {
            if-feature tls-initiate;
            container tls {
              description
                "Specifies TLS-specific transport configuration.";
              uses endpoints-container {
                refine endpoints/endpoint/port {
                  default 443;
                }
              }
              uses ts:tls-client-grouping;
            }
          } // end tls

        } // end transport

        container connection-type {
          description
           "Indicates the kind of connection to use.";
          choice connection-type {
            description
              "Selects between available connection types.";
            case persistent-connection {
              container persistent {
                presence true;
                description
                 "Maintain a persistent connection to the RESTCONF
                  server. If the connection goes down, immediately
                  start trying to reconnect to it, using the
                  reconnection strategy.

                  This connection type minimizes any RESTCONF server
                  to RESTCONF client data-transfer delay, albeit at
                  the expense of holding resources longer.";
                leaf idle-timeout {
                  type uint32;
                  units "seconds";
                  default 86400;  // one day;
                  description
                    "Specifies the maximum number of seconds that a
                     a RESTCONF session may remain idle. A RESTCONF
                     session will be dropped if it is idle for an
                     interval longer than this number of seconds.
                     If set to zero, then the client will never drop
                     a session because it is idle.  Sessions that
                     have a notification subscription active are
                     never dropped.";
                }
                container keep-alives {
                  description
                    "Configures the keep-alive policy, to proactively
                     test the aliveness of the SSH/TLS server.  An
                     unresponsive SSH/TLS server will be dropped after
                     approximately max-attempts * max-wait seconds.";
                  reference
                    "RFC 8071: NETCONF Call Home and RESTCONF Call
                     Home, Section 3.1, item S6";
                  leaf max-wait {
                    type uint16 {
                      range "1..max";
                    }
                    units seconds;
                    default 30;
                    description
                     "Sets the amount of time in seconds after which
                      if no data has been received from the SSH/TLS
                      server, a SSH/TLS-level message will be sent
                      to test the aliveness of the SSH/TLS server.";
                  }
                  leaf max-attempts {
                    type uint8;
                    default 3;
                    description
                     "Sets the maximum number of sequential keep-alive
                      messages that can fail to obtain a response from
                      the SSH/TLS server before assuming the SSH/TLS
                      server is no longer alive.";
                  }
                }
              }
            }
            case periodic-connection {
              container periodic {
                presence true;
                description
                 "Periodically connect to the RESTCONF server, so that
                  the RESTCONF server may deliver messages pending for
                  the RESTCONF client.  The RESTCONF server must close
                  the connection when it is ready to release it. Once
                  the connection has been closed, the RESTCONF client
                  will restart its timer until the next connection.";
                leaf idle-timeout {
                  type uint16;
                  units "seconds";
                  default 300; // five minutes
                  description
                    "Specifies the maximum number of seconds that a
                     a RESTCONF session may remain idle. A RESTCONF
                     session will be dropped if it is idle for an
                     interval longer than this number of seconds.
                     If set to zero, then the server will never drop
                     a session because it is idle.  Sessions that
                     have a notification subscription active are
                     never dropped.";
                }
                leaf reconnect-timeout {
                  type uint16 {
                    range "1..max";
                  }
                  units minutes;
                  default 60;
                  description
                   "Sets the maximum amount of unconnected time the
                    RESTCONF client will wait before re-establishing
                    a connection to the RESTCONF server.  The RESTCONF
                    client may initiate a connection before this
                    time if desired (e.g., to set configuration).";
                }
              }
            }
          }
        }
        container reconnect-strategy {
          description
           "The reconnection strategy directs how a RESTCONF client
            reconnects to a RESTCONF server, after discovering its
            connection to the server has dropped, even if due to a
            reboot.  The RESTCONF client starts with the specified
            endpoint and tries to connect to it max-attempts times
            before trying the next endpoint in the list (round
            robin).";
          leaf start-with {
            type enumeration {
              enum first-listed {
                description
                  "Indicates that reconnections should start with
                   the first endpoint listed.";
              }
              enum last-connected {
                description
                  "Indicates that reconnections should start with
                   the endpoint last connected to.  If no previous
                   connection has ever been established, then the
                   first endpoint configured is used.   RESTCONF
                   clients SHOULD be able to remember the last
                   endpoint connected to across reboots.";
              }
            }
            default first-listed;
            description
             "Specifies which of the RESTCONF server's endpoints the
              RESTCONF client should start with when trying to connect
              to the RESTCONF server.";
          }
          leaf max-attempts {
            type uint8 {
              range "1..max";
            }
            default 3;
            description
             "Specifies the number times the RESTCONF client tries to
              connect to a specific endpoint before moving on to the
              next endpoint in the list (round robin).";
          }
        }
      } // end restconf-server
    } // end initiate
    container listen {
      if-feature listen;
      description
        "Configures client accepting call-home TCP connections.";

      leaf max-sessions {
        type uint16;
        default 0;
        description
          "Specifies the maximum number of concurrent sessions
           that can be active at one time.  The value 0 indicates
           that no artificial session limit should be used.";
      }

      leaf idle-timeout {
        type uint16;
        units "seconds";
        default 3600; // one hour
        description
          "Specifies the maximum number of seconds that a RESTCONF
           session may remain idle. A RESTCONF session will be dropped
           if it is idle for an interval longer than this number of
           seconds.  If set to zero, then the server will never drop
           a session because it is idle.  Sessions that have a
           notification subscription active are never dropped.";
      }

      list endpoint {
        key name;
        description
          "List of endpoints to listen for RESTCONF connections.";
        leaf name {
          type string;
          description
            "An arbitrary name for the RESTCONF listen endpoint.";
        }
        choice transport {
          mandatory true;
          description
            "Selects between available transports.";
          case tls {
            if-feature tls-listen;
            container tls {
              description
                "TLS-specific listening configuration for inbound
                 connections.";
              leaf address {
                type inet:ip-address;
                description
                 "The IP address to listen for call-home connections.";
              }
              leaf port {
                type inet:port-number;
                default 4336;
                description
                 "The port number to listen for call-home connections.";
              }
              uses ts:tls-client-grouping;
            }
          }
        } // end transport
      } // end endpoint
    } // end listen

  } // end restconf-client

  grouping endpoints-container {
    description
      "This grouping is used to configure a set of RESTCONF servers
       a RESTCONF client may initiate connections to.";
    container endpoints {
      description
        "Container for the list of endpoints.";
      list endpoint {
        key name;
        unique "address port";
        min-elements 1;
        ordered-by user;
        description
          "A non-empty user-ordered list of endpoints for this RESTCONF
           client to try to connect to.  Defining more than one enables
           high-availability.";
        leaf name {
          type string;
          description
            "An arbitrary name for this endpoint.";
        }
        leaf address {
          type inet:host;
          mandatory true;
          description
           "The IP address or hostname of the endpoint.  If a
            hostname is configured and the DNS resolution results
            in more than one IP address, the RESTCONF client
            will process the IP addresses as if they had been
            explicitly configured in place of the hostname.";
        }
        leaf port {
          type inet:port-number;
          description
           "The IP port for this endpoint. The RESTCONF client will
            use the IANA-assigned well-known port (set via a refine
            statement when uses) if no value is specified.";
        }
      }
    }
  }
}
