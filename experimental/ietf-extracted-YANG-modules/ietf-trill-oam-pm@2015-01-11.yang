module ietf-trill-oam-pm {
     namespace "urn:ietf:params:xml:ns:yang:ietf-trill-oam-pm";
     prefix trilloampm;

     import ietf-gen-oam {
       prefix goam;
     }
     import ietf-trill-oam {
       prefix toam;
     }
     import ietf-yang-types {
       prefix yang;
     }
     organization "IETF TRILL Working Group";
     contact
       "Deepak Kumar dekumar@cisco.com";
     description
       "This YANG module defines the configuration for TRILL,
        OAM Performance Management statistics and rpc";

     revision 2015-01-11 {
       description
         "Initial revision.";
       reference "RFC 7456";
     }

     identity trill {
       base goam:technology-types;
       description
         "trill type";
     }

     grouping context-id-group {
        leaf context-type {
	   type boolean;
        description
          "context Identifier";
	   }
	description
	  "If context-type is set then it's context-id-vlan, else
	   it's context-id-fgl.";
        leaf context-id-vlan {
	     type toam:vlan;
          description
            "context Identifier vlan.";
	   }
	   leaf context-id-fgl {
	      type toam:fgl;
           description
             "context Identifier Fine Grain label.";
	   }
     }

     grouping loss-measurement-configuration-group {
       description
         "This grouping includes configuration objects for Frame Loss
	  Measurement function defined in TRILL-PM.";
       reference
          TRILL-PM;

	   leaf measurement-type {
	     type enumeration {
	       enum slm {
	         description
	           "TRILL PM SLM Frames generated and
                     received SLR responses
	            tracked.";
	       }
               enum 1sl {
                 description
	           "TRILL PM 1SL Frames generated.";
               }
	     }
	     default slm;

	     description
	       "This object specifies what type of Loss Measurement will be
	        performed.";
	     reference
	       TRILL-PM;
	   }

	   leaf enabled-counters {
	     type bits {
	       bit forward-min-flr {
            description
              "Forward minimum Frame Loss Ratio.";
            }
	       bit forward-max-flr {
            description
              "Forward maximum Frame Loss Ratio.";
            }
	       bit forward-average-flr {
            description
              "Forward average Frame Loss Ratio.";
            }
	       bit backward-min-flr {
            description
              "Backward Minimum Frame Loss Ratio.";
            }
	       bit backward-max-flr {
            description
              "Backward Maximum Frame Loss Ratio.";
            }
	       bit backward-average-flr {
            description
               "Backward Average Frame Loss Ratio.";
            }
	       bit TRILL-PM-pdus-sent {
            description
               "TRILL PM Packets sent.";
            }
	       bit TRILL-PM-pdus-received {
            description
               "TRILL PM Packets received.";
            }
	     }
         default " ";

         description
           "A vector of bits that indicates the type of TRILL-PM loss
            measurement coutners found in the
            current-stats and history
            that are enabled.

            A present bit enables the specific counter. A not present
            bit disables the specific counter.

            Not all counters are supported for all
            TRILL-PM Loss Measurement types.";
	   }

       leaf message-period {
	     type uint32;
	     default 1000;

	     description
	       "This objects specifies the interval between Loss
	        Measurement OAM message transmission. Default value is
	        1 sec.";
	   }

       leaf frame-size {
	     type uint32 {
	       range "64 .. 9600";
	     }
	     default 64;
	     description
	       "This object specifies the Loss
                 Measurement OAM frame size.
	        The adjustment of the frame size of the
                 standard frame size is
	        accomplished by addition of a Data TLV
                 as mention in TRILL-PM.
	        ";
	   }

	   leaf data-pattern {
	     type enumeration {
	       enum zeroes {
	         description "Indicates the Data TLV contains all 0s.";
	       }
	       enum ones {
	         description "Indicates the Data TLV contains all 1s.";
	       }
	     }
	     default zeroes;

	     description
	       "This object specifies the LM data pattern included in OAM
	        frame.";
	   }

	   leaf measurement-interval {
	     type uint32;
	     units minutes;
	     default 15;

	     description
	       "This object specifies a Measurement Interval in minutes.";
	   }

       leaf number-intervals-stored {
         type uint32 {
            range "2..10";
         }
         default 10;
         description
           "This object specifies the number of
            completed measurement
            intervals to store in the history statistics table.";
       }

	   leaf session-type {
	     type enumeration {
	       enum proactive {
	         description
		   "The current session is 'proactive'.";
	       }
	       enum on-demand {
	         description
		   "The current session is on-demand.";
	       }
	     }
	     description
	       "This object indicates whether the current session is defined
	        to be proactive or on-demand.";
	   }
     }

     grouping loss-stats-group {
       description
         "This grouping includes statistics object for TRILL PM Loss
          Measurement session.";
       leaf suspect-status {
	    type boolean;
	    description
	      "if bit is set it means measurement
                interval statistics is
	       not valid.";
       }

       leaf backward-transmitted-frames {
         type yang:gauge32;

         description
           "This object contains the number of
            frames transmitted in the
            backward direction by this session.
            This is count of TRILL-PM SLM and 1SL frames.";
       }
       leaf backward-received-frames {
         type yang:gauge32;

         description
           "This object contains the number of
            frames received in the
            backward direction by this session.
            This is count of TRILL-PM SLM and 1SL frames.";
       }
       leaf backward-min-frame-loss-ration {
          type uint32 {
            range "0..100000";
          }
          units milli-percent;

          description
            "This object contains the minimum
             one-way frame loss ratio
             in the backward direction calculated by this
             MEP for the session
             in this Measurement Interval.
             The FLR value is a ratio that
             is expressed as a percent with a value 0
             (ratio 0.00) through
             100000 (ration 1.00)";
       }
       leaf backward-max-frame-loss-ration {
          type uint32 {
            range "0..100000";
          }
          units milli-percent;

          description
            "This object contains the maximum
             one-way frame loss ratio
             in the backward direction calculated by
             this MEP for the session
             in this Measurement Interval.
             The FLR value is a ratio that
             is expressed as a percent with a value 0
             (ratio 0.00) through
             100000 (ration 1.00)";
       }
       leaf backward-average-frame-loss-ration {
          type uint32 {
            range "0..100000";
          }
          units milli-percent;

          description
            "This object contains the average
             one-way frame loss ratio
             in the backward direction calculated
             by this MEP for the session
             in this Measurement Interval.
             The FLR value is a ratio that
             is expressed as a percent with a
             value 0 (ratio 0.00) through
             100000 (ration 1.00)";
       }

       leaf forward-transmitted-frames {
         type yang:gauge32;

         description
           "This object contains the number of
            frames transmitted in the
            forward direction by this session.
            This is count of TRILL-PM SLM and 1SL frames.";
       }
       leaf forward-received-frames {
         type yang:gauge32;

         description
           "This object contains the number
            of frames received in the
            forward direction by this session.
            This is count of TRILL-PM SLM and 1SL frames.";
       }
       leaf forward-min-frame-loss-ration {
          type uint32 {
            range "0..100000";
          }
          units milli-percent;

          description
            "This object contains the minimum one-way
             frame loss ratio
             in the forward direction calculated by this MEP
             for the session
             in this Measurement Interval.
             The FLR value is a ratio that
             is expressed as a percent with a value
             0 (ratio 0.00) through
             100000 (ration 1.00)";
       }
       leaf forward-max-frame-loss-ration {
          type uint32 {
            range "0..100000";
          }
          units milli-percent;

          description
            "This object contains the maximum one-way
             frame loss ratio
             in the forward direction calculated by this MEP
             for the session
             in this Measurement Interval. The FLR value is
             a ratio that
             is expressed as a percent with a value
             0 (ratio 0.00) through
             100000 (ration 1.00)";
       }
       leaf forward-average-frame-loss-ration {
          type uint32 {
            range "0..100000";
          }
          units milli-percent;

          description
            "This object contains the average one-way
             frame loss ratio
             in the forward direction calculated by this
             MEP for the session
             in this Measurement Interval. The FLR value
             is a ratio that
             is expressed as a percent with a value
             0 (ratio 0.00) through
             100000 (ration 1.00)";
       }

     }

     grouping measurement-timing-group {
       description
         "This grouping includes objects used for
          proactive and on-demand
	 scheduling of PM measurement sessions.";

	container start-time {
	  description
	  "This container defines the session start time.";

	  choice start-time {
	    description
	      "Measurement sessions tart time can be immediate, relative, or
	       absolute.";

	     container immediate {
	       presence "Start the measurement session immediately.";
            description
              "Immediate start time.";
	     }
	     leaf absolute {
	       type yang:date-and-time;

	       description
	         "This objects specifies the scheduled start time
		  to perform the on-demand monitoring operations.";
	     }
	  }
	}

	   container stop-time {
	     description
	       "This container defines the session stop time.";

	     choice stop-time {
	       description
	         "Measurement session stop time can be none, or absolute.";

	       container none {
	         presence "Never end the measurement session.";
              description
                "None.";
	       }

	       leaf absolute {
	          type yang:date-and-time;

	          description
	            "This objects specifies the scheduled stop time
	         to perform the on-demand monitoring operations.";
	       }
	     }
	   }
     }

     grouping delay-measurement-configuration-group {
       description
         "This grouping includes configuration objects for Delay
	  Measurement function defined in TRILL-PM.";
       reference
          "TRILL-PM.";

       leaf measurement-type {
         type enumeration {
	       enum dmm {
	         description
	           "DMM PDU generated, DMR responses received.";
	       }
	       enum dm1-transmitted {
	         description
	           "1DM PDU generated.";
	       }
	       enum dm1-received {
	         description
	           "1DM PDU received and measurement generated.";
	       }
	     }
          description
            "Measurement type.";
       }

       leaf measurement-enable {
	   type bits {
	     bit toam-sent {
          description
            "Trill oam sent.";
          }
	     bit toam-received {
          description
            "Trill oam received.";
          }
	     bit frame-delay-two-way-min {
          description
            "Frame Delay Two Way Minimum.";
          }
	     bit frame-delay-two-way-max {
          description
            "Frame Delay Two way Maximum.";
          }
	     bit frame-delay-two-way-average {
          description
            "Frame Delay Two way Average.";
          }
	     bit frame-delay-forward-min {
          description
            "Frame Delay Forward Minimum.";
          }
	     bit frame-delay-forward-max {
          description
            "Frame Delay forward Maximum.";
          }
	     bit frame-delay-forward-average {
          description
            "Frame Delay forward Average.";
          }
	     bit frame-delay-backward-min {
          description
            "Frame Delay backward minimum.";
          }
	     bit frame-delay-backward-max {
          description
            "Frame Delay backward maximum.";
          }
	     bit frame-delay-backward-average {
          description
            "Frame Delay backward average.";
          }
	     bit inter-frame-delay-variation-forward-min {
          description
            "Inter Frame Delay variation forward minimum.";
          }
	     bit inter-frame-delay-variation-forward-max {
          description
            "Inter Frame delay variation forward maximum.";
          }
	     bit inter-frame-delay-variation-forward-average {
          description
            "Inter Frame delay variation forward average.";
          }
	     bit inter-frame-delay-variation-backward-min {
          description
            "Inter frame delay variation backward minimum.";
          }
	     bit inter-frame-delay-variation-backward-max {
          description
            "Inter Frame Delay variation backward maximum.";
          }
	     bit inter-frame-delay-variation-backward-average {
          description
            "Inter Frame delay variation backward average.";
          }
	     bit inter-frame-delay-variation-two-way-min {
          description
            "Inter Frame delay variation two way minimum.";
          }
	     bit inter-frame-delay-variation-two-way-max {
          description
            "Inter Frame delay variation two way maximum.";
          }
	     bit inter-frame-delay-variation-two-way-average {
          description
            "Inter Frame delay variation Two way Average.";
          }
	   }
	   default " ";

	   description
	    "A vector of bits that indicates the type of DM counters
	     that are enabled. A set bit enables the specific DM
	     counter. A clear bit disables the specific DM counter.
	     Not all DM counters are supported for all DM types.";
	 }
     leaf message-period {
	   type uint32;
	   default 100;

	   description
	     "This objects specifies the interval between Delay
	      Measurement OAM message transmission. Default value is
	      100ms.";
	 }

	 leaf frame-size {
	   type uint32 {
	     range "64 .. 9600";
	   }
	   default 64;

	   description
	     "This object specifies the Delay Measurement OAM frame size.
	      The adjustment of the frame size of the
               standard frame size is
	      accomplished by addition of a Data TLV as
               mention in TRILL-PM.
	      ";
	 }

	 leaf data-pattern {
	   type enumeration {
	     enum zeroes {
	       description "Indicates the Data TLV contains all 0s.";
	     }
	     enum ones {
	       description "Indicates the Data TLV contains all 1s.";
	     }
	   }
	   default zeroes;

	   description
	     "This object specifies the DM data pattern included in OAM
	      frame.";
	 }

	 leaf measurement-interval {
	   type uint32;
	   units minutes;
	   default 15;

	   description
	     "This object specifies a Measurement Interval in minutes.";
	 }

     leaf number-intervals-stored {
         type uint32 {
            range "2..10";
         }
         default 10;
         description
           "This object specifies the number of completed measurement
            intervals to store in the history statistics table.";
     }

	 leaf ifdv-selection-offset {
	   type uint32 {
	     range "1..10";
	   }
	   default 1;
	   description
	     "This object specifies the selection offset for Inter
	    Frame Delay variation measurements. If this value is set
	    to n, then the IFDV is calculated by taking the difference in
	    frame delay between frame F and frame (F+n).";
	  }

	  leaf session-type {
	     type enumeration {
	       enum proactive {
	         description
		     "The current session is 'proactive'.";
	       }
	       enum on-demand {
	         description
		     "The current session is on-demand.";
	       }
	    }
	    description
	      "This object indicates whether the current session is defined
	       to be proactive or on-demand.";
	   }

     }

     grouping delay-measurement-stats-group {
       description
	   "This grouping includes statistics objects for a TRILL PM
	    Delay Measurement session.";

	   leaf suspect-status {
	     type boolean;
	     description
	       "if bit is set it means measurement interval statistics is
	        not valid.";
	   }

	   leaf frame-delay-two-way-min {
	     type uint32;
	     units microseconds;
          description
            "Frame delay two way minimum.";
	   }
	   leaf frame-delay-two-way-max {
	     type uint32;
	     units microseconds;
          description
            "Frame delay two way maximum.";
	   }

	   leaf frame-delay-two-way-average {
	     type uint32;
	     units microseconds;
          description
            "Frame delay two way average.";
	   }

	   leaf frame-delay-forward-min {
	     type uint32;
	     units microseconds;
          description
            "Frame delay forward direction minimum.";
	   }
	   leaf frame-delay-forward-average {
	     type uint32;
	     units microseconds;
          description
            "Frame delay forward direction average.";
	   }
	   leaf frame-delay-forward-max {
	     type uint32;
	     units microseconds;
          description
            "Frame delay forward direction maximum.";
	   }
	   leaf frame-delay-backward-min {
	     type uint32;
	     units microseconds;
          description
            "Frame delay backward direction minimum.";
	   }
	   leaf frame-delay-backward-max {
	     type uint32;
	     units microseconds;
          description
            "Frame delay backward direction maximum.";
	   }
	   leaf frame-delay-backward-average {
	     type uint32;
	     units microseconds;
          description
            "Frame delay backward direction average..";
	   }
	   leaf frame-delay-variation-backward-min {
	     type uint32;
	     units microseconds;
          description
            "Frame delay variation backward minimum.";
	   }
	   leaf frame-delay-variation-backward-max {
	     type uint32;
	     units microseconds;
          description
            "Frame delay variation backward maximum.";
	   }
	   leaf frame-delay-variation-backward-average {
	     type uint32;
	     units microseconds;
          description
            "Frame delay variation backward average.";
	   }
	   leaf frame-delay-variation-forward-min {
	     type uint32;
	     units microseconds;
          description
            "Frame delay variation forward minimum.";
	   }
	   leaf frame-delay-variation-forward-average {
	     type uint32;
	     units microseconds;
          description
            "Frame delay variation forward average.";
	   }
	   leaf frame-delay-variation-forward-max {
	     type uint32;
	     units microseconds;
          description
            "Frame delay variation forward maximum.";
	   }
	   leaf frame-delay-variation-two-way-min {
	     type uint32;
	     units microseconds;
          description
            "Frame delay variation two way minimum.";
	   }
	   leaf frame-delay-variation-two-way-average {
	     type uint32;
	     units microseconds;
          description
            "Frame delay variation two way average.";
	   }
	   leaf frame-delay-variation-two-way-max {
	     type uint32;
	     units microseconds;
          description
            "Frame delay variation two way maximum.";
	   }
     }

     augment "/goam:domains/goam:domain/goam:MAs/goam:MA/goam:MEP" {
       description
         "This set of data definitions extends the MEP as described
          in goam";

       leaf delay-responder {
          type boolean;
          default true;

          description
            "This object specifies whether Delay Measurement (DMM)
             single ended
             Responder is enabled.
             The value 'false' indicates the Delay measurement
             responder is disabled
             and received DMM will be discarded.";

        }
     }
     augment "/goam:domains/goam:domain/goam:MAs/goam:MA/goam:MEP" {
       description
         "This set of data definitions extends the MEP as described
          in goam, specially with regards to Delay Measurements.";

       container delay-measurements {
         description
	   "This container contains a collection of data definitions
	    related to Delay Measurements as defined in TRILL-PM.";

	    list delay-measurements {
	      key "session-cookie";
	      config false;
	      description
	        "List of Delay Measurement PM Sessions where each
		 instance is uniquely identified by an session-cookie
		 attribute.";
	      leaf session-cookie {
             type uint32;
             config false;
		description
		  "cookie to identify Delay Measurement session.";
	      }

           leaf id {
	        type string;

		description
		  "This object uniquely identifies a scheduled measurement
		   time.";
	      }

	      leaf status {
	        type boolean;
		config false;
		description
		  "This object indicates DM session status, true means
		   Active, false means not-active.";
	      }
	    }

	    uses delay-measurement-configuration-group;
            uses measurement-timing-group;
            container destination-mep {
	       uses goam:mp-address;
	       leaf mep-id {
	         type toam:tril-rb-nickname;
              description
                "MEP Identifier.";
	       }
            description
              "Delay Measurement configuration group";
	    }

            leaf frame-delay-two-way {
              type yang:gauge32;
              units microseconds;
              description
                "This object contains the frame delay
                 calculated by this MEP from the last
                 received TRILL-PM frame.
                 This object is undefined if
                 measurement-type is dm1.";
            }

            leaf frame-delay-forward {
              type yang:gauge32;
              units microseconds;
              description
                "This object contains the frame delay in the
                forward direction
                 calculated by this MEP from the last received
                 TRILL-PM frame.
                 One way Delay require sufficiently precise clock
                 Synchronization.
                 This object is undefined if it's dm1-transmitted.";
            }
            leaf frame-delay-backward {
              type yang:gauge32;
              units microseconds;
              description
                "This object contains the frame delay in the
                 backward direction
                 calculated by this MEP from the last received
                 TRILL-PM frame.
                 One way Delay require sufficiently precise clock
                 Synchronization.
                 This object is undefined if it's dm1-transmitted or
                 dm1-received.";
            }
            leaf inter-frame-delay-variation-two-way {
              type yang:gauge32;
              units microseconds;

              description
                "This object contains the last two-way
                 inter-frame delay
                 interval calculated by this MEP.

                 The value of this object is undefined
                 when measurement-type
                 is dm1-transmitted or dm1-received.";
            }
            leaf inter-frame-delay-variation-forward {
              type yang:gauge32;
              units microseconds;

              description
                "This object contains the last one-way
                 inter-frame delay in
                 the forward direction calculated by this MEP.

                 The value of this object is undefined when
                 measurement-type
                 is dm1-transmitted.";
            }
            leaf inter-frame-delay-variation-backward {
              type yang:gauge32;
              units microseconds;

              description
                "This object contains the last one-way inter-frame
                 delay in
                 the backward direction calculated by this MEP.

                 The value of this object is undefined when
                 measurement-type
                 is dm1-transmitted or dm-received.";
            }

            container current-stats {
              description
                "This container contains result of the
                 current Measurement
                 Interval in a TRILL-PM Delay measurement
                 session gathered
                 during the interval indicated by
                 measurement-interval.";

              leaf start-time {
                type yang:date-and-time;

                description
                  "Start time for current measurement interval.";
              }

              leaf elapsed-time {
                type uint32;

                description
                  "Elapsed time for current measurement
                   interval in 0.01
                   seconds.";
              }
              uses delay-measurement-stats-group;
            }

            list history-stats {
              key id;

              description
                 "This list contains the result for
                  historic Measurement
                  Interval for TRILL-PM session.";

              leaf id {
                type uint32;
                description
                  "Identifier";
              }

              leaf start-time {
                type yang:date-and-time;

                description
                  "Start time for measurement interval.";
              }

              leaf elapsed-time {
                type uint32;

                description
                  "Elapsed time for measurement interval in 0.01
                   seconds.";
              }
              uses delay-measurement-stats-group;
            }
       }
     }

     augment "/goam:domains/goam:domain/goam:MAs/goam:MA/goam:MEP" {

       description
         "This set of data definitions extends the MEP as described
          in goam, specially with regards to Loss Measurements.";

       container loss-measurements {
         description
	   "This container contains a collection of data definitions
	    related to Loss Measurements as defined in TRILL-PM.";

	    list loss-measurements {
	      key "session-cookie";
	      config false;
	      description
	        "List of Loss Measurement PM Sessions where each
		 instance is uniquely identified by an session-cookie
		 attribute.";

	      leaf session-cookie {
             type uint32;
             config false;
		description
		  "cookie to identify Loss Measurement session.";
	      }

              leaf id {
	        type string;

		description
		  "This object uniquely identifies a scheduled measurement
		   time.";
	      }

	      leaf status {
	        type boolean;
		config false;
		description
		  "This object indicates DM session status, true means
		   Active, false means not-active.";
	      }
	    }

	    uses loss-measurement-configuration-group;
            uses measurement-timing-group;
            container destination-mep {
	       uses goam:mp-address;
	       leaf mep-id {
	         type toam:tril-rb-nickname;
              description
                "Trill Rbridge Nickname MP address";
	       }
            description
              "Destination MEP";
	       }
            leaf measurement-forward-flr {
              type yang:gauge32 {
                range "0..100000";
              }
              units milli-percent;

              description
                "This object contains the Frame loss Ratio in forward
                 direction.";
            }
            leaf measurement-backward-flr {
              type yang:gauge32 {
                range "0..100000";
              }
              units milli-percent;

              description
                "This object contains the Frame loss Ratio
                 in backward direction.";
            }
            container current-stats {
              description
                "This container contains result of the
                 current Measurement
                 Interval in a TRILL-PM Loss measurement
                 session gathered
                 during the interval indicated by
                 measurement-interval.";

              leaf start-time {
                type yang:date-and-time;

                description
                  "Start time for current measurement interval.";
              }

              leaf elapsed-time {
                type uint32;

                description
                  "Elapsed time for current measurement
                   interval in 0.01 seconds.";
              }
              uses loss-stats-group;
            }

            list history-stats {
              key id;

              description
                 "This list contains the result for
                  historic Measurement
                  Interval for TRILL-PM session.";

              leaf id {
                type uint32;
                description
                  "Identifier.";
              }

              leaf start-time {
                type yang:date-and-time;

                description
                  "Start time for measurement interval.";
              }

              leaf elapsed-time {
                type uint32;

                description
                  "Elapsed time for measurement interval in 0.01
                   seconds.";
              }
              uses loss-stats-group;
            }
       }
     }

     //RPCs related to TRILLOAM PM

     rpc create-loss-measurement {
       description
         "Schedule a one-way and two-way on-demand or proactive
          performance
          monitoring loss measurements on a specific MEP and Flow.

          A list entry associated with the newly created session
          will be
          created in the loss-measurements container and the assigned
          session identifier will be returned in the
          output parameter.";

       input {
         uses loss-measurement-configuration-group;
         uses measurement-timing-group;
         container destination-mep {
	    uses goam:mp-address;
	    leaf mep-id {
	      type toam:tril-rb-nickname;
           description
             "MEP Id.";
	    }
         description
           "";
         }
	 leaf flow-entropy {
           type toam:flow-entropy-trill;
           description
              "";
	 }
         uses context-id-group;
       }
       output {
         leaf session-id {
           type uint32;
           mandatory true;

           description
             "The session identifier of the newly
              created loss measurement session.";
         }
       }

     } //end of rpc

     rpc abort-loss-measurement {
       description
         "Abort a currently running or scheduled
          single-ended on-demand TRILL
          PM function.";

       input {
          uses goam:maintenance-domain-id;
          uses goam:ma-identifier;
          container destination-mep {
	     uses goam:mp-address;
	     leaf mep-id {
	       type toam:tril-rb-nickname;
            description
              "MEP Identifier.";
	     }
          description
            "";
          }
          leaf session-id {
            type uint32;

            mandatory true;
            description
              "The session Id of the measurement session to
               be aborted.";
          }

       }
     } //end of RPC
     rpc create-delay-measurement {
       description
         "Schedule a one-way and two-way on-demand or proactive
          performance
          monitoring delay measurements on a specific MEP and Flow.

          A list entry associated with the newly created session
          will be created in the delay-measurements container
          and the assigned
          session identifier will be returned in the
          output parameter.";

       input {
         uses delay-measurement-configuration-group;
         uses measurement-timing-group;
         container destination-mep {
	    uses goam:mp-address;
	    leaf mep-id {
	      type toam:tril-rb-nickname;
           description
             "MEP Identifier.";
	    }
         description
           "Destination MEP.";
         }
	 leaf flow-entropy {
	   type toam:flow-entropy-trill;
        description
          "Flow Entropy";
	 }
	 uses context-id-group;
       }
       output {
         leaf session-id {
           type uint32;
           mandatory true;

           description
             "The session identifier of the newly created
              delay measurement session.";
         }
       }

     } //end of rpc

     rpc abort-delay-measurement {
       description
         "Abort a currently running or scheduled single-ended
          on-demand TRILL PM function.";

       input {
          uses goam:maintenance-domain-id;
          uses goam:ma-identifier;
          container destination-mep {
	     uses goam:mp-address;
	     leaf mep-id {
	       type toam:tril-rb-nickname;
            description
              "MEP Identifier.";
	     }
          description
            "Destination MEP.";
          }
	  uses context-id-group;
          leaf session-id {
            type uint32;

            mandatory true;
            description
              "The session Id of the measurement session to
               be aborted.";
          }

       }
     } //end of RP
}
