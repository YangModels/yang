module ietf-lm-hierarchy {
  yang-version 1.1;
  namespace "urn:ietf:params:xml:ns:yang:ietf-lm-hierarchy";
  prefix lm;

  import ietf-yang-types { prefix yang; }
  // NOTE: Removed unused import of ietf-inet-types

  organization
    "IETF NETMOD (Network Modeling) Working Group";

  contact
    "WG Web:   <https://datatracker.ietf.org/wg/netmod/>
     WG List:  <mailto:netmod@ietf.org>

     Author: Kevin Williams
             <mailto:telesis001@icloud.com>";

  description
    "This module defines a YANG data model for hierarchical Language
Model (LM) nodes that coordinate inference, summarization and
escalation across tiny/small/large LM tiers.

Copyright (c) 2026 IETF Trust and the persons identified as the
document authors.  All rights reserved.

This document is subject to BCP 78 and the IETF Trust's Legal
Provisions Relating to IETF Documents
(https://trustee.ietf.org/license-info) in effect on the date of
publication of this document.  Please review these documents
carefully, as they describe your rights and restrictions with
respect to this document.  Code Components extracted from this
document must include Revised BSD License text as described in
Section 4.e of the Trust Legal Provisions and are provided without
warranty as described in the Revised BSD License.

This version of this YANG module is part of draft-williams-netmod-lm-hierarchy-topology-02;
see the Internet-Draft itself for full legal notices.";
     reference
       "RFC 7950: The YANG 1.1 Data Modeling Language
        RFC 8407: Guidelines for Authors and Reviewers of YANG Data Model Documents";

     revision 2026-02-11 {
       description
         "Initial revision for I-D draft-williams-netmod-lm-hierarchy-topology-02.";
       reference
         "I-D: draft-williams-netmod-lm-hierarchy-topology-02";
     }

     feature pluggable-token-validation {
       description
         "Indicates support for a pluggable token validation mechanism for
          requests handled by LM nodes.";
     }

     identity lm-node-type {
       description "Base identity for LM node types.";
     }

     identity tiny-lm {
       base lm-node-type;
       description "A lightweight edge-deployed language model.";
     }

     identity small-lm {
       base lm-node-type;
       description "A mid-tier aggregator or summarizer.";
     }

     identity large-lm {
       base lm-node-type;
       description "A central reasoning or escalation endpoint.";
     }

     grouping auth-token-grouping {
       description "Reusable auth-token structure.";
       leaf auth-token {
         type string;
         description "A signed authentication/authorization token.";
       }
     }

     // Top-level configuration for LM hierarchy
     container lm {
       presence
         "Enable LM hierarchy configuration on this device.";
       description
         "Presence of this container enables configuration and state for
          the Language Model (LM) hierarchy on the device.";

       container node {
         description
           "Attributes describing this node within the LM hierarchy.";

         leaf node-id {
           type string;
           description
             "Implementation-specific identifier for this LM node.";
         }

         leaf node-type {
           type identityref { base lm-node-type; }
           description
             "Classification of this node (tiny, small, large).";
         }
       }

       container trust {
         if-feature pluggable-token-validation;
         description
           "Configuration for token validation used to authorize LM
            requests and actions.";

         leaf trust-anchor {
           type string;
           description "Root or public key used for token validation.";
         }

         leaf token-scope-enforced {
           type boolean;
           default true;
           description "Whether to enforce scope claims in tokens.";
         }

         action validate-token {
           description
             "Validate a presented token against the active trust policy.";
           input {
             leaf token {
               type string;
               description
                 "Opaque bearer or structured token presented by a caller.";
             }
           }
           output {
             leaf valid {
               type boolean;
               description
                 "True if the token is valid per current trust policy.";
             }
             leaf reason {
               type string;
               description
                 "Human-readable reason when validation fails, or an
                  implementation-specific note when it succeeds.";
             }
           }
         }
       }
     }

     rpc lm-request {
       description
         "Submit an LM request for processing within the hierarchy.";

       input {
         uses auth-token-grouping;
         leaf source-node {
           type string;
           description
             "Identifier of the node submitting the request.";
         }
         leaf target-node {
           type string;
           description
             "Desired target node identifier; implementations may ignore
              and route based on policy and availability.";
         }
         leaf request-type {
           type enumeration {
             enum inference {
               description "Perform inference over provided payload.";
             }
             enum summarization {
               description "Summarize the provided payload.";
             }
           }
           description
             "The kind of operation requested.";
         }
         leaf payload {
           type string;
           description
             "The operation payload. Encoding is implementation-specific
              (e.g., JSON).";
         }
       }
       output {
         leaf result {
           type string;
           description
             "The result produced by the LM operation (implementation-
              specific encoding, e.g., JSON).";
         }
         leaf status {
           type enumeration {
             enum ok {
               description "The request completed successfully.";
             }
             enum error {
               description "The request failed; see result for details.";
             }
           }
           description
             "Status of the processed request.";
         }
       }
     }

     rpc model-escalation {
       description
         "Request an escalation to a different LM tier (e.g., from tiny to
          small/large) with rationale.";

       input {
         uses auth-token-grouping;
         leaf original-payload {
           type string;
           description
             "Original payload requiring escalation.";
         }
         leaf reason {
           type string;
           description
             "Reason for escalation (e.g., insufficient context, model
              limitations, or policy).";
         }
       }
       output {
         leaf resolution {
           type string;
           description
             "Resolution or answer produced after escalation.";
         }
         leaf downstream-directive {
           type string;
           description
             "Optional directive for downstream workers/coordinators.";
         }
       }
     }

     notification lm-heartbeat {
       description
         "Periodic heartbeat emitted by LM nodes to advertise presence and
          health.";

       leaf sender-node {
         type string;
         description
           "Identifier of the node emitting the heartbeat.";
       }
       leaf status {
         type enumeration {
           enum alive {
             description "Node is reachable and operating nominally.";
           }
           enum degraded {
             description "Node is reachable but operating with reduced capacity.";
           }
           enum unreachable {
             description "Node is currently unreachable.";
           }
         }
         description
           "Operational status reported by the node.";
       }
       leaf timestamp {
         type yang:date-and-time;
         description
           "Timestamp for the emitted heartbeat.";
       }
     }
   }
