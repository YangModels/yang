module ietf-poweff-level-4 {
  yang-version 1.1;
  namespace "urn:ietf:params:xml:ns:yang:ietf-poweff-level-4";
  prefix ietf-poweff-level-4;

  import ietf-poweff-types {
    prefix ietf-poweff-types;
  }
  import ietf-poweff-level-1 {
    prefix ietf-poweff-level-1;
  }

  organization
    "IETF GREEN (Getting Ready for Energy Efficient Networking)
     Working Group";
  contact
    "WG Web:   <https://datatracker.ietf.org/wg/green/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    "This YANG module defines the POWEFF Level 4.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.

    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";

  revision 2024-04-16 {
    description
      "Initial revision of POWEFF Level 4";
    reference
      "RFC XXXX: ...";
  }

  augment /ietf-poweff-level-1:poweff/ietf-poweff-level-1:stats {
    description 
      "Level 4 extends the Level 1, 2 & 3 defintions with 
      power draw data broken down on services.
      ";
    list service {
      key name;
      description 
        "List of services that the Network Element is aware of, and
        their current power draw. The power draw MAY be further
        subdivided for each service by using a dot notation.

        One service instance called '-idle-' may be present in the
        list and absorb any overhead/idle/other/unknown kind of power
        draw that the system would not allocate to any service.

        It is up to the implementor to decide what a 'service' means
        for this type of system. It may be any kind of service that it
        delivers user value towards. 

        For example, if a system serves three customers, X, Y and Z,
        their power draw could be declared as follows:

        | name          | current- | children                    |
        |               | power-   |                             |
        |               | draw     |                             |
        |---------------|----------|-----------------------------|
        | X             |       45 | [ vpn ]                     |
        | X.vpn         |       39 | [ eth1/16 eth2/33 eth3/11 ] |
        | X.vpn.eth1/16 |       14 |                             |
        | X.vpn.eth2/33 |       12 |                             |
        | X.vpn.eth3/11 |        9 |                             |
        | Y             |       26 |                             |
        | Z             |       19 |                             |
        | -idle-        |       48 |                             |

        The sum of the current-power-draw top level entries 
        (in this example: X, Y, Z and -idle-, with values
        45 + 26 + 19 + 48 = 138) must match the value provided in
        ietf-poweff-level-1:device-current-total-power-draw

        The sub-service values (e.g. X.vpn, 39W) need to be lower than
        or equal to (but do not necessarily need to match) their
        parent level (e.g. X, 45W).

        Note: the name of the children have been abbreviated in
        the diagram above. In the actual payload, the full names
        would always be used, e.g. 'eth1/16' above would actually be
        communicated as 'X.vpn.eth1/16'.
        ";
      leaf name {
        type string;
        description 
          "Name of the service/tenant/client/domain/function that the
          system allocates power draw for. Power draw MAY be further
          subdivided for each service by using a dot notation.
          ";
      }
      leaf current-power-draw {
        type uint32;
        units W;
        ietf-poweff-types:sensor-type 
          ietf-poweff-types:st-p-in-true-watt;
        ietf-poweff-types:tsdb-path 
          poweff.stats.service.current_power_draw;
        description 
          "The current power draw of the service provided in Watts.
          ";
      }
      leaf-list children {
        type leafref {
          path ../../service/name;
        }
        description 
          "Child-services that contribute to the service's power draw.
          All leafref values must exactly match the names used in
          the name leaf.
          ";
      }
    }
  }
}
