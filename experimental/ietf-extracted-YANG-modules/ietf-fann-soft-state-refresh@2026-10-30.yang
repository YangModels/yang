module ietf-fann-soft-state-refresh {
  yang-version 1.1;
  namespace
    "urn:ietf:params:xml:ns:yang:ietf-fann-soft-state-refresh";
  prefix fann-ssr;

  import ietf-yang-types {
    prefix yang;
    reference
      "RFC 9911: Common YANG Data Types";
  }

  organization
    "IETF Fast Network Notifications (FANN) Working Group";
  contact
    "WG Web:   <https://datatracker.ietf.org/wg/fann/>
     WG List:  <mailto:fann@ietf.org>
     Author:   Zhiqiang Li
               <mailto:lizhiqiangyjy@chinamobile.com>";
  description
    "This module defines configuration and operational state
     parameters for per-record receipt aging and bounded refresh
     scheduling in Fast Network Notification (FANN) Link-Quality
     Telemetry.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2026-10-30 {
    description
      "Initial version specifying per-record receipt aging
       parameters including multi-packet fragmentation emission
       margin (E).";
    reference
      "RFC XXXX: Per-Record Receipt Aging and Bounded Refresh
       Scheduling for Fast Network Notification (FANN)
       Link-Quality Telemetry";
  }

  container fann-soft-state-refresh {
    description
      "Per-record receipt aging configuration and operational
       telemetry.";
    leaf record-expire-ms {
      type uint32 {
        range "1..3600000";
      }
      units "milliseconds";
      default "1000";
      description
        "Receiver per-record expiration interval (T_expire).";
    }
    leaf safety-margin-ms {
      type uint32;
      units "milliseconds";
      default "200";
      description
        "Configured transit, jitter, and loss safety margin (M).";
    }
    leaf fragment-spacing-ms {
      type uint32;
      units "milliseconds";
      default "10";
      description
        "Maximum inter-fragment emission spacing (T_spacing).";
    }
    leaf max-fragments-per-sweep {
      type uint16 {
        range "1..1024";
      }
      default "1";
      description
        "Maximum fragments (F) required to emit a full link-record
         sweep.";
    }
    leaf refresh-interval-ms {
      type uint32 {
        range "1..3600000";
      }
      units "milliseconds";
      must ". + ../safety-margin-ms + "
         + "((../max-fragments-per-sweep - 1) * "
         + "../fragment-spacing-ms) <= ../record-expire-ms" {
        error-message
          "T_refresh + M + (F - 1) * T_spacing MUST NOT exceed "
        + "T_expire.";
      }
      default "500";
      description
        "Bounded full-sweep refresh interval (T_refresh).";
    }
    leaf expired-record-purges {
      type yang:counter64;
      config false;
      description
        "Total number of link-quality records transitioned to
         Expired because T_now - T_rx_last >= T_expire.";
    }
  }
}
