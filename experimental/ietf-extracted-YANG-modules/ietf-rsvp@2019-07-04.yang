module ietf-rsvp {
  yang-version 1.1;

  namespace "urn:ietf:params:xml:ns:yang:ietf-rsvp";

  /* Replace with IANA when assigned */
  prefix "rsvp";
  import ietf-interfaces {
    prefix if;
    reference "RFC8343: A YANG Data Model for Interface Management";
  }

  import ietf-inet-types {
    prefix inet;
    reference "RFC6991: Common YANG Data Types";
  }

  import ietf-yang-types {
    prefix "yang";
    reference "RFC6991: Common YANG Data Types";
  }

  import ietf-routing {
    prefix "rt";
    reference
      "RFC8349: A YANG Data Model for Routing Management
       (NMDA Version)";
  }

  import ietf-key-chain {
    prefix "key-chain";
    reference "RFC8177: YANG Data Model for Key Chains";
  }

  organization
    "IETF Traffic Engineering Architecture and Signaling (TEAS)
     Working Group";

  contact
    "WG Web:   <http://tools.ietf.org/wg/teas/>
     WG List:  <mailto:teas@ietf.org>

     Editor:   Vishnu Pavan Beeram
               <mailto:vbeeram@juniper.net>

     Editor:   Tarek Saad
               <mailto:tsaad@juniper.net>

     Editor:   Rakesh Gandhi
               <mailto:rgandhi@cisco.com>

     Editor:   Xufeng Liu
               <mailto: xufeng.liu.ietf@gmail.com>

     Editor:   Igor Bryskin
               <mailto:Igor.Bryskin@huawei.com>

     Editor:   Himanshu Shah
               <mailto:hshah@ciena.com>";

  description
    "This module contains the RSVP YANG data model.
     The model fully conforms to the Network Management Datastore
     Architecture (NMDA).

     Copyright (c) 2019 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  // RFC Ed.: replace XXXX with actual RFC number and remove this
  // note.

  // RFC Ed.: update the date below with the date of RFC publication
  // and remove this note.

  revision "2019-07-04" {
    description
      "A YANG Data Model for Resource Reservation Protocol";
    reference
      "RFCXXXX: A YANG Data Model for Resource Reservation Protocol
       (RSVP)";
  }

  identity rsvp {
    base "rt:routing-protocol";
    description "RSVP protocol";
  }

  identity rsvp-session-type {
    description "Base RSVP session type";
  }

  identity rsvp-session-ip {
    base rsvp-session-type;
    description "RSVP IP session type";
  }

  identity reservation-style {
    description "Base identity for reservation style";
  }

  identity reservation-wildcard-filter {
    base reservation-style;
    description "Wildcard-Filter (WF) Style";
    reference "RFC2205";
  }

  identity reservation-fixed-filter {
    base reservation-style;
    description "Fixed-Filter (FF) Style";
    reference "RFC2205";
  }

  identity reservation-shared-explicit {
    base reservation-style;
    description "Shared Explicit (SE) Style";
    reference "RFC2205";
  }

  grouping graceful-restart-config {
    description
      "Base configuration parameters relating to RSVP
       Graceful-Restart";
    leaf enabled {
      type boolean;
      description
        "'true' if RSVP Graceful Restart is enabled.
         'false' if RSVP Graceful Restart is disabled.";
    }
  }

  grouping graceful-restart {
    description
      "RSVP graceful restart parameters grouping";
    container graceful-restart {
      description
        "RSVP graceful restart parameters container";
      uses graceful-restart-config;
    }
  }

  grouping refresh-reduction-config {
    description
      "Configuration parameters relating to RSVP
       refresh reduction";

    leaf enabled {
      type boolean;
      description
        "'true' if RSVP Refresh Reduction is enabled.
         'false' if RSVP Refresh Reduction is disabled.";
    }
  }

  grouping refresh-reduction {
    description
      "Top level grouping for RSVP refresh reduction
       parameters";
    container refresh-reduction {
      description
        "Top level container for RSVP refresh reduction
         parameters";
      uses refresh-reduction-config;
    }
  }

  grouping authentication-config {
    description
      "Configuration parameters relating to RSVP
       authentication";
    leaf enabled {
      type boolean;
      description
        "'true' if RSVP Authentication is enabled.
         'false' if RSVP Authentication is disabled.";
    }
    leaf authentication-key {
      type string;
      description
        "An authentication key string";
      reference
        "RFC 2747: RSVP Cryptographic Authentication";
    }
    leaf crypto-algorithm {
     type identityref {
       base key-chain:crypto-algorithm;
     }
     mandatory true;
     description
       "Cryptographic algorithm associated with key.";
    }
  }

  grouping authentication {
    description
      "Top level grouping for RSVP authentication parameters";
    container authentication {
      description
        "Top level container for RSVP authentication
         parameters";
      uses authentication-config;
    }
  }

  grouping hellos-config {
    description
      "Configuration parameters relating to RSVP
      hellos";
    leaf enabled {
      type boolean;
      description
        "'true' if RSVP Hello is enabled.
         'false' if RSVP Hello is disabled.";
    }
  }

  grouping hellos {
    description
      "Top level grouping for RSVP hellos parameters";
    container hellos {
      description
        "Top level container for RSVP hello parameters";
      uses hellos-config;
    }
  }

  grouping signaling-parameters-config {
    description
      "Configuration parameters relating to RSVP
      signaling";
  }

  grouping signaling-parameters {
    description
      "Top level grouping for RSVP signaling  parameters";
    uses signaling-parameters-config;
  }

  grouping session-attributes-state {
    description
      "Top level grouping for RSVP session properties";
    leaf destination-port {
      type inet:port-number;
      description "RSVP destination port";
      reference "RFC2205";
    }
    leaf protocol-id {
      type uint8;
      description "The IP protocol ID.";
      reference "RFC2205, section 3.2";
    }
    leaf source {
      type inet:ip-address;
      description "RSVP source address";
      reference "RFC2205";
    }
    leaf destination {
      type inet:ip-address;
      description "RSVP destination address";
      reference "RFC2205";
    }
    leaf session-name {
      type string;
      description
        "The signaled name of this RSVP session.";
    }
    leaf session-state {
      type enumeration {
        enum "up" {
          description
            "RSVP session is up";
        }
        enum "down" {
          description
            "RSVP session is down";
        }
      }
      description
        "Enumeration of RSVP session states";
    }
    leaf session-type {
      type identityref {
        base rsvp-session-type;
      }
      description "RSVP session type";
    }
    container psbs {
      description "Path State Block container";
      list psb {
        description "List of path state blocks";
        leaf source-port {
          type inet:port-number;
          description "RSVP source port";
          reference "RFC2205";
        }
        leaf expires-in {
          type uint32;
          units seconds;
          description "Time to reservation expiry (in seconds)";
        }
      }
    }
    container rsbs {
      description "Reservation State Block container";
      list rsb {
        description "List of reservation state blocks";
        leaf source-port {
          type inet:port-number;
          description "RSVP source port";
          reference "RFC2205";
        }
        leaf reservation-style {
          type identityref {
            base reservation-style;
          }
          description "RSVP reservation style";
        }
        leaf expires-in {
          type uint32;
          units seconds;
          description "Time to reservation expiry (in seconds)";
        }
      }
    }
  }

  grouping neighbor-attributes {
    description
      "Top level grouping for RSVP neighbor properties";
    leaf address {
      type inet:ip-address;
      description
        "Address of RSVP neighbor";
    }

    leaf epoch {
      type uint32;
      description
        "Neighbor epoch.";
    }

    leaf expiry-time {
      type uint32;
      units seconds;
      description
        "Neighbor expiry time after which the neighbor state
        is purged if no states associated with it";
    }

    container graceful-restart {
      description
        "Graceful restart information.";

      leaf enabled {
        type boolean;
        description
          "'true' if graceful restart is enabled for the neighbor.";
      }

      leaf local-restart-time {
        type uint32;
        units seconds;
        description
          "Local node restart time";
      }

      leaf local-recovery-time {
        type uint32;
        units seconds;
        description
          "Local node recover time";
      }

      leaf neighbor-restart-time {
        type uint32;
        units seconds;
        description
          "Neighbor restart time";
      }

      leaf neighbor-recovery-time {
        type uint32;
        units seconds;
        description
          "Neighbor recover time";
      }

      container helper-mode {
        description
          "Helper mode information ";

        leaf enabled {
          type boolean;
          description
            "'true' if helper mode is enabled.";
        }

        leaf max-helper-restart-time {
          type uint32;
          units seconds;
          description
            "The time the router or switch waits after it
             discovers that a neighboring router has gone down
             before it declares the neighbor down";
        }

        leaf max-helper-recovery-time {
          type uint32;
          units seconds;
          description
            "The amount of time the router retains the state of its
             RSVP neighbors while they undergo a graceful restart";
        }

        leaf neighbor-restart-time-remaining {
          type uint32;
          units seconds;
          description
            "Number of seconds remaining for neighbor to send
             Hello message after restart.";
        }

        leaf neighbor-recovery-time-remaining {
          type uint32;
          units seconds;
          description
            "Number of seconds remaining for neighbor to
             refresh.";
        }
      } // helper-mode
    } // graceful-restart
    leaf hello-status {
      type enumeration {
        enum "enabled" {
          description
            "Enabled";
        }
        enum "disabled" {
          description
            "Disabled";
        }
        enum "restarting" {
          description
            "Restarting";
        }
      }
      description
        "Hello status";
    }

    leaf interface {
      type if:interface-ref;
      description
        "Interface where RSVP neighbor was detected";
    }

    leaf neighbor-state {
      type enumeration {
        enum "up" {
          description
            "up";
        }
        enum "down" {
          description
            "down";
        }
        enum "hello-disable" {
          description
            "hello-disable";
        }
        enum "restarting" {
          description
            "restarting";
        }
      }
      description
        "Neighbor state";
    }

    leaf refresh-reduction-capable {
      type boolean;
      description
        "enables all RSVP refresh reduction message
         bundling, RSVP message ID, reliable message delivery
         and summary refresh";
      reference
        "RFC 2961 RSVP Refresh Overhead Reduction
         Extensions";
    }

    leaf restart-count {
      type yang:counter32;
      description
        "Number of times this neighbor restart";
    }

    leaf restart-time {
      type yang:date-and-time;
      description
        "Last restart time of the neighbor";
    }
  }

  grouping packets-state {
    description
      "Packet statistics grouping";
    container packets {
      description
        "Packet statistics container";
      leaf sent {
        type yang:counter64;
        description
          "Packet sent count";
      }

      leaf received {
        type yang:counter64;
        description
          "Packet received count";
      }
    }
  }

  grouping protocol-state {
    description
      "RSVP protocol statistics grouping";
    container messages {
      description
        "RSVP protocol statistics container";
      leaf ack-sent {
        type yang:counter64;
        description
          "Hello sent count";
      }

      leaf ack-received {
        type yang:counter64;
        description
          "Hello received count";
      }

      leaf bundle-sent {
        type yang:counter64;
        description
          "Bundle sent count";
      }

      leaf bundle-received {
        type yang:counter64;
        description
          "Bundle received count";
      }

      leaf hello-sent {
        type yang:counter64;
        description
          "Hello sent count";
      }

      leaf hello-received {
        type yang:counter64;
        description
          "Hello received count";
      }

      leaf integrity-challenge-sent {
        type yang:counter64;
        description
          "Integrity Challenge sent count";
      }

      leaf integrity-challenge-received {
        type yang:counter64;
        description
          "Integrity Challenge received count";
      }

      leaf integrity-response-sent {
        type yang:counter64;
        description
          "Integrity Response sent count";
      }

      leaf integrity-response-received {
        type yang:counter64;
        description
          "Integrity Response received count";
      }

      leaf notify-sent {
        type yang:counter64;
        description
          "Notify sent count";
      }

      leaf notify-received {
        type yang:counter64;
        description
          "Notify received count";
      }

      leaf path-sent {
        type yang:counter64;
        description
          "Path sent count";
      }

      leaf path-received {
        type yang:counter64;
        description
          "Path received count";
      }

      leaf path-err-sent {
        type yang:counter64;
        description
          "Path error sent count";
      }

      leaf path-err-received {
        type yang:counter64;
        description
          "Path error received count";
      }

      leaf path-tear-sent {
        type yang:counter64;
        description
          "Path tear sent count";
      }

      leaf path-tear-received {
        type yang:counter64;
        description
          "Path tear received count";
      }

      leaf resv-sent {
        type yang:counter64;
        description
          "Resv sent count";
      }

      leaf resv-received {
        type yang:counter64;
        description
          "Resv received count";
      }

      leaf resv-confirm-sent {
        type yang:counter64;
        description
          "Confirm sent count";
      }

      leaf resv-confirm-received {
        type yang:counter64;
        description
          "Confirm received count";
      }

      leaf resv-err-sent {
        type yang:counter64;
        description
          "Resv error sent count";
      }

      leaf resv-err-received {
        type yang:counter64;
        description
          "Resv error received count";
      }

      leaf resv-tear-sent {
        type yang:counter64;
        description
          "Resv tear sent count";
      }

      leaf resv-tear-received {
        type yang:counter64;
        description
          "Resv tear received count";
      }

      leaf summary-refresh-sent {
        type yang:counter64;
        description
          "Summary refresh sent count";
      }

      leaf summary-refresh-received {
        type yang:counter64;
        description
          "Summary refresh received count";
      }

      leaf unknown-messages-received {
        type yang:counter64;
        description
          "Unknown packet received count";
      }
    }
  }

  grouping errors-state {
    description
      "Error statistics state grouping";
    container errors {
      description
        "Error statistics state container";
      leaf authenticate {
        type yang:counter64;
        description
          "The total number of packets received with an
          authentication failure.";
      }

      leaf checksum {
        type yang:counter64;
        description
          "The total number of packets received with an invalid
          checksum value.";
      }

      leaf packet-length {
        type yang:counter64;
        description
          "The total number of packets received with an invalid
          packet length.";
      }
    }
  }

  grouping statistics-state {
    description "RSVP statistic attributes.";
    container statistics {
      config false;
      description
        "statistics state container";
      uses protocol-state;
      uses packets-state;
      uses errors-state;
    }
  }

  grouping neighbor-derived-state {
    description
      "Derived state at neighbor level.";

  }

  grouping global-attributes {
    description
      "Top level grouping for RSVP global properties";
    container sessions {
      description
        "RSVP sessions container";
      list session-ip {
        key "destination protocol-id destination-port";
        config false;
        description
          "List of RSVP sessions";

        uses session-attributes-state;
      }
    }
    uses statistics-state;
  }

  grouping intf-attributes {
    description
      "Top level grouping for RSVP interface properties";
    uses signaling-parameters;
    uses refresh-reduction;
    uses hellos;
    uses authentication;
    uses statistics-state;
  }

  augment "/rt:routing/rt:control-plane-protocols/"
    + "rt:control-plane-protocol" {
    when "rt:type = 'rsvp:rsvp'" {
    description
     "This augment is only valid when routing protocol
      instance type is RSVP.";
    }
    description
      "RSVP protocol augmentation";
    container rsvp {
      presence "Enable RSVP feature";
      description "RSVP feature container";
      container globals {
        description "RSVP global properties.";
        uses global-attributes;
        uses graceful-restart;
      }

      container interfaces {
        description
          "RSVP interfaces container";
        uses intf-attributes;

        list interface {
          key "interface";
          description
            "RSVP interfaces.";
          leaf interface {
            type if:interface-ref;
            description
              "RSVP interface.";
          }
          uses intf-attributes;
        }
      }
      container neighbors {
        description "RSVP neighbors container";
        list neighbor {
          key "address";
          description "List of RSVP neighbors";
          uses neighbor-attributes;
        }
      }
    }
  }

  grouping session-ref {
    description "Session reference information";
    leaf destination {
      type leafref {
        path "/rt:routing/rt:control-plane-protocols" +
             "/rt:control-plane-protocol/rsvp:rsvp/rsvp:globals" +
             "/rsvp:sessions/rsvp:session-ip/destination";
      }
      mandatory true;
      description "RSVP session";
    }
    leaf protocol-id {
      type uint8;
      mandatory true;
      description "The RSVP session protocol ID";
    }
    leaf destination-port {
      type inet:ip-address;
      mandatory true;
      description "The RSVP session destination port";
    }
  }

  rpc clear-session {
    description "Clears RSVP sessions RPC";
    input {
      leaf routing-protocol-instance-name {
        type leafref {
          path "/rt:routing/rt:control-plane-protocols/"
             + "rt:control-plane-protocol/rt:name";
        }
        mandatory "true";
        description
          "Name of the RSVP protocol instance whose session
           is being cleared.

           If the corresponding RSVP instance doesn't exist,
           then the operation will fail with an error-tag of
           'data-missing' and an error-app-tag of
           'routing-protocol-instance-not-found'.";
      }
      choice filter-type {
        mandatory true;
        description "Filter choice";
        case match-all {
          leaf all {
            type empty;
            mandatory true;
            description "Match all RSVP sessions";
          }
        }
        case match-one {
          container session-info {
            description
              "Specifies the specific session to invoke operation on";
            choice session-type {
              mandatory true;
              description "RSVP session type";
              case rsvp-session-ip {
                uses session-ref;
              }
            }
          }
        }
      }
    }
  }

  rpc clear-neighbor {
    description
      "RPC to clear the RSVP Hello session to a neighbor";
    input {
      leaf routing-protocol-instance-name {
        type leafref {
          path "/rt:routing/rt:control-plane-protocols/"
             + "rt:control-plane-protocol/rt:name";
        }
        mandatory "true";
        description
          "Name of the RSVP protocol instance whose session
           is being cleared.

           If the corresponding RSVP instance doesn't exist,
           then the operation will fail with an error-tag of
           'data-missing' and an error-app-tag of
           'routing-protocol-instance-not-found'.";
      }
      choice filter-type {
        mandatory true;
        description "Filter choice";
        case match-all {
          leaf all {
            type empty;
            mandatory true;
            description "Match all RSVP neighbor sessions";
          }
        }
        case match-one {
          leaf neighbor-address {
            type leafref {
              path "/rt:routing/rt:control-plane-protocols" +
                   "/rt:control-plane-protocol/rsvp:rsvp" +
                   "/rsvp:neighbors/rsvp:neighbor/address";
            }
            mandatory true;
            description "Match specific RSVP neighbor session";
          }
        }
      }
    }
  }
}
