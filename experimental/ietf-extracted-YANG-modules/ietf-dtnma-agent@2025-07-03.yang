module ietf-dtnma-agent {
  yang-version 1.1;
  namespace "ari://ietf/dtnma-agent/";
  prefix da;

  import ietf-amm {
    prefix amm;
  }
  import ietf-amm-semtype {
    prefix amm-semtype;
  }
  import ietf-amm-base {
    prefix amm-base;
  }
  import ietf-network-base {
    prefix network-base;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module implements the DTN Management Architecture (DTNMA)
     Agent core functionality.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2025-07-03 {
    description
      "Updated for latest ADM document.";
    reference
      "draft-ietf-dtn-adm-yang";
  }

  feature rules {
    description
      "Conforming to this feature enables time-based and
       state-based autonomy rules.";
  }

  grouping obj-list-params {
    description
      "Common parameters for object listing";
    amm:parameter include-adm {
      description
        "If true, listings will include objects from ADMs";
      amm:default "false";
      amm:type "/aritype/BOOL";
    }
  }

  grouping ensure-object-id {
    description
      "Common parameters for providing object reference to
       ensure an object exists in an ODM.

       When this grouping is used, the logic operates according
       to the following in order to succeed.
       The parent 'namespace' SHALL refer to an existing ODM.
       Both the text 'obj-name' and integer 'obj-enum' SHALL
       either both not exist, in which case the object will be
       created, or both are allocated to the same object, in
       which case the object will be modified as needed.";
    amm:parameter namespace {
      description
        "The parent ODM namespace.";
      amm:type "/aritype/namespace";
    }
    amm:parameter obj-name {
      description
        "Text name for the desired object.";
      amm:type "//ietf/amm-base/typedef/id-text";
    }
    amm:parameter obj-enum {
      description
        "Integer enumeration for the desired object.";
      amm:type "//ietf/amm-base/typedef/id-int";
    }
  }

  grouping any-binary-operands {
    description
      "Any-value bianry operands";
    amm:operand left {
      description
        "The left-side operand.";
      amm:type "//ietf/amm-base/typedef/any";
    }
    amm:operand right {
      description
        "The left-side operand.";
      amm:type "//ietf/amm-base/typedef/any";
    }
  }

  grouping any-unary-result {
    description
      "Any-value result";
    amm:result result {
      description
        "The single value.";
      amm:type "//ietf/amm-base/typedef/any";
    }
  }

  grouping numeric-unary-operands {
    description
      "Numeric unary operand";
    amm:operand val {
      description
        "The single value.";
      amm:type "//ietf/amm-base/typedef/NUMERIC";
    }
  }

  grouping numeric-binary-operands {
    description
      "Numeric bianry operands";
    amm:operand left {
      description
        "The left-side operand.";
      amm:type "//ietf/amm-base/typedef/NUMERIC";
    }
    amm:operand right {
      description
        "The left-side operand.";
      amm:type "//ietf/amm-base/typedef/NUMERIC";
    }
  }

  grouping numeric-unary-result {
    description
      "Numeric result";
    amm:result result {
      description
        "The single value.";
      amm:type "//ietf/amm-base/typedef/NUMERIC";
    }
  }

  grouping integer-unary-operands {
    description
      "Integer unary operand";
    amm:operand val {
      description
        "The single value.";
      amm:type "//ietf/amm-base/typedef/INTEGER";
    }
  }

  grouping integer-binary-operands {
    description
      "Integer bianry operands";
    amm:operand left {
      description
        "The left-side operand.";
      amm:type "//ietf/amm-base/typedef/INTEGER";
    }
    amm:operand right {
      description
        "The left-side operand.";
      amm:type "//ietf/amm-base/typedef/INTEGER";
    }
  }

  grouping integer-unary-result {
    description
      "Integer result";
    amm:result result {
      description
        "The single value.";
      amm:type "//ietf/amm-base/typedef/INTEGER";
    }
  }

  grouping bool-unary-operands {
    description
      "Boolean unary operand";
    amm:operand val {
      description
        "The single value.";
      amm:type "/aritype/BOOL";
    }
  }

  grouping bool-binary-operands {
    description
      "Boolean bianry operands";
    amm:operand left {
      description
        "The left-side operand.";
      amm:type "/aritype/BOOL";
    }
    amm:operand right {
      description
        "The left-side operand.";
      amm:type "/aritype/BOOL";
    }
  }

  grouping bool-unary-result {
    description
      "Boolean result";
    amm:result result {
      description
        "The single value.";
      amm:type "/aritype/BOOL";
    }
  }

  amm:enum 1;
  amm:edd sw-vendor {
    amm:enum 0;
    description
      "The vendor for this Agent implementation.";
    amm:type "/aritype/TEXTSTR";
  }
  amm:edd sw-version {
    amm:enum 1;
    description
      "The version for this Agent implementation.";
    amm:type "/aritype/TEXTSTR";
  }
  amm:edd capability {
    amm:enum 2;
    description
      "A table to indicate the ADM capability of the sending agent.";
    amm:tblt {
      amm:key "org-name adm-name";
      amm:column org-name {
        description
          "The organization name containing the ADM";
        amm:type "/aritype/TEXTSTR";
      }
      amm:column org-enum {
        description
          "The organization enumeration containing the ADM";
        amm:type "/aritype/VAST";
      }
      amm:column model-name {
        description
          "The model name of the ADM";
        amm:type "/aritype/TEXTSTR";
      }
      amm:column model-enum {
        description
          "The model enumeration of the ADM";
        amm:type "/aritype/VAST";
      }
      amm:column revision {
        description
          "The specific revision the agent supports.";
        amm:type "/aritype/TEXTSTR";
      }
      amm:column features {
        description
          "The features of the ADM which the agent supports.";
        amm:ulist {
          amm:type "/aritype/TEXTSTR";
        }
      }
    }
  }
  amm:const hello {
    amm:enum 0;
    description
      "A report template to indicate the presence of an agent
       on a network.";
    amm:init-value "/AC/(./EDD/sw-vendor,./EDD/sw-version,"
                 + "./EDD/capability)";
    amm:type "//ietf/amm-base/typedef/RPTT";
  }

  // Messaging counters
  amm:edd num-msg-rx {
    amm:enum 3;
    amm:type "//ietf/amm-base/typedef/counter64";
  }
  amm:edd num-msg-rx-failed {
    amm:enum 4;
    amm:type "//ietf/amm-base/typedef/counter64";
  }
  amm:edd num-msg-tx {
    amm:enum 5;
    amm:type "//ietf/amm-base/typedef/counter64";
  }
  amm:edd num-msg-tx-failed {
    amm:enum 15;
    amm:type "//ietf/amm-base/typedef/counter64";
  }
  amm:edd last-msg-rx-time {
    amm:enum 17;
    amm:type "/aritype/TP";
  }

  // Execution counters and states
  amm:edd num-exec-started {
    amm:enum 6;
    amm:type "//ietf/amm-base/typedef/counter64";
  }
  amm:edd num-exec-succeeded {
    amm:enum 7;
    amm:type "//ietf/amm-base/typedef/counter64";
  }
  amm:edd num-exec-failed {
    amm:enum 8;
    amm:type "//ietf/amm-base/typedef/counter64";
  }
  amm:edd exec-running {
    amm:enum 9;
    amm:tblt {
      amm:key "pid";
      amm:column pid {
        amm:type "/aritype/UVAST";
      }
      amm:column target {
        amm:type "//ietf/amm-base/typedef/any";
      }
      amm:column state {
        amm:type "/aritype/BYTE" {
          amm:int-labels {
            enum waiting {
              value 0;
              description
                "The execution is waiting on a condition or timer
                 to continue.";
            }
            enum running {
              value 1;
              description
                "The execution is currently running.";
            }
          }
        }
      }
    }
  }

  // MAC helper controls
  amm:ctrl if-then-else {
    amm:enum 0;
    description
      "Evaluate an expression and follow one of two branches of
       further evaluation.";
    amm:parameter condition {
      description
        "The condition to evaluate.";
      amm:type "//ietf/amm-base/typedef/eval-tgt";
    }
    amm:parameter on-truthy {
      description
        "The object to execute when the condition is truthy.";
      amm:default "null";
      amm:union {
        amm:type "//ietf/amm-base/typedef/exec-tgt";
        amm:type "/aritype/NULL";
      }
    }
    amm:parameter on-falsy {
      description
        "An optional execution when the condition is falsey.";
      amm:default "null";
      amm:union {
        amm:type "//ietf/amm-base/typedef/exec-tgt";
        amm:type "/aritype/NULL";
      }
    }
    amm:result branch {
      description
        "Indication of which branch was executed.";
      amm:type "/aritype/BOOL";
    }
  }
  amm:ctrl catch {
    amm:enum 1;
    description
      "Attempt to execute a target, and if there is some failure
       catch it and execute an alternative target.";
    amm:parameter try {
      description
        "The object to execute.";
      amm:type "//ietf/amm-base/typedef/exec-tgt";
    }
    amm:parameter on-failure {
      description
        "An optional execution after failure.";
      amm:default "null";
      amm:union {
        amm:type "//ietf/amm-base/typedef/exec-tgt";
        amm:type "/aritype/NULL";
      }
    }
    amm:result try-success {
      description
        "True if the try target succeeded without exception.";
      amm:type "/aritype/BOOL";
    }
  }
  amm:ctrl wait-for {
    amm:enum 2;
    description
      "This control causes the execution to pause for a given
       amount of time.
       This is intended to be used within a macro to separate
       controls in time.";
    amm:parameter duration {
      amm:type "/aritype/TD";
    }
  }
  amm:ctrl wait-until {
    amm:enum 3;
    description
      "This control causes the execution to pause until a specific
       absolute time point.
       This is intended to be used within a macro to separate
       controls in time or as a first macro item to delay execution
       after the time of reception.";
    amm:parameter time {
      amm:type "/aritype/TP";
    }
  }
  amm:ctrl wait-cond {
    amm:enum 4;
    description
      "This control causes the execution to pause until a condition
       expression evaluates to truthy.
       This is intended to be used within a macro to separate
       controls in time or as a first macro item to delay execution
       until the condition is met.";
    amm:parameter condition {
      amm:type "//ietf/amm-base/typedef/eval-tgt";
    }
  }

  // Value production and reporting
  amm:ctrl inspect {
    amm:enum 5;
    description
      "Produce a result value to inspect the agent state.
       This does not perform any EXPR evaluation or RPTT handling.";
    amm:parameter ref {
      description
        "An object to produce a value from.";
      amm:type "//ietf/amm-base/typedef/VALUE-OBJ";
    }
    amm:result val {
      description
        "The produced value.";
      amm:type "//ietf/amm-base/typedef/any";
    }
  }
  amm:ctrl report-on {
    amm:enum 6;
    description
      "Agent-wide control to generate a report from a report
       template (RPTT) value.
       The parameter is a single RPTT list that would be produced
       by an object.
       If used for more than one-shot diagnostics, defining a RPTT
       (e.g. in a CONST within an ODM) is more efficient because
       the RPTT value would not need be present in the EXECSET or
       corresponding RPTSET.";
    amm:parameter template {
      description
        "The reporting template, either as a RPTT value directly or
         as a reference to a value-producing object (possibly
         parameterized) which itself produces an RPTT value.";
      amm:type "//ietf/amm-base/typedef/rpt-tgt";
    }
    amm:parameter destinations {
      description
        "Destinations for the resulting report.
         If given an empty list (the default) reports will be sent
         to the manager executing this CTRL.
         When executed as a rule action, the destinations list is
         mandatory.

         It is possible that each destination has different access
         limitations so each destination might see different report
         contents.";
      amm:default "/ac/()";
      amm:ulist {
        amm:type "//ietf/network-base/typedef/endpoint-or-uri";
      }
    }
  }

  // Objects related to ODM handling
  amm:edd odm-list {
    amm:enum 16;
    description
      "A table of ODM within the agent.";
    amm:tblt {
      amm:key "org-name odm-name";
      amm:column org-name {
        description
          "The organization name containing the ODM";
        amm:type "//ietf/amm-base/typedef/id-text";
      }
      amm:column org-enum {
        description
          "The organization enumeration containing the ODM";
        amm:type "//ietf/amm-base/typedef/id-int";
      }
      amm:column model-name {
        description
          "The model name of the ODM";
        amm:type "//ietf/amm-base/typedef/id-text";
      }
      amm:column model-enum {
        description
          "The model enumeration of the ODM";
        amm:type "//ietf/amm-base/typedef/id-int";
      }
      amm:column revision {
        description
          "The specific revision the agent supports.";
        amm:type "/aritype/TEXTSTR";
      }
    }
  }
  amm:ctrl ensure-odm {
    amm:enum 18;
    description
      "Ensure a specific ODM is present.
       The referenced organization and model identifiers SHALL either
       not already exist or exist with the exact combination given by
       these parameters";
    amm:parameter org-name {
      description
        "The organization name containing the ODM";
      amm:type "//ietf/amm-base/typedef/id-text";
    }
    amm:parameter org-id {
      description
        "The organization enumeration ID containing the ODM";
      amm:type "//ietf/amm-base/typedef/id-int";
    }
    amm:parameter model-name {
      description
        "The model name containing the ODM.";
      amm:type "//ietf/amm-base/typedef/id-text" {
        pattern '!.+';
      }
    }
    amm:parameter model-id {
      description
        "The model enumeration ID containing the ODM";
      amm:type "//ietf/amm-base/typedef/id-int" {
        range "min..-1";
      }
    }
  }
  amm:ctrl obsolete-odm {
    amm:enum 19;
    description
      "Mark a specific ODM as obsolete if it is present.";
    amm:parameter odm-ns {
      description
        "Namespace of the ODM";
      amm:type "/aritype/namespace";
    }
  }

  // Helpers for VAR
  amm:ctrl var-reset {
    amm:enum 7;
    description
      "Modify a VAR state to its default value.";
    amm:parameter target {
      description
        "The VAR object to affect.";
      amm:type "/aritype/VAR";
    }
  }
  amm:ctrl var-store {
    amm:enum 8;
    description
      "Modify a VAR state to a specific value.";
    amm:parameter target {
      description
        "The VAR object to affect.";
      amm:type "/aritype/VAR";
    }
    amm:parameter value {
      description
        "The exact value to store in the VAR.";
      amm:type "//ietf/amm-base/typedef/any";
    }
  }

  // Objects related to TYPEDEF handling
  amm:edd typedef-list {
    amm:enum 10;
    description
      "A table of TYPEDEF within the agent.";
    uses obj-list-params;
    amm:tblt {
      amm:key "obj";
      amm:column obj {
        amm:type "/aritype/typedef";
      }
    }
  }

  // Objects related to CONST handling
  amm:edd const-list {
    amm:enum 14;
    description
      "A table of CONST within the agent.";
    uses obj-list-params;
    amm:tblt {
      amm:key "obj";
      amm:column obj {
        amm:type "/aritype/CONST";
      }
      amm:column type {
        amm:type "//ietf/amm-semtype/typedef/semtype";
      }
    }
  }
  amm:ctrl ensure-const {
    amm:enum 11;
    description
      "Ensure a specific CONST is present in an ODM.
       If an object already exists with the same identifiers, type,
       and value this control will do nothing and succeed.
       If an object already exists in the same namespace with either
       of the object identifiers this control will fail.";
    uses ensure-object-id;
    amm:parameter type {
      description
        "The type for the CONST object.";
      amm:type "//ietf/amm-semtype/typedef/semtype";
    }
    amm:parameter value {
      description
        "A required constant value.
         This value SHALL match the type given for this object.";
      amm:type "//ietf/amm-base/typedef/any";
    }
  }
  amm:ctrl obsolete-const {
    amm:enum 12;
    description
      "Mark a specific CONST as obsolete if it is present in an
       ODM.";
    amm:parameter obj {
      description
        "A reference to a CONST within an ODM only.";
      amm:type "/aritype/CONST";
    }
  }

  // Objects related to VAR handling
  amm:edd var-list {
    amm:enum 11;
    description
      "A table of VAR within the agent.";
    uses obj-list-params;
    amm:tblt {
      amm:key "obj";
      amm:column obj {
        amm:type "/aritype/VAR";
      }
      amm:column type {
        amm:type "//ietf/amm-semtype/typedef/semtype";
      }
    }
  }
  amm:ctrl ensure-var {
    amm:enum 9;
    description
      "Ensure a specific VAR is present in an ODM.
       If an object already exists with the same identifiers, type,
       and init-value this control will do nothing and succeed.
       If an object already exists in the same namespace with either
       of the object identifiers (but not both), or the type or
       is different, this control will fail.
       That means that this control can change only the initial value
       of a pre-existing VAR object.";
    uses ensure-object-id;
    amm:parameter type {
      description
        "The type for the VAR object.";
      amm:type "//ietf/amm-semtype/typedef/semtype";
    }
    amm:parameter init-value {
      description
        "The exact value to use as the initial value of
         the new object and to store as the initial state
         of the object if created.
         This value SHALL match the type given for this object.";
      amm:type "//ietf/amm-base/typedef/any";
    }
  }
  amm:ctrl obsolete-var {
    amm:enum 10;
    description
      "Mark a specific VAR as obsolete if it is present in an ODM.";
    amm:parameter obj {
      description
        "A reference to a VAR within an ODM only.";
      amm:type "/aritype/VAR";
    }
  }

  // Objects related to SBR handling
  amm:edd sbr-list {
    if-feature "rules";
    amm:enum 12;
    description
      "A table of SBR within the agent.";
    uses obj-list-params;
    amm:tblt {
      amm:key "obj";
      amm:column obj {
        amm:type "/aritype/SBR";
      }
      amm:column action {
        description
          "The execution when this rule triggers.";
        amm:type "//ietf/amm-base/typedef/MAC";
      }
      amm:column condition {
        amm:type "//ietf/amm-base/typedef/EXPR";
      }
      amm:column min-interval {
        amm:type "/aritype/TD";
      }
      amm:column max-count {
        amm:type "/aritype/UVAST";
      }
      amm:column init-enabled {
        amm:type "/ARITYPE/BOOL";
      }
      amm:column enabled {
        amm:type "/ARITYPE/BOOL";
      }
    }
  }
  amm:edd tbr-list {
    if-feature "rules";
    amm:enum 13;
    description
      "A table of TBR within the agent.";
    uses obj-list-params;
    amm:tblt {
      amm:key "obj";
      amm:column obj {
        amm:type "/aritype/TBR";
      }
      amm:column action {
        description
          "The execution when this rule triggers.";
        amm:type "//ietf/amm-base/typedef/MAC";
      }
      amm:column start-time {
        amm:type "//ietf/amm-base/typedef/TIME";
      }
      amm:column period {
        amm:type "/aritype/TD";
      }
      amm:column max-count {
        amm:type "/aritype/UVAST";
      }
      amm:column init-enabled {
        amm:type "/ARITYPE/BOOL";
      }
      amm:column enabled {
        amm:type "/ARITYPE/BOOL";
      }
    }
  }

  // CTRLs related to rules
  amm:ctrl ensure-sbr {
    if-feature "rules";
    amm:enum 13;
    description
      "Ensure that a state-based rule with the given identifiers
       exists within an ODM.";
    uses ensure-object-id;
    amm:parameter action {
      description
        "The execution when this rule triggers.";
      amm:type "//ietf/amm-base/typedef/MAC";
    }
    amm:parameter condition {
      amm:type "//ietf/amm-base/typedef/EXPR";
    }
    amm:parameter min-interval {
      amm:type "/ARITYPE/TD";
    }
    amm:parameter max-count {
      amm:type "/ARITYPE/UVAST";
    }
    amm:parameter init-enabled {
      amm:type "/ARITYPE/BOOL";
    }
    amm:result res {
      amm:type "/ARITYPE/UINT";
    }
  }
  amm:ctrl ensure-tbr {
    if-feature "rules";
    amm:enum 14;
    description
      "Ensure that a time-based rule with the given identifiers
       exists within an ODM.";
    uses ensure-object-id;
    amm:parameter action {
      description
        "The execution when this rule triggers.";
      amm:type "//ietf/amm-base/typedef/MAC";
    }
    amm:parameter start-time {
      amm:type "//ietf/amm-base/typedef/TIME";
    }
    amm:parameter period {
      amm:type "/ARITYPE/TD";
    }
    amm:parameter max-count {
      amm:type "/ARITYPE/UVAST";
    }
    amm:parameter init-enabled {
      amm:type "/ARITYPE/BOOL";
    }
    amm:result res {
      amm:type "/ARITYPE/UINT";
    }
  }
  amm:ctrl ensure-rule-enabled {
    if-feature "rules";
    amm:enum 15;
    description
      "Ensure rule is enabled or disabled.";
    amm:parameter obj-id {
      description
        "The rule to ensure enabled setting for.";
      amm:union {
        amm:type "/ARITYPE/SBR";
        amm:type "/ARITYPE/TBR";
      }
    }
    amm:parameter enabled {
      amm:type "/ARITYPE/BOOL";
    }
    amm:result res {
      amm:type "/ARITYPE/uint";
    }
  }
  amm:ctrl reset-rule-enabled {
    if-feature "rules";
    amm:enum 16;
    description
      "Reset rule enabled to initial setting.";
    amm:parameter obj-id {
      description
        "The rule to reset enabled seetting for.";
      amm:union {
        amm:type "/ARITYPE/SBR";
        amm:type "/ARITYPE/TBR";
      }
    }
    amm:result res {
      amm:type "/ARITYPE/UINT";
    }
  }
  amm:ctrl obsolete-rule {
    if-feature "rules";
    amm:enum 17;
    description
      "Mark a specific SBR or TBR as obsolete if it is present in
       an ODM.";
    amm:parameter obj-id {
      description
        "A reference to a rule within an ODM only.";
      amm:union {
        amm:type "/ARITYPE/SBR";
        amm:type "/ARITYPE/TBR";
      }
    }
    amm:result success {
      amm:type "/ARITYPE/BOOL";
    }
  }

  // Numeric operators
  amm:oper negate {
    amm:enum 0;
    description
      "Negate a value.
       This is equivalent to multiplying by -1 but a shorter
       expression.";
    uses numeric-unary-operands;
    uses numeric-unary-result;
  }
  amm:oper add {
    amm:enum 1;
    description
      "Add two numeric values.
       The operands are cast to the least compatible numeric type
       before the arithmetic.";
    uses any-binary-operands;
    uses any-unary-result;
  }
  amm:oper sub {
    amm:enum 2;
    uses any-binary-operands;
    uses any-unary-result;
  }
  amm:oper multiply {
    amm:enum 3;
    uses any-binary-operands;
    uses any-unary-result;
  }
  amm:oper divide {
    amm:enum 4;
    uses any-binary-operands;
    uses any-unary-result;
  }
  amm:oper remainder {
    amm:enum 5;
    uses numeric-binary-operands;
    uses numeric-unary-result;
  }

  // Bitwise operators
  amm:oper bit-not {
    amm:enum 6;
    uses integer-unary-operands;
    uses integer-unary-result;
  }
  amm:oper bit-and {
    amm:enum 7;
    uses integer-binary-operands;
    uses integer-unary-result;
  }
  amm:oper bit-or {
    amm:enum 8;
    uses integer-binary-operands;
    uses integer-unary-result;
  }
  amm:oper bit-xor {
    amm:enum 9;
    uses integer-binary-operands;
    uses integer-unary-result;
  }

  // Boolean operators
  amm:oper bool-not {
    amm:enum 10;
    uses bool-unary-operands;
    uses bool-unary-result;
  }
  amm:oper bool-and {
    amm:enum 11;
    uses bool-binary-operands;
    uses bool-unary-result;
  }
  amm:oper bool-or {
    amm:enum 12;
    uses bool-binary-operands;
    uses bool-unary-result;
  }
  amm:oper bool-xor {
    amm:enum 13;
    uses bool-binary-operands;
    uses bool-unary-result;
  }

  // Value comparison
  amm:oper compare-eq {
    amm:enum 14;
    uses any-binary-operands;
    uses bool-unary-result;
  }
  amm:oper compare-ne {
    amm:enum 15;
    uses any-binary-operands;
    uses bool-unary-result;
  }

  // Numeric comparison
  amm:oper compare-gt {
    amm:enum 16;
    description
      "Compare two numbers by value.
       The result is true if the left value is greater than the
       right value.
       The operands are cast to the least compatible numeric type
       before the comparison.";
    uses numeric-binary-operands;
    uses bool-unary-result;
  }
  amm:oper compare-ge {
    amm:enum 17;
    description
      "Compare two numbers by value.
       The result is true if the left value is greater than or equal
       to the right.
       The operands are cast to the least compatible numeric type
       before the comparison.";
    uses numeric-binary-operands;
    uses bool-unary-result;
  }
  amm:oper compare-lt {
    amm:enum 18;
    description
      "Compare two operands by value.
       The result is true if the left value is less than the right.
       The operands are cast to the least compatible numeric type
       before the comparison.";
    uses numeric-binary-operands;
    uses bool-unary-result;
  }
  amm:oper compare-le {
    amm:enum 19;
    description
      "Compare two operands by value.
       The result is true if the left value is less than or
       equal to the right.
       The operands are cast to the least compatible numeric type
       before the comparison.";
    uses numeric-binary-operands;
    uses bool-unary-result;
  }

  // Table filtering
  amm:oper tbl-filter {
    amm:enum 20;
    description
      "Filter a table first by rows and then by columns.";
    amm:parameter row-match {
      description
        "A filter applied using two phases for each row:
           1. Substitute row values for LABEL items within EXPR
           2. Evaluate the expression and consider the row matched
              if the result is a truthy value
         Each LABEL item refers to the value at a column index
         within the context of the input row. Label substitution
         is performed as described in the value production section
         of the DTNMA AMM document.";
      amm:type "//ietf/amm-base/typedef/EXPR";
    }
    amm:parameter columns {
      description
        "A filter to restrict output to only the listed columns.
         The order of columns in the filtered table shall
         correspond with the order of columns in this list.";
      amm:ulist {
        amm:type "/aritype/UVAST";
      }
    }
    amm:operand in {
      description
        "Table to filter.";
      amm:type "/aritype/TBL";
    }
    amm:result out {
      description
        "The filtered table.";
      amm:type "/aritype/TBL";
    }
  }

  // List filtering
  amm:oper list-get {
    amm:enum 21;
    description
      "Retrieve an item from the given list.";
    amm:parameter index {
      description
        "Index of the value to retrieve from the list.";
      amm:type "//ietf/amm-base/typedef/INTEGER";
    }
    amm:operand in {
      description
        "List to retrieve a value from.";
      amm:type "/aritype/AC";
    }
    amm:result out {
      description
        "The retrieved value or undefined if the index is not valid.";
      amm:type "//ietf/amm-base/typedef/any";
    }
  }

  // Map filtering
  amm:oper map-get {
    amm:enum 22;
    description
      "Retrieve an item from the given map.";
    amm:parameter key {
      description
        "Key of the value to retrieve from the map.";
      amm:type "//ietf/amm-base/typedef/primitive";
    }
    amm:operand in {
      description
        "Map to retrieve a value from.";
      amm:type "/aritype/AM";
    }
    amm:result out {
      description
        "The retrieved value or undefined if the key is not valid.";
      amm:type "//ietf/amm-base/typedef/any";
    }
  }
}
