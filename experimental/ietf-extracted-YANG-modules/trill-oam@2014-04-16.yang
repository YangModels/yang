module trill-oam {
  namespace "urn:cisco:params:xml:ns:yang:tril-oam";
  prefix trilloam;

  import gen-oam {
    prefix goam;
  }
  import ietf-inet-types {
    prefix inet;
  }
  import ietf-interfaces {
    prefix if;
  }

  revision 2014-04-16 {
    description
      "Initial revision.";
  }

 identity trill {
    base goam:technology-types;
    description
      "trill type";
  }

  typedef tril-rb-nickname {
    type uint16;
  }

  typedef flow-entropy-trill {
    type binary {
      length "1..96";
    }
  }

  typedef vlan {
    type uint16 {
      range "0..4095";
    }
  }

  typedef fgl {
    type uint32;
  }

  identity trill-mtv {
    base goam:command-sub-type;
    description
      "identfies this command as multicast tree verification comand";
  }

  identity trill-ping {
    base goam:command-sub-type;
  }

  identity trill-trace-route {
    base goam:command-sub-type;
  }

  grouping command-ext-trill {
    description
      "group the rpc command extensions for trill";
    choice out-of-band {
      case ipv4-address {
        leaf ipv4-address {
          type inet:ipv4-address;
        }
      }
      case ipv6-address {
        leaf ipv6-address {
          type inet:ipv6-address;
        }
      }
      case trill-nickname {
        leaf trill-nickname {
          type tril-rb-nickname;
        }
      }
      description
        "presence of this node indicate out of band request needed";
    }
    leaf diagnostic-vlan {
      type boolean;
      description
        "indicates whether to include diagnostic VLAN/fgl TLV or not
         in the request.  actual value is the VLAN/FGL specified
         in the command";
    }
  }
  augment
"/goam:domains/goam:domain/goam:MAs/goam:MA/goam:MEP/goam:mep-
address" {
    case mep-address-trill {
      leaf mep-address-trill {
        when "/goam:domains/goam:domain/goam:technology='trill'";
        type tril-rb-nickname;
      }
    }
  }
  augment "/goam:domains/goam:domain/goam:MAs/goam:MA/goam:context-
id" {
    case context-id-vlan {
      leaf context-id-vlan {
        type vlan;
      }
    }
    case context-id-fgl {
      leaf context-id-fgl {
        type fgl;
      }
    }
  }
  augment "/goam:domains/goam:domain/goam:MAs/goam:MA/goam:flow-
entropy" {
    case flow-entropy-trill {
      leaf flow-entropy-trill {
        type flow-entropy-trill;
      }
    }
  }
  augment
"/goam:domains/goam:domain/goam:MAs/goam:MA/goam:MEP/goam:context-id"
{
    case context-id-vlan {
      leaf context-id-vlan {
        type vlan;
      }
    }
    case context-id-fgl {
      leaf context-id-fgl {
        type fgl;
      }
    }
  }

  augment
"/goam:domains/goam:domain/goam:MAs/goam:MA/goam:MEP/goam:flow-
entropy" {
    case flow-entropy-trill {
      leaf flow-entropy-trill {
        type flow-entropy-trill;
      }
    }
  }
  augment
"/goam:domains/goam:domain/goam:MAs/goam:MA/goam:MEP/goam:session/goa
m:context-id" {
    case context-id-vlan {
      leaf context-id-vlan {
        type vlan;
      }
    }
    case context-id-fgl {
      leaf context-id-fgl {
        type fgl;
      }
    }
  }
  augment
"/goam:domains/goam:domain/goam:MAs/goam:MA/goam:MEP/goam:session/goa
m:flow-entropy" {
    case flow-entropy-trill {
      leaf flow-entropy-trill {
        type flow-entropy-trill;
      }
    }
  }
  augment "/goam:ping/goam:input" {
    uses command-ext-trill;
  }
  augment "/goam:ping/goam:input/goam:context-id" {
    case context-id-vlan {
      leaf context-id-vlan {
        type vlan;
      }
    }
    case context-id-fgl {
      leaf context-id-fgl {
        type fgl;
      }
    }
  }
  augment "/goam:ping/goam:input/goam:flow-entropy" {
    case flow-entropy-trill {
      leaf flow-entropy-trill {
        type flow-entropy-trill;
      }
    }
  }
  augment "/goam:ping/goam:input/goam:source-mep/goam:mep-address" {
    case trill-nickname {
      leaf trill-nickname {
        type tril-rb-nickname;
      }
    }
  }
  augment "/goam:ping/goam:input/goam:destination-mep/goam:mep-
address" {
    case trill-nickname {
      leaf trill-nickname {
        type tril-rb-nickname;
      }
    }
  }
  augment "/goam:ping/goam:output" {
    description
      "adds trill specific items on the response";
    leaf upstream-rbridge {
      type tril-rb-nickname;
    }
    leaf-list next-hop-rbridge {
      type tril-rb-nickname;
      description
        "nickname of the next hop RBRdige";
    }
  }
  augment "/goam:trace-route/goam:input" {
    uses command-ext-trill;
  }
  augment "/goam:trace-route/goam:input/goam:context-id" {
    case context-id-vlan {
      leaf context-id-vlan {
        type vlan;
      }
    }
    case context-id-fgl {
      leaf context-id-fgl {
        type fgl;
      }
    }
  }
  augment "/goam:trace-route/goam:input/goam:flow-entropy" {
    case flow-entropy-trill {
      leaf flow-entropy-trill {
        type flow-entropy-trill;
      }
    }
  }
  augment "/goam:trace-route/goam:input/goam:source-mep/goam:mep-
address" {
    case trill-nickname {
      leaf trill-nickname {
        type tril-rb-nickname;
      }
    }
  }
  augment "/goam:trace-route/goam:input/goam:destination-
mep/goam:mep-address" {
    case trill-nickname {
      leaf trill-nickname {
        type tril-rb-nickname;
      }
    }
  }
  augment "/goam:trace-
route/goam:output/goam:response/goam:destination-mep/goam:mep-
address" {
    case trill-nickname {
      leaf trill-nickname {
        type tril-rb-nickname;
      }
    }
  }
  augment "/goam:trace-route/goam:output/goam:response" {
    description
      "adds trill specific items on the response";
    leaf upstream-rbridge {
      type tril-rb-nickname;
    }
    leaf-list next-hop-rbridge {
      type tril-rb-nickname;
      description
        "nickname of the next hop RBRdige";
    }
  }
  rpc mtv {
    description
      "Generates Trace-route and return response. Starts with TTL
       of one and increment by one at each hop. Untill destination
       reached or TTL reach max valune";
    input {
      uses goam:maintenance-domain {
        description
          "Specifies the MA-domain";
      }
      uses goam:ma-identifier {
        description
          "identfies the Maintenance association";
      }
      uses command-ext-trill {
        description
          "defines extensions needed for trill.
           We are using this structure so mtv command is in line
           with ping and trace-route";
      }
      choice context-id {
        case context-id-vlan {
          leaf context-id-vlan {
            type vlan;
          }
        }
        case context-id-fgl {
          leaf context-id-fgl {
            type fgl;
          }
        }
      }
      choice flow-entropy {
        case flow-entropy-null {
          leaf flow-entropy-null {
            type empty;
          }
        }
        case flow-entropy-trill {
          leaf flow-entropy-trill {
            type flow-entropy-trill;
          }
        }
      }
      leaf max-hop-count {
        type uint8;
        default "255";
        description
          "Defines maximum value of hop count";
      }
      leaf type {
        type identityref {
          base goam:command-sub-type;
        }
        description
          "defines different command types";
      }
      leaf-list scope {
        type tril-rb-nickname;
        reference "draft-ietf-trill-oam-fm";
        description
          "This list contain rbridges that needed to respond
           Empty list indicate all Rbridges needed to respond";
      }
      leaf ecmp-choice {
        type goam:ecmp-choices;
        description
          "0 means use the specified interface
           1 means use round robin";
      }
      list outgoing-interfaces {
        key "interface";
        leaf interface {
          type if:interface-ref;
        }
      }
      container source-mep {
        uses goam:mep-address;
        leaf mep-id {
          type goam:MEP-id;
        }
      }
      container destination-mep {
        uses goam:mep-address;
        leaf mep-id {
          type goam:MEP-id;
        }
      }
    }
    output {
      list response {
        key "mep-address mep-id";
        leaf hop-count {
          type uint8;
        }
        leaf mep-id {
          type goam:MEP-id;
        }
        leaf mep-address {
          type tril-rb-nickname;
        }
        leaf-list next-hop-rbridge {
          type tril-rb-nickname;
          description
            "list of downstream rbridges. There is no perticular
order";
        }
        leaf upstream-rbridge {
          type tril-rb-nickname;
        }
        leaf multicast-receiver-count {
          type uint32;
          description
            "number of ports that are interested in this multicast
stream";
        }
        uses goam:monitor-stats;
      }
    }
  }
}
