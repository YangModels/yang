module ietf-nvo3{
        namespace "urn:ietf:params:xml:ns:yang:ietf-nvo3";
        prefix "nvo3";

        import ietf-inet-types {
    prefix "inet";
        }

        import ietf-interfaces {
    prefix "if";
        }

        organization
          "IETF Nvo3( Network Virtualization Overlays) Working Group";

        contact
       "WG List:  <mailto:nvo3@ietf.org>
        WG Chair: Matthew Bocci
                  <mailto:matthew.bocci@nokia.com>
         WG Chair: Sam Aldrin
                  <mailto:aldrin.ietf@gmail.com>

                Editor:   Ran Chen
                                <mailto:chen.ran@zte.com.cn>
        Editor:   Fangwei Hu
                <mailto:hu.fangwei@zte.com.cn>
                Editor:   yubao wang
                <mailto:wang.yubao@zte.com.cn>
                Editor:   xufeng liu
                <mailto:xufeng.liu.ietf@gmail.com>
                ";

                description
                "The YANG module defines a generic configuration model for nvo3 yang module.";
         revision 2019-03-20{
                description
                "02 version";
                reference "draft-chen-nvo3-yang-02";
     }

                revision 2019-03-11{
                description
                "01 version";
                reference "draft-chen-nvo3-yang-01";
     }
                revision 2018-10-31{
                description
                "Initial version";
                reference "draft-chen-nvo3-yang-00";
     }

    /*Typedefs*/

    typedef vni{
          type uint32;
          description
            "Virtual Network Identifier";
         }

        typedef unicast-tunnel-name{
          type string;
          description
            "the name for unicast tunnel";
         }
        typedef multicast-tunnel-name{
          type string;
          description
            "the name for multicast tunnel";
         }
         typedef evpn-instance-ref {
       type leafref {
         path "/evpn/evpn-instances/evpn-instance/name";
       }
       description "A leafref type to an EVPN instance";
     }

        typedef ac-name{
          type string;
          description
            "the name for ac";
         }

        typedef interface-name{
          type string;
          description
            "the name for interface";
         }

         grouping unicast-tunnel-cfg{
            leaf encaptype{
                  type enumeration{
                    enum "vxlan"{
                      description
                        "vxlan type";
                            }
                    enum "geneve"{
                      description
                        "geneve type";
                            }
                    }
             description "the type for encapsulation.";
             }
           leaf tunnel-source-ipv4{
                 type inet:ipv4-prefix;
                 description
                 "tunnel source ipv4 prefix.";
               }
           leaf tunnel-source-ipv6{
                 type inet:ipv6-prefix;
                 description
                 "tunnel source ipv6 prefix.";
               }
                   leaf tunnel-destination-ipv4{
                 type inet:ipv4-prefix;
                 description
                 "tunnel destination ipv4 prefix.";
               }
              leaf tunnel-destination-ipv6{
                 type inet:ipv6-prefix;
                 description
                 "tunnel destination ipv6 prefix.";
               }
              description
                 "defines the unicast tunnel configuration.";
                }
                grouping multicast-tunnel-cfg{
            leaf encaptype{
                  type enumeration{
                    enum "vxlan"{
                      description
                        "vxlan type";
                            }
                    enum "geneve"{
                      description
                        "geneve type";
                            }
                    }
             description "the type for encapsulation.";
             }
           leaf tunnel-source-ipv4{
                 type inet:ipv4-prefix;
                 description
                 "tunnel source ipv4 prefix.";
               }
           leaf tunnel-source-ipv6{
                 type inet:ipv6-prefix;
                 description
                 "tunnel source ipv6 prefix.";
               }
                   list tunnel-destination-ipv4{
             key "destination-ipv4";
                         description
               "the list of destination ipv4 prefix.";
                       leaf destination-ipv4{
                 type inet:ipv4-prefix;
                 description
                   "tunnel destination ipv4 prefix.";
               }
                           }
                   list tunnel-destination-ipv6{
                   key "destination-ipv6";
                   description
               "the list of destination ipv6 prefix.";
                       leaf destination-ipv6{
                 type inet:ipv6-prefix;
                 description
                   "tunnel destination ipv6 prefix.";
               }
                           }
              description
                 "defines the multicast tunnel configuration.";
                }

        container nvo3{
          leaf vxlan-enable{
                type boolean;
            default false;
            description
              "Enables vxlan protocol.";
                  }
          leaf geneve-enable{
                type boolean;
            default false;
            description
              "Enables geneve protocol.";
                  }
           list nvo3-instance {
           key "vni";
           leaf vni {
             type vni;
             description "Virtual Network Identifier.";
           }
           leaf protocol-type{
             type enumeration{
                       enum "ipv4"{
                         description
                           "ipv4 protocol";
                              }
                       enum "ipv6"{
                         description
                           "ipv6 protocol";
                               }
                       enum "ethernet"{
                         description
                           "ethernet protocol";
                              }
                       enum "mpls"{
                         description
                           "mpls protocol";
                              }
                       enum "GBP"{
                         description
                           "gbp";
                          }
                      enum "vBNG"{
                        description
                          "vbng";
                              }
                        }
             description "the next protocol type";
             }
                         leaf vtep-ipv4 {
             type inet:ipv4-address-no-zone;
             description
               "NVO3 tunnel source address";
           }
           leaf vtep-ipv6 {
             type inet:ipv6-address-no-zone;
             description
               "ipv6 NVO3 tunnel source address";
           }

           leaf bridge-interface {
            type if:interface-ref;
            description "bridge interface.";
                }

                choice control-plane {
                  case evpn{
                     leaf evpn-instance{
               type evpn-instance-ref;
                           description "Reference to an EVPN instance";
                          }
                         }
                  case static-config{
           leaf ac-name {
             type ac-name;
             description "the name for ac.";
           }
                   leaf l2interface-name{
                     type if:interface-ref;
            description "L2 interface.";
                }
        description
                                "static-config.";
            }
       description "the control-plane.";
           }
                list unicast-tunnel{
           key "unicast-tunnel-name";
           leaf unicast-tunnel-name {
             type unicast-tunnel-name;
             description "the name for unicast tunnel.";
           }
        description
                                "the information for the unicast tunnel configuration.";
                }

        list multicast-tunnel{
           key "multicast-tunnel-name";
           leaf multicast-tunnel-name {
             type multicast-tunnel-name;
             description "the name for multicast tunnel.";
           }
        description
                                "the information for the multicast tunnel.";
                }
        description
                                "defines the nvo3 instance configuration.";
       }

                list unicast-tunnel{
           key "unicast-tunnel-name";
           leaf unicast-tunnel-name {
             type unicast-tunnel-name;
             description "the name for unicast tunnel.";
           }
                    uses nvo3:unicast-tunnel-cfg;
        description
                                "defines the unicast tunnel configuration.";
                }

              list multicast-tunnel{
           key "multicast-tunnel-name";
           leaf multicast-tunnel-name {
             type multicast-tunnel-name;
             description "the name for multicast tunnel.";
           }
                    uses nvo3:multicast-tunnel-cfg;
        description
                                "defines the multicast tunnel configuration.";
                }
                description
                    "defines the nvo3 configuration.";
                }

                container nvo3-state{
             config false;
                 description
                   "nvo3 operational state.";
                 list nvo3-instance {
           key "vni";
           leaf vni {
             type vni;
             description "Virtual Network Identifier.";
           }
           leaf protocol-type{
             type enumeration{
                       enum "ipv4"{
                         description
                           "ipv4 protocol";
                              }
                       enum "ipv6"{
                         description
                           "ipv6 protocol";
                               }
                       enum "ethernet"{
                         description
                           "ethernet protocol";
                              }
                       enum "mpls"{
                         description
                           "mpls protocol";
                              }
                       enum "GBP"{
                         description
                           "gbp";
                          }
                      enum "vBNG"{
                        description
                          "vbng";
                              }
                        }
             description "the next protocol type";
             }
             leaf vtep-ipv4 {
             type inet:ipv4-address-no-zone;
             description
               "NVO3 tunnel source address";
           }
           leaf vtep-ipv6 {
             type inet:ipv6-address-no-zone;
             description
               "ipv6 NVO3 tunnel source address";
           }
           leaf bridge-interface {
            type if:interface-ref;
            description "bridge interface.";
                }
                choice control-plane {
                  case evpn{
                     leaf evpn-instance{
               type evpn-instance-ref;
                           description "Reference to an EVPN instance";
                          }
                         }
                  case static-config{
           leaf ac-name {
             type ac-name;
             description "the name for ac.";
           }
                   leaf l2interface-name{
                     type if:interface-ref;
            description "L2 interface.";
                }
        description
                                "static-config.";
            }
       description "the control-plane.";
           }
                list unicast-tunnel{
           key "unicast-tunnel-name";
           leaf unicast-tunnel-name {
             type unicast-tunnel-name;
             description "the name for unicast tunnel.";
           }
        description
                                "the information for the unicast tunnel.";
                }

        list multicast-tunnel{
           key "multicast-tunnel-name";
           leaf multicast-tunnel-name {
             type multicast-tunnel-name;
             description "the name for multicast tunnel.";
           }
        description
                                "the state for multicast tunnel.";
                }
        description
                                "the state for nvo3 instance.";
       }

                list unicast-tunnel{
           key "unicast-tunnel-name";
           leaf unicast-tunnel-name {
             type unicast-tunnel-name;
             description "the name for unicast tunnel.";
           }
                    uses nvo3:unicast-tunnel-cfg;
        description
                                "the state for the unicast tunnel.";
                }

              list multicast-tunnel{
           key "multicast-tunnel-name";
           leaf multicast-tunnel-name {
             type multicast-tunnel-name;
             description "the name for multicast tunnel.";
           }
                    uses nvo3:multicast-tunnel-cfg;
        description
                                "the state for the multicast tunnel.";
                }
                }
                }
