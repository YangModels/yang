module ietf-pim-sm {
  namespace "urn:ietf:params:xml:ns:yang:ietf-pim-sm";
  // replace with IANA namespace when assigned
  prefix pim-sm;

  import ietf-inet-types {
    prefix "inet";
  }

  import ietf-routing {
    prefix "rt";
  }

  import ietf-pim-base {
    prefix "pim-base";
  }

  import ietf-pim-rp {
    prefix "pim-rp";
  }

  organization
    "IETF PIM Working Group";

  contact
    "WG Web:   <http://tools.ietf.org/wg/pim/>
     WG List:  <mailto:pim@ietf.org>

     WG Chair: Stig Venaas
               <mailto:stig@venaas.com>

     WG Chair: Mike McBride
               <mailto:mmcbride7@gmail.com>

     Editors:   ";

  description
    "The YANG module defines a sparse mode PIM model.";

  revision 2016-03-18 {
    description
      "Initial revision.";
    reference
      "RFC XXXX: A YANG Data Model for PIM";
  }

  /*
   * Features
   */
  feature spt-switch-infinity {
    description
      "This feature indicates that the system supports configuration
      choice whether to trigger the switchover from the rpt to the
      spt.";
  }

  feature spt-switch-policy {
    description
      "This feature indicates that the system supports configuring
      policy for the switchover from the rpt to the spt.";
  }

  /*
   * Identities
   */
  identity sm {
    base pim-rp:rp-mode;
    description
      "SM (Spars Mode).";
  }

  /*
   * Groupings
   */
  grouping af-sm-container {
    description
      "Gouping of address family SM container.";
    container sm {
      description
        "PIM SM configuration data.";

      container asm {
        description
          "ASM (Any Source Multicast) attributes.";

        container anycast-rp {
          presence
            "Present to enable anycast RP.";
          description
            "Anycast RP attributes.";

          container ipv4 {
            when "../../../../address-family = 'rt:ipv4'" {
              description
                "Only applicable to ipv4 address family.";
            }
            description
              "IPv4 attributes. Only applicable when
              pim-base:address-family is ipv4.";
            list ipv4-anycast-rp {
              key "anycast-addr rp-addr";
              description
                "A list of anycast RP setttings.";
              leaf anycast-addr {
                type inet:ipv4-address;
                description
                  "IP address of the anycast RP set. This IP address
                  is used by the multicast groups or sources to join
                  or register.";
              }

              leaf rp-addr {
                type inet:ipv4-address;
                description
                  "IP address of the router configured with anycast
                  RP. This is the IP address where the Register
                  messages are forwarded.";
              }
            }
          }
          container ipv6 {
            when "../../../../address-family = 'rt:ipv6'" {
              description
                "Only applicable to ipv6 address family.";
            }
            description
              "IPv6 attributes. Only applicable when
              pim-base:address-family is ipv6.";
            list ipv6-anycast-rip {
              key "anycast-addr rp-addr";
              description
                "A list of anycast RP setttings.";
              leaf anycast-addr {
                type inet:ipv6-address;
                description
                  "IP address of the anycast RP set. This IP address
                  is used by the multicast groups or sources to join
                  or register.";
              }
              leaf rp-addr {
                type inet:ipv6-address;
                description
                  "IP address of the router configured with anycast
                  RP. This is the IP address where the Register
                  messages are forwarded.";
              }
            }
          }
        }

        container spt-switch {
          description
            "SPT (Shortest Path Tree) switching attributes.";
          container infinity {
            if-feature spt-switch-infinity;
            presence "Present if spt-switch is set to infinity.";
            description
              "The receiver's dr never triggers the
              switchover from the rpt to the spt.";
            leaf policy-name {
              if-feature spt-switch-policy;
              type string;
              description
                "Switch policy.";
            }
          } // infinity
        }
      } // asm

      container ssm {
        presence
          "Present to enable SSM (Source-Specific Multicast).";
        description
          "SSM (Source-Specific Multicast) attributes.";

        leaf range-poligy {
          type string;
          description
            "Policy used to define SSM address range.";
        }
      } // ssm
    } // sm
  } // af-sm-container

  grouping interface-sm-container {
    description
      "Gouping of interface SM container.";
    container sm {
      presence "Present to enable sparse-mode.";
      description
        "PIM SM configuration data.";

      leaf passive {
        type empty;
        description
          "Specifies that no PIM messages are sent out of the PIM
          interface, but the interface can be included in a multicast
          forwarding entry.";
      }
    } // sm
  } // interface-sm-container

  grouping static-rp-sm-container {
    description
      "Gouping that contains SM attributes for static RP.";
    container sm {
      presence
        "Indicate the support of sparse mode.";
      description
        "PIM SM configuration data.";

      uses pim-rp:static-rp-attributes;
    } // sm
  } // static-rp-sm-container

  /*
   * Configuration data nodes
   */

  augment "/rt:routing/rt:routing-protocols/pim-base:pim/"
    + "pim-base:address-family" {
    description "PIM SM augmentation.";

    uses af-sm-container;
  } // augment

  augment "/rt:routing/rt:routing-protocols/pim-base:pim/"
    + "pim-base:interfaces/pim-base:interface/"
    + "pim-base:address-family" {
    description "PIM SM augmentation.";

    uses interface-sm-container;
  } // augment

  augment "/rt:routing/rt:routing-protocols/pim-base:pim/"
    + "pim-base:address-family/pim-rp:rp/"
    + "pim-rp:static-rp/pim-rp:ipv4-rp" {
    description "PIM SM augmentation.";

    uses static-rp-sm-container;
  } // augment

  augment "/rt:routing/rt:routing-protocols/pim-base:pim/"
    + "pim-base:address-family/pim-rp:rp/"
    + "pim-rp:static-rp/pim-rp:ipv6-rp" {
    description "PIM SM augmentation.";

    uses static-rp-sm-container;
  } // augment

  /*
   * Operational state data nodes
   */

  augment "/rt:routing-state/rt:routing-protocols/pim-base:pim/"
    + "pim-base:address-family" {
    description
      "PIM SM state.";

    uses af-sm-container;
  } // augment

  augment "/rt:routing-state/rt:routing-protocols/pim-base:pim/"
    + "pim-base:interfaces/pim-base:interface/"
    + "pim-base:address-family" {
    description "PIM SM augmentation.";

    uses interface-sm-container;
  } // augment

  augment "/rt:routing-state/rt:routing-protocols/pim-base:pim/"
    + "pim-base:address-family/pim-rp:rp/"
    + "pim-rp:static-rp/pim-rp:ipv4-rp" {
    description "PIM SM augmentation.";

    uses static-rp-sm-container;
  } // augment

  augment "/rt:routing-state/rt:routing-protocols/pim-base:pim/"
    + "pim-base:address-family/pim-rp:rp/"
    + "pim-rp:static-rp/pim-rp:ipv6-rp" {
    description "PIM SM augmentation.";

    uses static-rp-sm-container;
  } // augment

  /*
   * RPCs
   */

  /*
   * Notifications
   */
}
