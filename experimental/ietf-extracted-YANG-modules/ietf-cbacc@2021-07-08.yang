module ietf-cbacc {
  yang-version 1.1;

  namespace "urn:ietf:params:xml:ns:yang:ietf-cbacc";
  prefix "cbacc";

  import ietf-dorms {
    prefix "dorms";
    reference "I-D.jholland-mboned-dorms";
  }

  organization "IETF";

  contact
      "Author:   Jake Holland
                 <mailto:jholland@akamai.com>
      ";

  description
  "Copyright (c) 2019 IETF Trust and the persons identified as
   authors of the code.  All rights reserved.

   Redistribution and use in source and binary forms, with or
   without modification, is permitted pursuant to, and subject to
   the license terms contained in, the Simplified BSD License set
   forth in Section 4.c of the IETF Trust's Legal Provisions
   Relating to IETF Documents
   (https://trustee.ietf.org/license-info).

   This version of this YANG module is part of
   draft-jholland-mboned-cbacc.  See the internet draft for full
   legal notices.

   The key words 'MUST', 'MUST NOT', 'REQUIRED', 'SHALL', 'SHALL
   NOT', 'SHOULD', 'SHOULD NOT', 'RECOMMENDED', 'NOT RECOMMENDED',
   'MAY', and 'OPTIONAL' in this document are to be interpreted as
   described in BCP 14 (RFC 2119) (RFC 8174) when, and only when,
   they appear in all capitals, as shown here.

   This module contains the definition for bandwidth consumption
   metadata for SSM channels, as an extension to DORMS
   (draft-ietf-mboned-dorms).";

  revision 2021-07-08 {
    description "Draft version, post-early-review.";
    reference
      "draft-ietf-mboned-cbacc";
  }

  augment
    "/dorms:dorms/dorms:metadata/dorms:sender/dorms:group" {
      description "Definition of the manifest stream providing
          integrity info for the data stream";

    container cbacc {
      presence "CBACC-enabled flow";
      description
        "Information to enable fast-trip circuit breakers";
      leaf max-speed {
        type uint32;
        units "kilobits/second";
        mandatory true;
        description "Maximum bitrate for this stream, in Kilobits
            of IP packet data (including headers) of native
            multicast traffic per second";
      }
      leaf max-packet-size {
        type uint16;
        default 1400;
        description "Maximum IP payload size, in octets.";
      }
      leaf data-rate-window {
          type uint32;
          units "milliseconds";
          default 2000;
          description
            "Time window over which data rate is guaranteed,
             in milliseconds.";
          /* TBD: range limits? */
      }
      leaf priority {
          type uint16;
          default 256;
          description
            "The relative preference level for keeping this flow
             compared to other flows from this sender (higher
             value is more preferred to keep)";
      }
    }
  }
}
