module ietf-te-topology-sf-state {
  yang-version 1;
  namespace "urn:ietf:params:xml:ns:yang:ietf-te-topology-sf-state";

  prefix "tet-sf-s";

  import ietf-te-topology-sf {
    prefix "tet-sf";
  }

  import ietf-network-state {
    prefix "nw-s";
  }

  import ietf-network-topology-state {
    prefix "nt-s";
  }

  import ietf-te-topology-state {
    prefix "tet-s";
  }

  organization
    "Traffic Engineering Architecture and Signaling (TEAS)
     Working Group";

  contact
    "WG Web:   <http://tools.ietf.org/wg/teas/>
     WG List:  <mailto:teas@ietf.org>

     Editors:  Igor Bryskin
               <mailto:Igor.Bryskin@huawei.com>

               Xufeng Liu
               <mailto:Xufeng_Liu@jabil.com>";

  description
    "Network service and function aware aware TE topology operational
     state model for non-NMDA compliant implementations.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).";

  revision 2018-02-27 {
    description "Initial revision";
    reference "TBD";
  }

  /*
   * Augmentations
   */
  /* Augmentations to network-types/te-topology */
  augment "/nw-s:networks/nw-s:network/nw-s:network-types/"
    + "tet-s:te-topology" {
    description
      "Defines the SF aware TE topology type.";
    uses tet-sf:sf-topology-type;
  }

  /* Augmentations to connectivity-matrix */
  augment "/nw-s:networks/nw-s:network/nw-s:node/tet-s:te/"
    + "tet-s:te-node-attributes" {
    description
      "Parameters for SF aware TE topology.";
    uses tet-sf:service-function-node-augmentation;
  }

  augment "/nw-s:networks/nw-s:network/nw-s:node/tet-s:te/"
        + "tet-s:information-source-entry" {
    description
      "Parameters for SF aware TE topology.";
    uses tet-sf:service-function-node-augmentation;
  }

  /* Augmentations to tunnel-termination-point */
  augment "/nw-s:networks/nw-s:network/nw-s:node/tet-s:te/"
    + "tet-s:tunnel-termination-point" {
    description
      "Parameters for SF aware TE topology.";
    uses tet-sf:service-function-ttp-augmentation;
  }

  /* Augmentations to connectivity-matrix */
  augment "/nw-s:networks/nw-s:network/nw-s:node/tet-s:te/"
    + "tet-s:te-node-attributes/tet-sf-s:service-function/"
    + "tet-sf-s:link-terminations/tet-sf-s:link-termination/"
    + "tet-sf-s:from" {
    description
      "Add reference to the link termination point.
       This portion cannot be shared with the state module.";
    leaf tp-ref {
      type leafref {
        path "../../../../../../../nt-s:termination-point/"
          + "nt-s:tp-id";
      }
      description
        "Reference to the link termination point.";
    }
  }
}
