module ietf-adapt-subscription {
  yang-version 1.1;
  namespace "urn:ietf:params:xml:ns:yang:ietf-adapt-subscription";
  prefix as;

  import ietf-subscribed-notifications {
    prefix sn;
    reference
      "RFC 8639: Subscription to YANG Notifications";
  }
  import ietf-yang-push {
    prefix yp;
    reference
      "RFC 8641: Subscription to YANG Notifications for Datastore
       Updates";
  }
  import ietf-yang-types {
    prefix yang;
    reference
      "RFC YYYY: Common YANG Data Types";
  }

  organization
    "IETF NETCONF (Network Configuration) Working Group";
  contact
    "WG Web:   <http://tools.ietf.org/wg/netconf>
     WG List:  <netconf@ietf.org>

     Editor: Qin Wu
           <mailto:bill.wu@huawei.com>

     Editor: Wei Song
           <mailto: songwei80@huawei.com>

     Editor: Peng Liu
           <mailto: liupengyjy@chinamobile.com>

     Editor: Qiufang Ma
           <mailto: maqiufang1@huawei.com>

     Editor: Wei Wang
          <mailto: wangw36@chinatelecom.cn>

     Editor: Zhixiong Niu
          <mailto: Zhixiong.Niu@microsoft.com>";
  description
    "This module extends the YANG data module defined in
     YANG-push to enable the subscriber's adaptive
     subscriptions to a publisher's event streams with various
     different period intervals to report updates.

     Copyright (c) 2023 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC xxxx
     (https://www.rfc-editor.org/info/rfcxxxx); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2023-05-30 {
    description
      "Initial revision";
    reference
      "RFC xxxx: Adaptive Subscription to YANG Notification.";
  }

  identity adaptive-unsupported {
    base sn:establish-subscription-error;
    description
      "Adaptive-subscription is not supported for any objects
       that are selectable by the filter.";
  }

  identity xpath-evaluation-unsupported {
    base sn:establish-subscription-error;
    description
      "Unable to parse the xpath evaluation criteria defined in
       'xpath-external-eval' because of a syntax error or some
       XPath 1.0 syntax not supported against the specific
       object.";
  }

  identity multi-xpath-criteria-conflict {
    base sn:establish-subscription-error;
    base sn:subscription-terminated-reason;
    description
      "Multiple Xpath evaluation criteria represented by
       'xpath-external-eval' are evaluated as a conflict. I.e.,
       more than one condition expression is evaluated to
       'true'.";
  }

  grouping adaptive-subscription-modifiable {
    description
      "This grouping describes the datastore-specific adaptive
       subscription conditions that can be changed during the
       lifetime of the subscription.";
    container adaptive-periods {
      list adaptive-period {
        key "name";
        description
          "An entry in this list represents an adaptive period
           which defines a push update interval and trigger
           conditions to switch to the update interval for
           sending an event record to the subscriber.";
        leaf name {
          type yang:yang-identifier;
          description
            "The name of adaptive period.";
        }
        leaf xpath-external-eval {
          type yang:xpath1.0;
          mandatory true;
          description
            "An XPath string, representing a logical expression,
             which can contain comparisons of datastore values
             and logical operations in the XPath format.";
        }
        leaf period {
          type yp:centiseconds;
          mandatory true;
          description
            "Duration of time that should occur between periodic
             push updates, in units of 0.01 seconds.";
        }
        leaf anchor-time {
          type yang:date-and-time;
          description
            "Designates a timestamp before or after which a series
             of periodic push updates is determined.  The next
             update will take place at a point in time that is a
             multiple of a period from the 'anchor-time'.
             For example, for an 'anchor-time' that is set for the
             top of a particular minute and a period interval of a
             minute, updates will be sent at the top of every
             minute that this subscription is active.";
        }
      }
      description
        "Container for adaptively periodic subscription.";
    }
  }

  augment "/sn:subscriptions/sn:subscription/yp:update-trigger" {
    description
      "This augmentation adds additional subscription parameters
       that apply specifically to adaptive subscription.";
    case adaptive-periodic {
      description
        "Defines adaptively periodic case for sending an event
         record to the subscriber.";
      uses adaptive-subscription-modifiable;
    }
  }

  augment "/sn:establish-subscription/sn:input/yp:update-trigger" {
    description
      "This augmentation adds additional establish-subscription
       parameters that apply specifically to datastore updates to
       RPC input.";
    case adaptive-periodic {
      description
        "Defines adaptively periodic case for sending an event
         record to the subscriber.";
      uses adaptive-subscription-modifiable;
    }
  }

  augment "/sn:modify-subscription/sn:input/yp:update-trigger" {
    description
      "This augmentation adds additional modify-subscription
       parameters that apply specifically to datastore updates to
       RPC input.";
    case adaptive-periodic {
      description
        "Defines adaptively periodic case for sending an event
         record to the subscriber.";
      uses adaptive-subscription-modifiable;
    }
  }

  augment "/sn:subscription-started/yp:update-trigger" {
    description
      "This augmentation adds additional adaptive subscription
       parameters to the notification that a subscription has
       started.";
    case adaptive-periodic {
      description
        "Defines adaptively periodic case for sending an event
         record to the subscriber.";
      uses adaptive-subscription-modifiable;
    }
  }

  augment "/sn:subscription-modified/yp:update-trigger" {
    description
      "This augmentation adds additional adaptive subscription
       parameters to the notification that a subscription has been
       modified.";
    case adaptive-periodic {
      description
        "Defines adaptively periodic case for sending an event
         record to the subscriber.";
      uses adaptive-subscription-modifiable;
    }
  }

  notification adaptive-period-update {
    sn:subscription-state-notification;
    description
      "This notification contains a push update that in turn
       contains data subscribed to via a subscription.  In the
       case of a periodic subscription, this notification is sent
       for periodic updates.  It can also be used for
       synchronization updates of an on-change subscription.
       This notification shall only be sent to receivers of a
       subscription.  It does not constitute a general-purpose
       notification that would be subscribable as part of the
       NETCONF event stream by any receiver.";
    leaf id {
      type sn:subscription-id;
      description
        "This references the subscription that drove the
         notification to be sent.";
    }
    leaf period {
      type yp:centiseconds;
      mandatory true;
      description
        "New duration of time that should occur between periodic
         push updates, in units of 0.01 seconds.";
    }
    leaf period-update-time {
      type yang:date-and-time;
      description
        "Designates a timestamp when the server starts to switch
         to another period interval because the evaluated 'xpath-
         external-eval' expression result changed.";
    }
    uses yp:datastore-criteria {
      refine "selection-filter/within-subscription" {
        description
          "Specifies the selection filter and where it originated
           from.  If the 'selection-filter-ref' is populated, the
           filter in the subscription came from the 'filters'
           container.  Otherwise, it is populated in-line as part
           of the subscription itself.";
      }
    }
  }
}
