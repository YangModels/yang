module ietf-layer1-types {
  yang-version 1.1;
  namespace "urn:ietf:params:xml:ns:yang:ietf-layer1-types";
  prefix l1-types;

  import ietf-routing-types {
    prefix rt-types;
    reference
      "RFC 8294: Common YANG Data Types for the Routing Area";
  }

  organization
    "IETF CCAMP Working Group";
  contact
    "WG Web: <https://datatracker.ietf.org/wg/ccamp/>
     WG List: <mailto:ccamp@ietf.org>

     Editor: Haomian Zheng
             <mailto:zhenghaomian@huawei.com>

     Editor: Italo Busi
             <mailto:Italo.Busi@huawei.com>";
  description
    "This module defines Layer 1 YANG types.

     Copyright (c) 2026 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-06-12 {
    description
      "Initial Version";
    reference
      "RFC XXXX: A YANG Data Model for Layer 1 Types";
    // RFC Editor: replace RFC XXXX with actual RFC number,
    // update date information and remove this note.
  }

  /*
   * Identities
   */

  identity tributary-slot-granularity {
    description
      "Tributary Slot Granularity (TSG).";
    reference
      "ITU-T G.709 v6.0 (06/2020): Interfaces for the Optical
                 Transport Network (OTN)";
  }

  identity tsg-1.25G {
    base tributary-slot-granularity;
    description
      "1.25G tributary slot granularity.";
  }

  identity tsg-2.5G {
    base tributary-slot-granularity;
    description
      "2.5G tributary slot granularity.";
  }

  identity tsg-5G {
    base tributary-slot-granularity;
    description
      "5G tributary slot granularity.";
  }

  identity odu-type {
    description
      "Base identity from which specific Optical Data Unit (ODU)
       type is derived.";
    reference
      "RFC 7139: GMPLS Signaling Extensions for Control of Evolving
                 G.709 Optical Transport Networks
       ITU-T G.709 v6.0 (06/2020): Interfaces for the Optical
                 Transport Network (OTN)";
  }

  identity ODU0 {
    base odu-type;
    description
      "ODU0 type (1.24Gb/s).";
    reference
      "RFC 7139: GMPLS Signaling Extensions for Control of
                 Evolving G.709 Optical Transport Networks
       ITU-T G.709 v6.0 (06/2020): Interfaces for the Optical
                 Transport Network (OTN)";
  }

  identity ODU1 {
    base odu-type;
    description
      "ODU1 type (2.49Gb/s).";
    reference
      "RFC 7139: GMPLS Signaling Extensions for Control of
                 Evolving G.709 Optical Transport Networks
       ITU-T G.709 v6.0 (06/2020): Interfaces for the Optical
                 Transport Network (OTN)";
  }

  identity ODU2 {
    base odu-type;
    description
      "ODU2 type (10.03Gb/s).";
    reference
      "RFC 7139: GMPLS Signaling Extensions for Control of
                 Evolving G.709 Optical Transport Networks
       ITU-T G.709 v6.0 (06/2020): Interfaces for the Optical
                 Transport Network (OTN)";
  }

  identity ODU2e {
    base odu-type;
    description
      "ODU2e type (10.39Gb/s).";
    reference
      "RFC 7139: GMPLS Signaling Extensions for Control of
                 Evolving G.709 Optical Transport Networks
       ITU-T G.709 v6.0 (06/2020): Interfaces for the Optical
                 Transport Network (OTN)";
  }

  identity ODU3 {
    base odu-type;
    description
      "ODU3 type (40.31Gb/s).";
    reference
      "RFC 7139: GMPLS Signaling Extensions for Control of
                 Evolving G.709 Optical Transport Networks
       ITU-T G.709 v6.0 (06/2020): Interfaces for the Optical
                 Transport Network (OTN)";
  }

  identity ODU4 {
    base odu-type;
    description
      "ODU4 type (104.79Gb/s).";
    reference
      "RFC 7139: GMPLS Signaling Extensions for Control of
                 Evolving G.709 Optical Transport Networks
       ITU-T G.709 v6.0 (06/2020): Interfaces for the Optical
                 Transport Network (OTN)";
  }

  identity ODUflex {
    base odu-type;
    description
      "ODUflex type (flexible bit rate, not resizable).

       It could be used for any type of ODUflex, including
       ODUflex(CBR), ODUflex(GFP), ODUflex(GFP,n,k), ODUflex(IMP,s),
       ODUflex(IMP) and ODUflex(FlexE-aware).";
    reference
      "RFC 7139: GMPLS Signaling Extensions for Control of
                 Evolving G.709 Optical Transport Networks
       ITU-T G.709 v6.0 (06/2020): Interfaces for the Optical
                 Transport Network (OTN)";
  }

  identity ODUflex-resizable {
    base odu-type;
    description
      "ODUflex protocol (flexible bit rate, resizable).

       It could be used only for ODUflex(GFP,n,k).";
    reference
      "RFC 7139: GMPLS Signaling Extensions for Control of
                 Evolving G.709 Optical Transport Networks
       ITU-T G.709 v6.0 (06/2020): Interfaces for the Optical
                 Transport Network (OTN)";
  }

  identity protocol {
    description
      "Base identity from which specific protocol is derived.";
    reference
      "MEF 63: Subscriber Layer 1 Service Attributes";
  }

  identity Ethernet {
    base protocol;
    description
      "Ethernet protocol.";
    reference
      "MEF 63: Subscriber Layer 1 Service Attributes";
  }

  identity Fibre-Channel {
    base protocol;
    description
      "Fibre-Channel (FC) protocol.";
    reference
      "MEF 63: Subscriber Layer 1 Service Attributes";
  }

  identity SDH {
    base protocol;
    description
      "SDH protocol.";
    reference
      "MEF 63: Subscriber Layer 1 Service Attributes";
  }

  identity SONET {
    base protocol;
    description
      "SONET protocol.";
    reference
      "MEF 63: Subscriber Layer 1 Service Attributes";
  }

  identity client-signal {
    description
      "Base identity from which specific Constant Bit Rate (CBR)
       client signal is derived";
  }

  identity coding-func {
    description
      "Base identity from which specific coding function
       is derived.";
    reference
      "MEF 63: Subscriber Layer 1 Service Attributes";
  }

  identity ETH-1Gb {
    base client-signal;
    description
      "Client signal type of 1GbE.";
    reference
      "IEEE Std 802.3-2022: IEEE Standard for Ethernet, Clause 36
       RFC 7139: GMPLS Signaling Extensions for Control of
                 Evolving G.709 Optical Transport Networks
       ITU-T G.709 v6.0 (06/2020): Interfaces for the Optical
                 Transport Network (OTN)";
  }

  identity ETH-10Gb-LAN {
    base client-signal;
    description
      "Client signal type of ETH-10Gb-LAN (10.3 Gb/s).";
    reference
      "IEEE Std 802.3-2022: IEEE Standard for Ethernet, Clause 49
       RFC 7139: GMPLS Signaling Extensions for Control of
                 Evolving G.709 Optical Transport Networks
       ITU-T G.709 v6.0 (06/2020): Interfaces for the Optical
                 Transport Network (OTN)";
  }

  identity ETH-10Gb-WAN {
    base client-signal;
    description
      "Client signal type of ETH-10Gb-WAN (9.95 Gb/s).";
    reference
      "IEEE Std 802.3-2022: IEEE Standard for Ethernet, Clause 50
       RFC 7139: GMPLS Signaling Extensions for Control of
                 Evolving G.709 Optical Transport Networks
       ITU-T G.709 v6.0 (06/2020): Interfaces for the Optical
                 Transport Network (OTN)";
  }

  identity ETH-40Gb {
    base client-signal;
    description
      "Client signal type of 40GbE.";
    reference
      "IEEE Std 802.3-2022: IEEE Standard for Ethernet, Clause 82
       RFC 7139: GMPLS Signaling Extensions for Control of
                 Evolving G.709 Optical Transport Networks
       ITU-T G.709 v6.0 (06/2020): Interfaces for the Optical
                 Transport Network (OTN)";
  }

  identity ETH-100Gb {
    base client-signal;
    description
      "Client signal type of 100GbE.";
    reference
      "IEEE Std 802.3-2022: IEEE Standard for Ethernet, Clause 82
       RFC 7139: GMPLS Signaling Extensions for Control of
                 Evolving G.709 Optical Transport Networks
       ITU-T G.709 v6.0 (06/2020): Interfaces for the Optical
                 Transport Network (OTN)";
  }

  identity STM-1 {
    base client-signal;
    base coding-func;
    description
      "Client signal type of STM-1;
       STM-1 G.707 (N=1) coding function.";
    reference
      "ITU-T G.707 v7.0 (01/2007): Network node interface for the
                 synchronous digital hierarchy (SDH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity STM-4 {
    base client-signal;
    base coding-func;
    description
      "Client signal type of STM-4;
       STM-4 G.707 (N=4) coding function.";
    reference
      "ITU-T G.707 v7.0 (01/2007): Network node interface for the
                 synchronous digital hierarchy (SDH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity STM-16 {
    base client-signal;
    base coding-func;
    description
      "Client signal type of STM-16;
       STM-16 G.707 (N=16) coding function.";
    reference
      "ITU-T G.707 v7.0 (01/2007): Network node interface for the
                 synchronous digital hierarchy (SDH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity STM-64 {
    base client-signal;
    base coding-func;
    description
      "Client signal type of STM-64;
       STM-64 G.707 (N=64) coding function.";
    reference
      "ITU-T G.707 v7.0 (01/2007): Network node interface for the
                 synchronous digital hierarchy (SDH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity STM-256 {
    base client-signal;
    base coding-func;
    description
      "Client signal type of STM-256;
       STM-256 G.707 (N=256) coding function.";
    reference
      "ITU-T G.707 v7.0 (01/2007): Network node interface for the
                 synchronous digital hierarchy (SDH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity OC-3 {
    base client-signal;
    base coding-func;
    description
      "Client signal type of OC3;
       OC-3 GR-253-CORE (N=3) coding function.";
    reference
      "ANSI T1.105-2001: Synchronous Optical Network (SONET)
                 Basic Description including Multiplex Structure,
                 Rates,  and Formats
       MEF 63: Subscriber Layer 1 Service Attributes";
  }

  identity OC-12 {
    base client-signal;
    base coding-func;
    description
      "Client signal type of OC12;
       OC-12 GR-253-CORE (N=12) coding function.";
    reference
      "ANSI T1.105-2001: Synchronous Optical Network (SONET)
                 Basic Description including Multiplex Structure,
                 Rates,  and Formats
       MEF 63: Subscriber Layer 1 Service Attributes";
  }

  identity OC-48 {
    base client-signal;
    base coding-func;
    description
      "Client signal type of OC48;
       OC-48 GR-253-CORE (N=48) coding function.";
    reference
      "ANSI T1.105-2001: Synchronous Optical Network (SONET)
                 Basic Description including Multiplex Structure,
                 Rates,  and Formats
       MEF 63: Subscriber Layer 1 Service Attributes";
  }

  identity OC-192 {
    base client-signal;
    base coding-func;
    description
      "Client signal type of OC192;
       OC-192 GR-253-CORE (N=192) coding function.";
    reference
      "ANSI T1.105-2001: Synchronous Optical Network (SONET)
                 Basic Description including Multiplex Structure,
                 Rates,  and Formats
       MEF 63: Subscriber Layer 1 Service Attributes";
  }

  identity OC-768 {
    base client-signal;
    base coding-func;
    description
      "Client signal type of OC768;
       OC-768 GR-253-CORE (N=768) coding function.";
    reference
      "ANSI T1.105-2001: Synchronous Optical Network (SONET)
                 Basic Description including Multiplex Structure,
                 Rates,  and Formats
       MEF 63: Subscriber Layer 1 Service Attributes";
  }

  identity FC-100 {
    base client-signal;
    base coding-func;
    description
      "Client signal type of Fibre Channel FC-100;
       FC-100 FC-FS-2 (1.0625 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity FC-200 {
    base client-signal;
    base coding-func;
    description
      "Client signal type of Fibre Channel FC-200;
       FC-200 FC-FS-2 (2.125 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity FC-400 {
    base client-signal;
    base coding-func;
    description
      "Client signal type of Fibre Channel FC-400;
       FC-400 FC-FS-2 (4.250 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity FC-800 {
    base client-signal;
    base coding-func;
    description
      "Client signal type of Fibre Channel FC-800;
       FC-800 FC-FS-2 (8.500 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity FC-1200 {
    base client-signal;
    base coding-func;
    description
      "Client signal type of Fibre Channel FC-1200;
       FC-1200 FC-10GFC (10.51875 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity FC-1600 {
    base client-signal;
    base coding-func;
    description
      "Client signal type of Fibre Channel FC-1600;
       FC-1600 FC-FS-3 (14.025 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity FC-3200 {
    base client-signal;
    base coding-func;
    description
      "Client signal type of Fibre Channel FC-3200;
       FC-3200 FC-FS-4 (28.05 Gb/s) coding function.";
    reference
      "ANSI INCITS 230-1994 (R1999): Information Technology -
                 Fibre Channel - Physical and Signaling Interface
                 (FC-PH)
       RFC 7139: GMPLS Signaling Extensions for Control of
                 Evolving G.709 Optical Transport Networks
       ITU-T G.709 v6.0 (06/2020): Interfaces for the Optical
                 Transport Network (OTN)
       MEF 63: Subscriber Layer 1 Service Attributes";
  }

  identity ETH-1000X {
    base coding-func;
    description
      "1000BASE-X PCS clause 36 coding function.";
    reference
      "IEEE Std 802.3-2022: IEEE Standard for Ethernet, Clause 36
       MEF 63: Subscriber Layer 1 Service Attributes";
  }

  identity ETH-10GW {
    base coding-func;
    description
      "IEEE Std 802.3-2022: IEEE Standard for Ethernet, Clause 50

       10GBASE-W (WAN PHY) PCS clause 49 and WIS clause 50
       coding function.";
    reference
      "MEF 63: Subscriber Layer 1 Service Attributes";
  }

  identity ETH-10GR {
    base coding-func;
    description
      "10GBASE-R (LAN PHY) PCS clause 49 coding function.";
    reference
      "IEEE Std 802.3-2022: IEEE Standard for Ethernet, Clause 49
       MEF 63: Subscriber Layer 1 Service Attributes";
  }

  identity ETH-40GR {
    base coding-func;
    description
      "40GBASE-R PCS clause 82 coding function.";
    reference
      "IEEE Std 802.3-2022: IEEE Standard for Ethernet, Clause 82
       MEF 63: Subscriber Layer 1 Service Attributes";
  }

  identity ETH-100GR {
    base coding-func;
    description
      "100GBASE-R PCS clause 82 coding function.";
    reference
      "IEEE Std 802.3-2022: IEEE Standard for Ethernet, Clause 82
       MEF 63: Subscriber Layer 1 Service Attributes";
  }

  identity optical-interface-func {
    description
      "Base identity from which optical-interface-function
       is derived.";
    reference
      "MEF 63: Subscriber Layer 1 Service Attributes";
  }

  identity SX-PMD-1000 {
    base optical-interface-func;
    description
      "SX-PMD-clause-38 Optical Interface function for
       1000BASE-X PCS-36.";
    reference
      "IEEE Std 802.3-2022: IEEE Standard for Ethernet, Clause 38
       MEF 63: Subscriber Layer 1 Service Attributes";
  }

  identity LX-PMD-1000 {
    base optical-interface-func;
    description
      "LX-PMD-clause-38 Optical Interface function for
       1000BASE-X PCS-36.";
    reference
      "IEEE Std 802.3-2022: IEEE Standard for Ethernet, Clause 38
       MEF 63: Subscriber Layer 1 Service Attributes";
  }

  identity LX10-PMD-1000 {
    base optical-interface-func;
    description
      "LX10-PMD-clause-59 Optical Interface function for
       1000BASE-X PCS-36.";
    reference
      "IEEE Std 802.3-2022: IEEE Standard for Ethernet, Clause 59
       MEF 63: Subscriber Layer 1 Service Attributes";
  }

  identity BX10-PMD-1000 {
    base optical-interface-func;
    description
      "BX10-PMD-clause-59 Optical Interface function for
       1000BASE-X PCS-36.";
    reference
      "IEEE Std 802.3-2022: IEEE Standard for Ethernet, Clause 59
       MEF 63: Subscriber Layer 1 Service Attributes";
  }

  identity LW-PMD-10G {
    base optical-interface-func;
    description
      "LW-PMD-clause-52 Optical Interface function for
       10GBASE-W PCS-49-WIS-50.";
    reference
      "IEEE Std 802.3-2022: IEEE Standard for Ethernet, Clause 52
       MEF 63: Subscriber Layer 1 Service Attributes";
  }

  identity EW-PMD-10G {
    base optical-interface-func;
    description
      "EW-PMD-clause-52 Optical Interface function for
       10GBASE-W PCS-49-WIS-50.";
    reference
      "IEEE Std 802.3-2022: IEEE Standard for Ethernet, Clause 52
       MEF 63: Subscriber Layer 1 Service Attributes";
  }

  identity LR-PMD-10G {
    base optical-interface-func;
    description
      "LR-PMD-clause-52 Optical Interface function for
       10GBASE-R PCS-49.";
    reference
      "IEEE Std 802.3-2022: IEEE Standard for Ethernet, Clause 52
       MEF 63: Subscriber Layer 1 Service Attributes";
  }

  identity ER-PMD-10G {
    base optical-interface-func;
    description
      "ER-PMD-clause-52 Optical Interface function for
       10GBASE-R PCS-49.";
    reference
      "IEEE Std 802.3-2022: IEEE Standard for Ethernet, Clause 52
       MEF 63: Subscriber Layer 1 Service Attributes";
  }

  identity LR4-PMD-40G {
    base optical-interface-func;
    description
      "LR4-PMD-clause-87 Optical Interface function for
       40GBASE-R PCS-82.";
    reference
      "IEEE Std 802.3-2022: IEEE Standard for Ethernet, Clause 87
       MEF 63: Subscriber Layer 1 Service Attributes";
  }

  identity ER4-PMD-40G {
    base optical-interface-func;
    description
      "ER4-PMD-clause-87 Optical Interface function for
       40GBASE-R PCS-82.";
    reference
      "IEEE Std 802.3-2022: IEEE Standard for Ethernet, Clause 87
       MEF 63: Subscriber Layer 1 Service Attributes";
  }

  identity FR-PMD-40G {
    base optical-interface-func;
    description
      "FR-PMD-clause-89 Optical Interface function for
       40GBASE-R PCS-82.";
    reference
      "IEEE Std 802.3-2022: IEEE Standard for Ethernet, Clause 89
       MEF 63: Subscriber Layer 1 Service Attributes";
  }

  identity LR4-PMD-100G {
    base optical-interface-func;
    description
      "LR4-PMD-clause-88 Optical Interface function for
       100GBASE-R PCS-82.";
    reference
      "IEEE Std 802.3-2022: IEEE Standard for Ethernet, Clause 88
       MEF 63: Subscriber Layer 1 Service Attributes";
  }

  identity ER4-PMD-100G {
    base optical-interface-func;
    description
      "ER4-PMD-clause-88 Optical Interface function for
       100GBASE-R PCS-82.";
    reference
      "IEEE Std 802.3-2022: IEEE Standard for Ethernet, Clause 88
       MEF 63: Subscriber Layer 1 Service Attributes";
  }

  /*
   * Typedefs
   */

  typedef otn-tpn {
    type uint16 {
      range "1..4095";
    }
    description
      "Tributary Port Number (TPN) for OTN.";
    reference
      "RFC 7139: GMPLS Signaling Extensions for Control of Evolving
                 G.709 Optical Transport Networks.";
  }

  typedef otn-ts {
    type uint16 {
      range "1..4095";
    }
    description
      "Tributary Slot (TS) for OTN.";
    reference
      "RFC 7139: GMPLS Signaling Extensions for Control of Evolving
                 G.709 Optical Transport Networks.";
  }

  typedef otn-label-range-type {
    type enumeration {
      enum trib-slot {
        description
          "Defines a range of OTN tributary slots (TS).";
      }
      enum trib-port {
        description
          "Defines a range of OTN tributary ports (TPN).";
      }
    }
    description
      "Defines the type of OTN label range: TS or TPN.";
  }

  typedef gfp-k {
    type enumeration {
      enum 2 {
        description
          "The ODU2.ts rate (1,249,177.230 kbit/s) is used
           to compute the rate of an ODUflex(GFP,n,2).";
      }
      enum 3 {
        description
          "The ODU3.ts rate (1,254,470.354 kbit/s) is used
           to compute the rate of an ODUflex(GFP,n,3).";
      }
      enum 4 {
        description
          "The ODU4.ts rate (1,301,467.133 kbit/s) is used
           to compute the rate of an ODUflex(GFP,n,4).";
      }
    }
    description
      "The ODUk.ts used to compute the rate of an ODUflex(GFP,n,k).";
    reference
      "ITU-T G.709 v6.0 (06/2020): Interfaces for the Optical
                 Transport Network (OTN), Tables 7-8 and L.7";
  }

  typedef flexe-client-rate {
    type union {
      type uint16;
      type enumeration {
        enum 10G {
          description
            "Represents a 10G FlexE Client signal (s=2).";
        }
        enum 40G {
          description
            "Represents a 40G FlexE Client signal (s=8).";
        }
      }
    }
    description
      "The FlexE Client signal rate (s x 5,156,250.000 kbit/s)
       used to compute the rate of an ODUflex(IMP, s).

       Valid values for s are s=2 (10G), s=4 (40G) and
       s=5 x n (n x 25G).

       In the first two cases an enumeration value
       (either 10G or 40G) is used, while in the latter case
       the value of n is used.";
    reference
      "ITU-T G.709 v6.0 (06/2020): Interfaces for the Optical
                 Transport Network (OTN), Table 7-2";
  }

  typedef odtu-flex-type {
    type enumeration {
      enum 2 {
        description
          "The ODTU2.ts ODTU type.";
      }
      enum 3 {
        description
          "The ODTU3.ts ODTU type.";
      }
      enum 4 {
        description
          "The ODTU4.ts ODTU type.";
      }
      enum Cn {
        description
          "The ODTUCn.ts ODTU type.";
      }
    }
    description
      "The type of Optical Data Tributary Unit (ODTU),
       whose nominal bitrate is used to compute the number of
       Tributary Slots (TS) required by an ODUflex LSP, according to
       the (19-1a) and (20-1a) formulas defined in G.709.";
    reference
      "ITU-T G.709 v6.0 (06/2020): Interfaces for the Optical
                 Transport Network (OTN), clauses 19.6 and 20.5,
                 and Table 7-7";
  }

  typedef bandwidth-scientific-notation {
    type string {
      pattern
        '0(\.0?)?([eE](\+)?0?)?|'
      + '[1-9](\.[0-9]{0,6})?[eE](\+)?(9[0-6]|[1-8][0-9]|0?[0-9])?';
    }
    units "bps";
    description
      "Bandwidth values, expressed using the scientific notation
       in bits per second.

       The encoding format is the external decimal-significant
       character sequences specified in IEEE 754 and
       ISO/IEC 9899 for 32-bit decimal floating-point numbers:
       (-1)**(S) * 10**(Exponent) * (Significant),
       where Significant uses 7 digits.

       An implementation for this representation MAY use decimal32
       or binary32. The range of the Exponent is from -95 to +96
       for decimal32, and from -38 to +38 for binary32.
       As a bandwidth value, the format is restricted to be
       normalized, non-negative, and non-fraction:
       n.dddddde{+}dd, N.DDDDDDE{+}DD, 0e0 or 0E0,
       where 'd' and 'D' are decimal digits; 'n' and 'N' are
       non-zero decimal digits; 'e' and 'E' indicate a power of ten.
       Some examples are 0e0, 1e10, and 9.953e9.";
    reference
      "IEEE Std 754-2019: IEEE Standard for Floating-Point
                 Arithmetic
       ISO/IEC 9899:2024: Information technology - Programming
                 Languages - C";
  }

  /*
   * Groupings
   */

  grouping otn-link-bandwidth {
    description
      "Bandwidth attributes for OTN links.";
    container otn-bandwidth {
      description
        "Bandwidth attributes for OTN links.";
      list odulist {
        key "odu-type";
        description
          "OTN bandwidth definition";
        leaf odu-type {
          type identityref {
            base odu-type;
          }
          description
            "ODU type";
        }
        leaf number {
          type uint16;
          description
            "Number of ODUs.";
        }
        leaf ts-number {
          when "derived-from-or-self(../odu-type,'l1-types:ODUflex')
                or derived-from-or-self(../odu-type,
                'l1-types:ODUflex-resizable')" {
            description
              "Applicable when odu-type is ODUflex or
               ODUflex-resizable.";
          }
          type uint16 {
            range "1..4095";
          }
          description
            "The number of Tributary Slots (TS) that
             could be used by all the ODUflex LSPs.";
        }
      }
    }
  }

  grouping otn-path-bandwidth {
    description
      "Bandwidth attributes for OTN paths.";
    container otn-bandwidth {
      description
        "Bandwidth attributes for OTN paths.";
      leaf odu-type {
        type identityref {
          base odu-type;
        }
        description
          "ODU type";
      }
      choice oduflex-type {
        when "derived-from-or-self(./odu-type,'l1-types:ODUflex')
              or derived-from-or-self(./odu-type,
              'l1-types:ODUflex-resizable')" {
          description
            "Applicable when odu-type is ODUflex or
             ODUflex-resizable.";
        }
        description
          "Types of ODUflex used to compute the ODUflex
           nominal bit rate.";
        reference
          "ITU-T G.709 v6.0 (06/2020): Interfaces for the Optical
                     Transport Network (OTN), Table 7-2";
        case generic {
          leaf nominal-bit-rate {
            type union {
              type l1-types:bandwidth-scientific-notation;
              type rt-types:bandwidth-ieee-float32;
            }
            mandatory true;
            description
              "Nominal ODUflex bit rate.";
          }
        }
        case cbr {
          leaf client-type {
            type identityref {
              base client-signal;
            }
            mandatory true;
            description
              "The type of Constant Bit Rate (CBR) client signal
               of an ODUflex(CBR).";
          }
        }
        case gfp-n-k {
          leaf gfp-n {
            type uint8 {
              range "1..80";
            }
            mandatory true;
            description
              "The value of n for an ODUflex(GFP,n,k).";
            reference
              "ITU-T G.709 v6.0 (06/2020): Interfaces for the
                         Optical Transport Network (OTN),
                         Tables 7-8 and L.7";
          }
          leaf gfp-k {
            type gfp-k;
            description
              "The value of k for an ODUflex(GFP,n,k).

               If omitted, it is calculated from the value of gfp-n
               as described in Table 7-8 of G.709.";
            reference
              "ITU-T G.709 v6.0 (06/2020): Interfaces for the
                         Optical Transport Network (OTN),
                         Tables 7-8 and L.7";
          }
        }
        case flexe-client {
          leaf flexe-client {
            type flexe-client-rate;
            mandatory true;
            description
              "The rate of the FlexE-client for an ODUflex(IMP,s).";
          }
        }
        case flexe-aware {
          leaf flexe-aware-n {
            type uint16;
            mandatory true;
            description
              "The rate of FlexE-aware client signal
               for ODUflex(FlexE-aware)";
          }
        }
        case packet {
          leaf opuflex-payload-rate {
            type union {
              type l1-types:bandwidth-scientific-notation;
              type rt-types:bandwidth-ieee-float32;
            }
            mandatory true;
            description
              "Either the GFP-F encapsulated packet client nominal
               bit rate for an ODUflex(GFP) or the 64b/66b encoded
               packet client nominal bit rate for an ODUflex(IMP).";
          }
        }
      }
    }
  }

  grouping otn-max-path-bandwidth {
    description
      "Maximum bandwidth attributes for OTN paths.";
    container otn-bandwidth {
      description
        "Maximum bandwidth attributes for OTN paths.";
      leaf odu-type {
        type identityref {
          base odu-type;
        }
        description
          "ODU type.";
      }
      leaf max-ts-number {
        when "derived-from-or-self(../odu-type,'l1-types:ODUflex')
              or derived-from-or-self(../odu-type,
              'l1-types:ODUflex-resizable')" {
          description
            "Applicable when odu-type is ODUflex or
             ODUflex-resizable.";
        }
        type uint16 {
          range "1..4095";
        }
        description
          "The maximum number of Tributary Slots (TS) that could be
           used by an ODUflex LSP.";
      }
    }
  }

  grouping otn-label-range-info {
    description
      "Label range information for OTN.

       This grouping SHOULD be used together with the
       otn-label-start-end and otn-label-step groupings to provide
       OTN technology-specific label information to the models which
       use the label-restriction-info grouping defined in the module
       ietf-te-types.";
    container otn-label-range {
      description
        "Label range information for OTN.";
      leaf range-type {
        type otn-label-range-type;
        description
          "The type of range (e.g., TPN or TS)
           to which the label range applies";
      }
      leaf tsg {
        type identityref {
          base tributary-slot-granularity;
        }
        description
          "Tributary slot granularity (TSG) to which the label range
           applies.

           This leaf MUST be present when the range-type is TS.

           This leaf MAY be omitted when mapping an ODUk over an OTUk
           Link. In this case the range-type is tpn, with only one
           entry (ODUk), and the tpn range has only one value (1).";
        reference
          "ITU-T G.709 v6.0 (06/2020): Interfaces for the Optical
                     Transport Network (OTN)";
      }
      leaf-list odu-type-list {
        type identityref {
          base odu-type;
        }
        description
          "List of ODU types to which the label range applies.

           An Empty odu-type-list means that the label range
           applies to all the supported ODU types.";
      }
      leaf priority {
        type uint8 {
          range "0..7";
        }
        description
          "Priority in Interface Switching Capability
           Descriptor (ISCD).";
        reference
          "RFC 4203: OSPF Extensions in Support of Generalized
                     Multi-Protocol Label Switching (GMPLS)";
      }
    }
  }

  grouping otn-label-start-end {
    description
      "The OTN label-start or label-end used to specify an OTN label
       range.

       This grouping is dependent on the range-type defined in the
       otn-label-range-info grouping.

       This grouping SHOULD be used together with the
       otn-label-range-info and otn-label-step groupings to provide
       OTN technology-specific label information to the models which
       use the label-restriction-info grouping defined in the module
       ietf-te-types.";
    container otn-label {
      description
        "Label start or label end for OTN.

         It is either a TPN or a TS depending on the OTN label range
         type specified in the 'range-type' leaf defined in the
         otn-label-range-info grouping.";
      leaf tpn {
        when "../../../../otn-label-range/range-type =
              'trib-port'" {
          description
            "Valid only when range-type represented by
             trib-port.";
        }
        type otn-tpn;
        description
          "Tributary Port Number (TPN).";
        reference
          "RFC 7139: GMPLS Signaling Extensions for Control of
                     Evolving G.709 Optical Transport Networks";
      }
      leaf ts {
        when "../../../../otn-label-range/range-type =
              'trib-slot'" {
          description
            "Valid only when range-type represented by
             trib-slot.";
        }
        type otn-ts;
        description
          "Tributary Slot (TS) number.";
        reference
          "RFC 7139: GMPLS Signaling Extensions for Control of
                     Evolving G.709 Optical Transport Networks";
      }
    }
  }

  grouping otn-label-hop {
    description
      "OTN Label";
    reference
      "RFC 7139: GMPLS Signaling Extensions for Control of Evolving
                 G.709 Optical Transport Networks, section 6";
    container otn-label {
      description
        "Label hop for OTN.";
      leaf tpn {
        type otn-tpn;
        description
          "Tributary Port Number (TPN).";
        reference
          "RFC 7139: GMPLS Signaling Extensions for Control of
                     Evolving G.709 Optical Transport Networks";
      }
      leaf tsg {
        type identityref {
          base tributary-slot-granularity;
        }
        description
          "Tributary Slot Granularity (TSG).";
        reference
          "ITU-T G.709 v6.0 (06/2020): Interfaces for the Optical
                     Transport Network (OTN)";
      }
      leaf ts-list {
        type string {
          pattern '([1-9][0-9]{0,3}(-[1-9][0-9]{0,3})?'
                + '(,[1-9][0-9]{0,3}(-[1-9][0-9]{0,3})?)*)';
        }
        description
          "A list of available Tributary Slots (TS) ranging
           between 1 and 4095. If multiple values or
           ranges are given, they all MUST be disjoint
           and MUST be in ascending order.
           For example 1-20,25,50-1000.";
        reference
          "RFC 7139: GMPLS Signaling Extensions for Control
                     of Evolving G.709 Optical Transport Networks";
      }
    }
  }

  grouping otn-label-step {
    description
      "Label step for OTN.

       This grouping is dependent on the range-type defined in the
       otn-label-range-info grouping.

       This grouping SHOULD be used together with the
       otn-label-range-info and otn-label-start-end groupings to
       provide OTN technology-specific label information to the
       models which use the label-restriction-info grouping defined
       in the module ietf-te-types.";
    container otn-label-step {
      description
        "Label step for OTN.

         It is either a TPN or a TS depending on the OTN label range
         type specified in the 'range-type' leaf defined in the
         otn-label-range-info grouping.";
      leaf tpn {
        when "../../../otn-label-range/range-type =
              'trib-port'" {
          description
            "Valid only when range-type represented by
             trib-port.";
        }
        type otn-tpn;
        description
          "Label step which represents possible increments for
           Tributary Port Number (TPN).";
        reference
          "RFC 7139: GMPLS Signaling Extensions for Control of
                     Evolving G.709 Optical Transport Networks";
      }
      leaf ts {
        when "../../../otn-label-range/range-type =
              'trib-slot'" {
          description
            "Valid only when range-type represented by
             trib-slot";
        }
        type otn-ts;
        description
          "Label step which represents possible increments for
           Tributary Slot (TS) number.";
        reference
          "RFC 7139: GMPLS Signaling Extensions for Control of
                     Evolving G.709 Optical Transport Networks";
      }
    }
  }
}
