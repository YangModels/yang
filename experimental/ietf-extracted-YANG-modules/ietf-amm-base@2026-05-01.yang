module ietf-amm-base {
  yang-version 1.1;
  namespace "ari://ietf/amm-base/";
  prefix amm-type;

  import ietf-amm {
    prefix amm;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module defines base IDENT objects and base TYPEDEF
     objects for the AMM.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2026-05-01 {
    description
      "Updated for latest ADM document.";
    reference
      "draft-ietf-dtn-adm-yang";
  }
  amm:enum 25;

  // abstract display hint hierarchy
  amm:ident display-hint {
    amm:enum 0;
    description
      "The base IDENT for objects usable as arguments for the
       'amm:display-hint' extension.
       This object itself provides no display hint purpose.";
    amm:abstract true;
  }
  amm:ident display-hint-integer {
    amm:enum 1;
    description
      "Intermediate base IDENT of display hints for integer values.
       Hints derived from this object SHALL only apply to built-in
       types BYTE, INT, UINT, VAST, and UVAST.";
    amm:abstract true;
    amm:base "./IDENT/display-hint";
  }
  amm:ident display-hint-float {
    amm:enum 2;
    description
      "Intermediate base IDENT of display hints for floating point
       values.
       Hints derived from this object SHALL only apply to built-in
       types REAL32 and REAL64.";
    amm:abstract true;
    amm:base "./IDENT/display-hint";
  }
  amm:ident display-hint-bstr {
    amm:enum 3;
    description
      "Intermediate base IDENT of display hints for byte string
       values.
       Hints derived from this object SHALL only apply to built-in
       type BYTESTR.";
    amm:abstract true;
    amm:base "./IDENT/display-hint";
  }
  amm:ident display-hint-time {
    amm:enum 4;
    description
      "Intermediate base IDENT of display hints for time values.
       Hints derived from this object SHALL only apply to built-in
       types TP and TD.";
    amm:abstract true;
    amm:base "./IDENT/display-hint";
  }

  // Named type unions
  amm:typedef type-ref {
    amm:enum 0;
    description
      "Reference to either a built-in type or a TYPEDEF object.";
    amm:union {
      amm:type "/ARITYPE/aritype";
      amm:type "/ARITYPE/typedef";
    }
  }
  amm:typedef integer {
    amm:enum 1;
    description
      "Any type which represents a discrete integer.
       This union order prefers smaller range and signed types.";
    amm:union {
      amm:type "/ARITYPE/byte";
      amm:type "/ARITYPE/int";
      amm:type "/ARITYPE/uint";
      amm:type "/ARITYPE/vast";
      amm:type "/ARITYPE/uvast";
    }
  }
  amm:typedef float {
    amm:enum 2;
    description
      "Any type which represents a floating point number.
       This union order prefers smaller range.";
    amm:union {
      amm:type "/ARITYPE/real32";
      amm:type "/ARITYPE/real64";
    }
  }
  amm:typedef numeric {
    amm:enum 3;
    description
      "Any type which can be used with numeric expressions.";
    amm:union {
      amm:type "./TYPEDEF/integer";
      amm:type "./TYPEDEF/float";
    }
  }
  amm:typedef numeric-or-time {
    amm:enum 27;
    description
      "Any type which can be used with numeric or time-as-numeric
       expressions.";
    amm:union {
      amm:type "./TYPEDEF/numeric";
      amm:type "./TYPEDEF/time";
    }
  }
  amm:typedef primitive {
    amm:enum 4;
    description
      "Any primitive type.
       This union order prefers conversion to wide types.";
    amm:union {
      amm:type "./TYPEDEF/numeric";
      amm:type "/ARITYPE/textstr";
      amm:type "/ARITYPE/bytestr";
      amm:type "/ARITYPE/bool";
      // null is last option for conversion
      amm:type "/ARITYPE/null";
    }
  }
  amm:typedef time {
    amm:enum 5;
    description
      "Any type which can be used with time expressions.";
    amm:union {
      amm:type "/ARITYPE/TP";
      amm:type "/ARITYPE/TD";
    }
  }
  amm:typedef simple {
    amm:enum 6;
    description
      "Any type which contains a single literal value (not nested).";
    amm:union {
      amm:type "./TYPEDEF/TIME";
      amm:type "./TYPEDEF/PRIMITIVE";
    }
  }
  amm:typedef nested {
    amm:enum 7;
    description
      "A literal type which contains other ARI values.";
    amm:union {
      amm:type "/ARITYPE/AC";
      amm:type "/ARITYPE/AM";
      amm:type "/ARITYPE/TBL";
    }
  }
  amm:typedef any {
    amm:enum 8;
    description
      "Any value representable by an ARI.";
    // These type names are built-in
    amm:union {
      amm:type "/ARITYPE/literal";
      amm:type "/ARITYPE/object";
      amm:type "/ARITYPE/namespace";
    }
  }
  amm:typedef value-obj {
    amm:enum 9;
    description
      "A reference to an object which can produce a value.";
    amm:union {
      amm:type "/ARITYPE/const";
      amm:type "/ARITYPE/edd";
      amm:type "/ARITYPE/var";
    }
  }
  amm:typedef nonce {
    amm:enum 10;
    description
      "This type union is used to correlate Agent-Manager messages.
       The union is defined in Section 4.2.5 of draft-ietf-dtn-amm.";
    reference
      "draft-ietf-dtn-amm";
    amm:union {
      amm:type "/ARITYPE/bytestr";
      amm:type "/ARITYPE/uvast";
      amm:type "/ARITYPE/null";
    }
  }
  amm:typedef id-text {
    amm:enum 25;
    description
      "This type is used to define and match object text names.
       The type is defined in Section 4.2.5 of draft-ietf-dtn-amm.";
    reference
      "draft-ietf-dtn-amm";
    amm:type "/ARITYPE/textstr" {
      pattern '!?[A-Za-z_][0-9A-Za-z_\-\.]*';
    }
  }
  amm:typedef id-int {
    amm:enum 26;
    description
      "This type is used to define and match object integer
       enumerations.
       The type is defined in Section 4.2.5 of draft-ietf-dtn-amm.";
    reference
      "draft-ietf-dtn-amm";
    amm:type "/ARITYPE/int";
  }

  // operational semantic types
  amm:typedef counter32 {
    amm:enum 11;
    description
      "A 32-bit counter with an arbitrary initial value which can
       only increment and never decrement.
       When the value reaches the upper limit of the type it wraps
       around to zero.
       At least two samples of this value need to be compared over
       time to be meaningful.
       This type is consistent with the SMIv2 and YANG data types
       of the same name.";
    reference
      "RFC 2578: Structure of Management Information Version 2
       RFC 6021: Common YANG Data Types";
    amm:type "/ARITYPE/uint";
  }
  amm:typedef counter64 {
    amm:enum 12;
    description
      "A 64-bit counter with an arbitrary initial value which can
       only increment and never decrement.
       When the value reaches the upper limit of the type it wraps
       around to zero.
       At least two samples of this value need to be compared over
       time to be meaningful.
       This type is consistent with the SMIv2 and YANG data types
       of the same name.";
    reference
      "RFC 2578: Structure of Management Information Version 2
       RFC 6021: Common YANG Data Types";
    amm:type "/ARITYPE/uvast";
  }
  amm:typedef gauge32 {
    amm:enum 13;
    description
      "A 32-bit value sampling some quantized measurement.
       The value can increase or decrease arbitrarily over time.
       This type is consistent with the SMIv2 and YANG data types
       of the same name.";
    reference
      "RFC 2578: Structure of Management Information Version 2
       RFC 6021: Common YANG Data Types";
    amm:type "/ARITYPE/int";
  }
  amm:typedef gauge64 {
    amm:enum 14;
    description
      "A 64-bit value sampling some quantized measurement.
       The value can increase or decrease arbitrarily over time.
       This type is consistent with the SMIv2 and YANG data types
       of the same name.";
    reference
      "RFC 2578: Structure of Management Information Version 2
       RFC 6021: Common YANG Data Types";
    amm:type "/ARITYPE/vast";
  }
  amm:typedef timestamp {
    amm:enum 15;
    description
      "A time point representing the system clock at which a specific
       occurrence happened.
       The specific occurrence must be defined in the description
       of any node defined using this type.
       This type is consistent with the SMIv2 and YANG data types
       of the same name.";
    reference
      "RFC 2579: Textual Conventions for SMIv2
       RFC 6021: Common YANG Data Types";
    amm:type "/ARITYPE/tp";
  }

  // Restrictions on AC item types for Evaluation and EXPR
  amm:typedef eval-tgt {
    amm:enum 16;
    description
      "A value which can be the target of an evaluation.
       An inline <./typedef/expr> value is evaluated directly.
       A reference to a value-producing object is dereferenced and
       SHALL produce a value that matches <./typedef/expr>, which
       is then evaluated.";
    amm:union {
      // object which produces an expression
      amm:type "./TYPEDEF/value-obj";
      // inline expression
      amm:type "./TYPEDEF/expr";
    }
  }
  amm:typedef expr-item {
    amm:enum 17;
    description
      "Each item of an EXPR list.";
    amm:union {
      // plain value for the stack
      amm:type "/ARITYPE/literal";
      // object which produces a value for the stack
      amm:type "./TYPEDEF/value-obj";
      // operator to evaluate
      amm:type "/ARITYPE/oper";
    }
  }
  amm:typedef expr {
    amm:enum 18;
    description
      "The contents of an EXPR container.";
    amm:ulist {
      amm:type "./TYPEDEF/expr-item";
    }
  }

  // Restrictions on AC item types for Execution and MAC
  amm:typedef exec-tgt {
    amm:enum 19;
    description
      "A value which can be the target of an execution.
       An inline <./typedef/mac> value is expanded and executed.
       A reference to a value-producing object is dereferenced and
       SHALL produce a value that matches <./typedef/exec-tgt>,
       which is then executed.
       A reference to a CTRL is executed directly.";
    amm:union {
      amm:type "./TYPEDEF/exec-item";
      // inline MAC
      amm:type "./TYPEDEF/mac";
    }
  }
  amm:typedef exec-item {
    amm:enum 20;
    description
      "A reference to an object which can be executed.
       The value-object must be typed to contain a
       <./typedef/exec-tgt>.";
    amm:union {
      amm:type "/ARITYPE/ctrl";
      // object which produces an exec-tgt
      amm:type "./TYPEDEF/value-obj";
    }
  }
  amm:typedef mac {
    amm:enum 21;
    description
      "The contents of a MAC container are an ordered list of
       executable values.";
    amm:ulist {
      amm:type "./TYPEDEF/exec-item";
    }
  }

  // Restrictions on AC item types for Reporting and RPTT
  amm:typedef rpt-tgt {
    amm:enum 22;
    description
      "A value which can be the target of reporting.";
    amm:union {
      // object which produces an RPTT
      amm:type "./TYPEDEF/value-obj";
      // inline RPTT
      amm:type "./TYPEDEF/rptt";
    }
  }
  amm:typedef rptt-item {
    amm:enum 23;
    description
      "Each item of a RPTT.
       Each item references a value-producing object or contains an
       expression to be evaluated.";
    amm:union {
      // produces the report item
      amm:type "./TYPEDEF/value-obj";
      // evaluates to the report item
      amm:type "./TYPEDEF/expr";
    }
  }
  amm:typedef rptt {
    amm:enum 24;
    description
      "The contents of a report template, encoded as the sequence
       of template items.";
    amm:ulist {
      amm:type "./TYPEDEF/rptt-item";
    }
  }
}
