module ietf-ucl-group {
  yang-version 1.1;
  namespace "urn:ietf:params:xml:ns:yang:ietf-ucl-group";
  prefix uclg;

  import ietf-yang-types {
    prefix yang;
    reference
      "RFC 6991: Common YANG Data Types, Section 3";
  }
  import ietf-inet-types {
    prefix inet;
    reference
      "RFC 6991: Common YANG Data Types, Section 4";
  }

  organization
    "IETF OPSAWG Working Group";
  contact
    "WG Web: <https://datatracker.ietf.org/wg/opsawg/>
     WG List: <mailto:opsawg@ietf.org>";
  description
    "This YANG module defines XXX.

     Copyright (c) 2022 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2022-10-14 {
    description
      "Initial revision.";
    reference
      "RFC XXXX: A Policy-based Network Access Control";
  }

  identity device-type {
    description
      "Base identity for device type.";
  }

  identity role-type {
    description
      "Identity for role group type.";
  }

  identity smartphone {
    base device-type;
    description
      "Identity for the smartphone terminal device.";
  }

  identity tablet {
    base device-type;
    description
      "Identity for the tablet accessed device.";
  }

  identity laptop {
    base device-type;
    description
      "Identity for the laptop accessed device.";
  }

  identity pc {
    base device-type;
    description
      "Identity for the PC accessed device.";
  }

  identity finance {
    base role-type;
    description
      "Identity for the finance role.";
  }

  identity sales {
    base role-type;
    description
      "Identity for the sales role.";
  }

  identity research {
    base role-type;
    description
      "Identity for the research role.";
  }

  identity developer {
    base role-type;
    description
      "Identity for the developer role.";
  }

  identity vip {
    base role-type;
    description
      "Identity for the VIP role.";
  }

  identity visitor {
    base role-type;
    description
      "Identity for the guest role.";
  }

  container ucl-groups {
    description
      "Defines the UCL groups";
    list user-group {
      key "group-id";
      description
        "The user group with which the traffic flow is
         associated can be identified by a user-group id.";
      leaf group-id {
        type uint32;
        description
          "The ID of the group which is used to
           identified a user group. This identifier is
           unique within the scope of a network.";
      }
      leaf role {
        type identityref {
          base role-type;
        }
        description
          "The common role of this user-group.";
      }
      list user {
        key "user-name";
        description
          "List of users indexed by their user-name.";
        leaf user-name {
          type string {
            length "1..max";
          }
          description
            "A special name given to a user to uniquely identify them.";
        }
        container address-grouping-mapping {
          description
            "Defines lists of IP and MAC addresses.";
          list address {
            key "address-id";
            description
              "The possible accessed address of the user, identified
               by the address-id.";
            leaf address-id {
              type uint32;
              description
                "A unique address-id that identifies a user's accessed
                 address.";
            }
            leaf ipv4-address {
              type inet:ipv4-prefix;
              description
                "The IPv4 address prefix of the user's accessed IP.";
            }
            leaf ipv6-address {
              type inet:ipv6-prefix;
              description
                "The IPv6 address prefix of the user's accessed IP.";
            }
            leaf mac-address {
              type yang:mac-address;
              description
                "The mac address of the user's accessed device.";
            }
          }
        }
        container access-locations {
          description
            "Defines lists of locations.";
          list location {
            key "location-id";
            description
             "List of locations.";
            leaf location-id {
              type string {
                length "1..max";
              }
              description
                "Location id information.";
            }
            leaf address {
              type string;
              description
                "User detailed address information.";
            }
            leaf postal-code {
              type string;
              description
                "Postal code information of the user's
                 accessed location.";
            }
          }
        }
        leaf accessed-devices {
          type identityref {
            base device-type;
          }
          description
            "The user's accessed device type.";
        }
        leaf start-time {
          type yang:date-and-time;
          description
            "The start time that the user belongs to
             this group ID.";
        }
        leaf end-time {
          type yang:date-and-time;
          description
            "The end time that the user belongs to
             this group ID.";
        }
      }
    }
  }
}
