module   ietf-wson-topology {
      yang-version 1.1;

      namespace "urn:ietf:params:xml:ns:yang:ietf-wson-topology";

      prefix "wson";

       import ietf-network {
          prefix "nd";
       }

      import ietf-network-topology {
        prefix "lnk";
      }

      import ietf-inet-types {
      prefix "inet";
      }
      import ietf-te-topology {
      prefix "tet";
      }

      organization
            "IETF CCAMP Working Group";

      contact
            "Editor:   Young Lee  <leeyoung@huawei.com>";

      description
            "This module contains a collection of YANG definitions for
            RWA WSON.

            Copyright (c) 2016 IETF Trust and the persons identified as
            authors of the code.  All rights reserved.

            Redistribution and use in source and binary forms, with or
            without modification, is permitted pursuant to, and subject
            to the license terms contained in, the Simplified BSD
            License set forth in Section 4.c of the IETF Trust's Legal
            Provisions Relating to IETF Documents
            (http://trustee.ietf.org/license-info).";

      revision 2017-07-03 {
            description
                  "version 7.";

            reference
                  "RFC XXX: A Yang Data Model for WSON Optical Networks ";
      }

      typedef wson-topology-id {
            type inet:uri;
            description
                  "The WSON Topology ID";
      }

      typedef wson-node-id {
            type inet:ip-address;
            description
                  "The WSON Node ID";
      }

      typedef devicetype {
            type enumeration {
                  enum adm {
                        value 1;
                        description
                              "Device is ADM";
                  }

                  enum roadm {
                        value 2;
                        description
                              "Device is ROAMD/OXC";
                  }
            }
            description
                  "device type: fixed (ADM) or switched (ROADM/OXC)";
      }

      typedef directionality {
            type enumeration {
                  enum bidir {
                        value 0;
                        description
                              "bi-directional";
                  }
                  enum input {
                        value 1;
                        description
                              "input direction";
                  }
                  enum output {
                        value 2;
                        description
                              "output direction";
                  }
            }
            description
                  "The directionality of link set";
      }

      typedef wson-interface-ref {
            type leafref {
                path "/nd:networks/nd:network/nd:node/tet:te/"
                  + "tet:te-node-attributes/wson:wson-node/"
                  + "wson:interfaces/wson:name";
            }
            description
                  "This type is used by data models that need to
                  reference WSON interface.";
      }

      grouping wson-topology-type {
            description "wson-topology type";
            container wson-topology {
                  presence "indicates a topology of wson";
                  description
                        "Container to identify wson topology type";
                  }
      }

      grouping wson-node-attributes {
            description "wson node attributes";
            container wson-node {
                  description "WSON node attrtibutes.";
                  leaf device-type {
                        type devicetype;
                        description
                              "device type: fixed (ADM) or switched
                              (ROADM/OXC)";
                  }
                  leaf dir {
                        type directionality;
                        description
                              "bi-directionality or input or output
                              of link set";
                  }
                  list interfaces {
                 key "name";
                unique "port-number"; // TODO Puerto y TP ID
                description "List of interfaces contained in the node";
                uses node-interface;
                  }
            }
      }

      grouping node-interface {
          description "node interface definition";
        leaf name {
           type string;
           description "Interface name";
        }
        leaf port-number {
           type uint32;
           description "Number of the port used by the interface";
        }
        leaf input-port {
           type boolean;
           description "Determines if the port is an input port";
        }
        leaf output-port {
           type boolean;
           description
           "Determines if the port is an output port";
        }
        leaf description {
           type string;
           description "Description of the interface";
        }
      }

      grouping available-wavelength {
            description "describe available wavelengths";
            leaf-list wavelength-available-bitmap {
                  type binary;
                  description
                        "array of bits (i.e., bitmap) that indicates
                        if a wavelength is available or not on each
                        channel.";
            }
      }

      grouping wson-link-attributes {
            description "Set of WSON link attributes";
                  leaf channel-max {
                        type int32;
                        description "Maximum Number of OCh channels available
by the node";
                  }
                  leaf default-frequency {
                        type decimal64 {
                              fraction-digits 5;
                        }
                        units THz;
                        default 193.1;
                        description "Default Central Frequency";
                  }
                  leaf channel-spacing {
                        type decimal64 {
                              fraction-digits 5;
                        }
                        units GHz;
                        description "This is fixed channel spacing for WSON,
e.g, 12.5, 25, 50, 100, ..";
                  }
      }

      grouping wson-connectivity-matrix {
            description "wson connectivity matrix";
            list matrix-interface {
                        key "in-port-id";

                        description
                              "matrix-interface describes input-ports
                              and out-ports around a connectivity
                              matrix";

                        leaf in-port-id {
                              type wson-interface-ref;
                              description
                                    "The reference to in-port";
                        }

                        leaf out-port-id {
                              type wson-interface-ref;
                              description
                                    "The reference to out-port";
                        }
            }
      }

      grouping resource-pool-attributes {
            description "resource pool describes regeneration or wave converter";
            list resource-pool {
                  key "resource-pool-id";
                  description
                        "The resource pool list";

                  leaf resource-pool-id {
                        type uint32;
                        description
                              "The resource pool ID";
                  }

                  leaf pool-state {
                        type boolean;
                        description
                              "TRUE is state UP; FALSE is state down";
                  }

                  uses wson-connectivity-matrix;
            }
      }

      augment "/nd:networks/nd:network/nd:network-types" {
            description "wson-topology augmented";
            uses wson-topology-type;
      }

      augment "/nd:networks/nd:network/nd:node/tet:te"
              + "/tet:te-node-attributes/tet:connectivity-matrices"
              + "/tet:connectivity-matrix" {
            when "/nd:networks/nd:network/nd:network-types"
                  +"/wson-topology" {
                  description
                        "This augment is only valid for
                        WSON connectivity matrix.";
          }
          description "WSON connectivity matrix state augmentation";
            uses wson-connectivity-matrix;
      }

      augment "/nd:networks/nd:network/lnk:link/tet:te"
                  + "/tet:te-link-attributes"   {
        when "/nd:networks/nd:network/nd:network-types"
                  +"/wson-topology" {
                  description
                        "This augment is only valid for WSON.";
            }
            description "WSON Link augmentation.";

            uses wson-link-attributes;
            uses available-wavelength;
      }

      augment "/nd:networks/nd:network/nd:node/tet:te"
              + "/tet:te-node-attributes" {
            when "/nd:networks/nd:network/nd:network-types"
                  +"/wson-topology" {
                  description
                        "This augment is only valid for WSON.";
            }
            description "WSON Node augmentation.";

            uses wson-node-attributes;
            uses resource-pool-attributes;
      }

}
