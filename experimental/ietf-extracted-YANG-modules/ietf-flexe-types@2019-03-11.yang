module ietf-flexe-types {
  yang-version 1.1;
  namespace "urn:ietf:params:xml:ns:yang:ietf-flexe-types";
  prefix "flexe-tp";
  import ietf-routing-types {
    prefix rt-types;
    description "Import ietf-routing-types module.";
  }
  organization
    "Internet Engineering Task Force (IETF) CCAMP WG";
  contact
    "WG List: <mailto:ccamp@ietf.org>
     Editor:  Xiaobing Niu (niu.xiaobing@zte.com.cn);
     Editor:  Qilei Wang (wang.qilei@zte.com.cn); ";
  description
    "This module defines a YANG data types used in FlexE YANG modules.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents(http://trustee.ietf.org/license-info).

     This version of this YANG module is part of RFC TBD; see
     the RFC itself for full legal notices.     ";

  revision 2019-03-11{
    description
      "Initial version.";
    reference
      "draft-xiaobn-ccamp-flexe-yang-mod-00.txt";
  }

  /* typedefs */
  typedef cal-slot-gran {
    type enumeration {
      enum csg-5G {
        value 1;
        description "Calendar slot with a 5G granularity";
      }
      enum csg-25G {
        value 2;
        description "Calendar slot with a 25G granularity";
      }
    }
    description
      "Defines a type representing the granularity of a calendar slot.";
  }

  typedef flexe-client-signal-rate {
    type enumeration {
      enum flexe-client-signal-10Gbps{
        value 1;
        description
          "FlexE Client signal rate of 10Gbps";
      }
      enum flexe-client-signal-40Gbps{
        value 2;
        description
          "FlexE Client signal rate of 40Gbps";
      }
      enum flexe-client-signal-25mGbps{
        value 3;
        description
          "FlexE Client signal rate of m*25Gbps";
      }
    }
    description
      "Defines FlexE Client signal rate, including 10, 40, m*25Gbps.";
  }
  typedef flexe-phy-type {
    type enumeration {
      enum flexe-phy-100GBASE-R {
        value 1;
        description "100GBASE-R PHY";
      }
      enum flexe-phy-200GBASE-R {
        value 2;
        description "200GBASE-R PHY";
      }
      enum flexe-phy-400GBASE-R {
        value 3;
        description "400GBASE-R PHY";
      }
    }
    description
      "Defines types of PHYs in a FlexE group";
  }
  typedef calendar-AorB {
    type enumeration {
      enum calendar-A {
        value 0 ;
        description
          "Set the A calendar configuration.";
      }
      enum calendar-B {
        value 1 ;
        description
          "Set the B calendar configuration.";
      }
    }
    description
      "Calendar configuration A or B";
  }
  /* interface states: OK, SF, SD */
  typedef intf-state {
    type enumeration {
      enum ok {
        value 0 ;
        description
          "The interface state of the FlexE Group is OK.";
      }
      enum sf {
        value 1 ;
        description
          "The interface state of the FlexE Group is SF."      ;
      }
      enum sd {
        value 2 ;
        description
          "The interface state of the FlexE Group is SD.";
      }
    }
    description
      "Interface state of port group.";
  }
  /* grouping */
  grouping flexe-client-bandwidth{
    leaf signal-type{
      type flexe-client-signal-rate;
      description
        "Client signal types: 10, 40, m*25 Gbps.";
    }
    leaf mac-rate {
      type rt-types:bandwidth-ieee-float32;
        description
          "Bandwidth of clients.";
    }
    description
      "The bandwidth of a FlexE client.";
  }
}
