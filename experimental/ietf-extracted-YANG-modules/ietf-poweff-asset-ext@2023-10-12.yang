module ietf-poweff-asset-ext {
  yang-version 1.1;
  namespace "urn:ietf:params:xml:ns:yang:ietf-poweff-asset-ext";
  prefix ietf-poweff-asset-ext;
  import ietf-lmo {
    prefix ietf-lmo;
  }
  import ietf-lmo-assets {
    prefix ietf-lmo-asset;
  }
  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module includes extra attributes which
     complement sustainability for assets.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";

  revision 2023-10-12 {
    description
      "Initial revision to complement Asset Inventory Module as
       part of the DMALMO YANG Model, with sustainability attributes";
    reference
      "RFC XXXX: DMALMO YANG Model";
  }

  augment /ietf-lmo:lmos/ietf-lmo:lmo/ietf-lmo:inst {
    when "derived-from-or-self(../ietf-lmo:lmo-class, "+
         " 'ietf-lmo-asset:asset')";
    description
      "Assets attributes related to sustainability";
    leaf age {
      type string;
      description
        "Age of the asset";
    }
    leaf site {
      when "not(../ietf-lmo:parent/ietf-lmo:id)";
    type string;
    description
      "location site name";
      // FIXME: Make this a reference to a list of sites?
      // FIXME: force this to be set for all assets that
      //        do not have a parent?
    }
    leaf modular {
      type boolean;
      description
        "The asset is or is not modular";
    }
    leaf status {
      type string;
      description
        "NEED to include: off, enabled, disabled, not present,
         failed, reserved-on, standby";
         //FIXME status is simply the most inconsistent field
         //with wide variety of values reported. It is better
         //to make this a Enum with fixed set list of states.
    }
    leaf slot {
      type string;
      mandatory "true";
      description
        "Defines the slot where the asset is placed in the chasssis.
        Used to map the sensor to particular UID.";
    }
    leaf device-family {
      type string;
      description
        "Device Family - may be derived from the product name or
         product id. It is to be used for immplementation
         purpose - filtering capability and future optimization
         purposes";
    }
  }
}
