module ietf-loopback {
  yang-version 1.1;
  namespace "urn:ietf:params:xml:ns:yang:ietf-loopback";
  prefix loopback;

  import ietf-interfaces {
    prefix if;
  }

  organization
    "IETF Benchmarking Methodology Working Group";
  contact
    "WG Web:   <http://tools.ietf.org/wg/bmwg/>
     WG List:  <mailto:bmwg@ietf.org>

     Editor:   Vladimir Vassilev
               <mailto:vladimir@transpacket.com>";
  description
    "This module contains a collection of YANG definitions for
     description and management of network interconnect testers.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2019-03-09 {
    description
      "Initial revision.";
    reference "RFC XXXX: Network Interconnect Tester";
  }
  identity loopback {
    description
      "Base loopback identity.";
  }

  identity near-end {
    base loopback;
    description
      "Identifies loopback mode where all local egress
       packets are looped back as ingress packets.";
  }

  identity far-end {
    base loopback;
    description
      "Identifies loopback mode where all remote ingress
       packets are looped back as egress packets.";
  }

  augment "/if:interfaces/if:interface" {
    leaf loopback {
      type identityref {
        base loopback;
      }
    }
  }
}
