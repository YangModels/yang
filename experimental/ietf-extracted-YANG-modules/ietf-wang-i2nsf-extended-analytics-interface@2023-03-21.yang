module ietf-wang-i2nsf-extended-analytics-interface {
  yang-version 1.1;
  namespace
    "urn:ietf:params:xml:ns:yang:wang-i2nsf-extension-
     analytics-interface";
  prefix i2nsf-exai;
  import ietf-inet-types {
    prefix inet;
    reference "RFC6991";
  }
  import ietf-yang-types {
     prefix yang;
     reference "RFC6991";
 }
 organization
   "IETF I2NSF (Interface to Network Security Functions)
    Working Group";
 contact
   "WG Web: <https://datatracker.ietf.org/wg/i2nsf>
    WG List: <mailto:i2nsf@ietf.org>
      Author: Weilin Wang
      <mailto:21111026@bjtu.edu.cn>
      Author: Qi Guo
      <mailto:20120044@bjtu.edu.cn>
      Author: Shuangxing Deng
      <mailto:21120038@bjtu.edu.cn>";
 description
   "This module is a YANG module for the extension of I2NSF
    Analytics Interface.
      The key words 'MUST', 'MUST NOT', 'REQUIRED', 'SHALL',
      'SHALL NOT', 'SHOULD', 'SHOULD NOT', 'RECOMMENDED',
      'NOT RECOMMENDED', 'MAY', and 'OPTIONAL' in this
      document are to be interpreted as described in BCP 14
      (RFC 2119) (RFC 8174) when, and only when, they appear
      in all capitals, as shown here.
      Copyright (c) 2022 IETF Trust and the persons identified as
      authors of the code. All rights reserved.
      Redistribution and use in source and binary forms, with or
      without modification, is permitted pursuant to, and subject
      to the license terms contained in, the Revised BSD License
      set forth in Section 4.c of the IETF Trust's
      Legal Provisions Relating to IETF Documents
      (https://trustee.ietf.org/license-info).
      This version of this YANG module is part of RFC XXXX
      (https://www.rfc-editor.org/info/rfcXXXX); see the RFC itself
      for full legal notices.";
 revision "2023-03-21"{
   description "Initial revision.";
   reference
     "RFC XXXX: Extension of I2NSF NSF Analytics Interface
      YANG Data Model";
 }
/*
 *Identity
 */
   identity protocol {
     description
       "An identity used to enable type choices in leaves
       and leaf-lists with respect to protocol metadata. This is used
       to identify the type of protocol that goes through the NSF.";
   }
   identity ip {
     base protocol;
     description
       "General IP protocol type.";
     reference
       "RFC0791: Internet Protocol
        RFC8200: Internet Protocol, Version 6 (IPv6)";
   }
   identity ipv4 {
     base ip;
     description
       "IPv4 protocol type.";
     reference
       "RFC0791: Internet Protocol";
   }
   identity ipv6 {
     base ip;
     description
       "IPv6 protocol type.";
     reference
       "RFC8200: Internet Protocol, Version 6 (IPv6)";
   }
   identity icmp {
     base protocol;
     description
       "Base identity for ICMPv4 and ICMPv6 condition capability";
     reference
       "RFC0792: Internet Control Message Protocol
        RFC4443: Internet Control Message Protocol (ICMPv6)
        for the Internet Protocol Version 6 (IPv6) Specification
        - ICMPv6";
   }
   identity icmpv4 {
     base icmp;
     description
       "ICMPv4 protocol type.";
     reference
      "RFC0791: Internet Protocol
       RFC0792: Internet Control Message Protocol";
  }
  identity icmpv6 {
    base icmp;
    description
      "ICMPv6 protocol type.";
    reference
      "RFC8200: Internet Protocol, Version 6 (IPv6)
       RFC4443: Internet Control Message Protocol (ICMPv6)
       for the Internet Protocol Version 6 (IPv6)
       Specification";
  }
  identity transport-protocol {
    base protocol;
    description
      "Base identity for Layer 4 protocol condition
      capabilities, e.g., TCP, UDP, SCTP, DCCP, and ICMP.";
  }
  identity tcp {
    base transport-protocol;
    description
      "TCP protocol type.";
    reference
      "[RFC9293]: Transmission
       Control Protocol (TCP).";
  }
  identity udp {
    base transport-protocol;
    description
      "UDP protocol type.";
    reference
      "RFC0768: User Datagram Protocol";
  }
  identity sctp {
    base transport-protocol;
    description
      "Identity for SCTP condition capabilities";
    reference
      "RFC9260: Stream
       Control Transmission Protocol";
  }
  identity dccp {
    base transport-protocol;
    description
      "Identity for DCCP condition capabilities";
    reference
      "RFC4340: Datagram Congestion Control Protocol";
  }
  identity application-protocol {
    base protocol;
    description
      "Base identity for Application protocol. Note
       that a subset of application protocols (e.g.,
       HTTP, HTTPS, FTP, POP3, and IMAP) are handled
       in this YANG module, rather than all the
       existing application protocols.";
  }
  identity http {
    base application-protocol;
    description
      "The identity for Hypertext Transfer Protocol
       version 1.1 (HTTP/1.1).";
    reference
      "[RFC9110]: HTTP Semantics
       [RFC9112]: HTTP/1.1";
  }
  identity https {
    base application-protocol;
    description
      "The identity for Hypertext Transfer Protocol
      version 1.1 (HTTP/1.1) over TLS.";
    reference
      "[RFC9110]: HTTP Semantics
       [RFC9112]: HTTP/1.1";
  }
  identity http2 {
    base application-protocol;
    description
      "The identity for Hypertext Transfer Protocol
      version 2 (HTTP/2).";
    reference
      "RFC9113: HTTP/2";
  }
  identity https2 {
    base application-protocol;
    description
      "The identity for Hypertext Transfer Protocol
      version 2 (HTTP/2) over TLS.";
    reference
      "RFC9113: HTTP/2";
  }
  identity ftp {
    base application-protocol;
    description
      "FTP protocol type.";
    reference
      "RFC 0959: File Transfer Protocol";
  }
  identity ssh {
    base application-protocol;
    description
      "SSH protocol type.";
    reference
      "RFC6242: Using the NETCONF Protocol over
       Secure Shell (SSH)";
  }
  identity telnet {
    base application-protocol;
    description
      "The identity for telnet.";
    reference
      "RFC 0854: Telnet Protocol";
  }
  identity smtp {
    base application-protocol;
    description
      "The identity for smtp.";
    reference
      "RFC 5321: Simple Mail Transfer
       Protocol (SMTP)";
  }
  identity pop3 {
    base application-protocol;
    description
      "The identity for Post Office
       Protocol 3 (POP3).";
    reference
      "RFC1939: Post Office Protocol
       - Version 3 (POP3)";
  }
  identity pop3s {
    base application-protocol;
    description
      "The identity for Post Office Protocol
       3 (POP3) over TLS";
    reference
      "RFC1939: Post Office Protocol
       - Version 3 (POP3)
      RFC2595: Using TLS with IMAP, POP3 and ACAP";
  }
  identity imap {
    base application-protocol;
    description
      "The identity for Internet Message Access
       Protocol (IMAP).";
    reference
      "RFC9051: Internet Message Access Protocol
       (IMAP) - Version 4rev2";
  }
  identity imaps {
    base application-protocol;
    description
      "The identity for Internet Message Access
       Protocol (IMAP) over TLS";
    reference
      "RFC9051: Internet Message Access Protocol
                 (IMAP) - Version 4rev2
       RFC2595: Using TLS with IMAP, POP3 and ACAP";
  }
/*
 *Grouping
 */
  grouping message {
    description
      "A set of common monitoring data that is needed
      as the basic information.";
    leaf message {
      type string;
      description
        "This is a free text annotation for
        monitoring a notification's content.";
    }
    leaf language {
      type string {
        pattern '((([A-Za-z]{2,3}(-[A-Za-z]{3}(-[A-Za-z]{3})'
          + '{0,2})?)|[A-Za-z]{4}|[A-Za-z]{5,8})(-[A-Za-z]{4})?'
          + '(-([A-Za-z]{2}|[0-9]{3}))?(-([A-Za-z0-9]{5,8}'
          + '|([0-9][A-Za-z0-9]{3})))*(-[0-9A-WYZa-wyz]'
          + '(-([A-Za-z0-9]{2,8}))+)*(-[Xx](-([A-Za-z0-9]'
          + '{1,8}))+)?|[Xx](-([A-Za-z0-9]{1,8}))+|'
          + '(([Ee][Nn]-[Gg][Bb]-[Oo][Ee][Dd]|[Ii]-'
          + '[Aa][Mm][Ii]|[Ii]-[Bb][Nn][Nn]|[Ii]-'
          + '[Dd][Ee][Ff][Aa][Uu][Ll][Tt]|[Ii]-'
          + '[Ee][Nn][Oo][Cc][Hh][Ii][Aa][Nn]'
          + '|[Ii]-[Hh][Aa][Kk]|'
          + '[Ii]-[Kk][Ll][Ii][Nn][Gg][Oo][Nn]|'
          + '[Ii]-[Ll][Uu][Xx]|[Ii]-[Mm][Ii][Nn][Gg][Oo]|'
          + '[Ii]-[Nn][Aa][Vv][Aa][Jj][Oo]|[Ii]-[Pp][Ww][Nn]|'
          + '[Ii]-[Tt][Aa][Oo]|[Ii]-[Tt][Aa][Yy]|'
          + '[Ii]-[Tt][Ss][Uu]|[Ss][Gg][Nn]-[Bb][Ee]-[Ff][Rr]|'
          + '[Ss][Gg][Nn]-[Bb][Ee]-[Nn][Ll]|[Ss][Gg][Nn]-'
          + '[Cc][Hh]-[Dd][Ee])|([Aa][Rr][Tt]-'
          + '[Ll][Oo][Jj][Bb][Aa][Nn]|[Cc][Ee][Ll]-'
          +   '[Gg][Aa][Uu][Ll][Ii][Ss][Hh]|'
          +   '[Nn][Oo]-[Bb][Oo][Kk]|[Nn][Oo]-'
          +   '[Nn][Yy][Nn]|[Zz][Hh]-[Gg][Uu][Oo][Yy][Uu]|'
          +   '[Zz][Hh]-[Hh][Aa][Kk][Kk][Aa]|[Zz][Hh]-'
          +   '[Mm][Ii][Nn]|[Zz][Hh]-[Mm][Ii][Nn]-'
          +   '[Nn][Aa][Nn]|[Zz][Hh]-[Xx][Ii][Aa][Nn][Gg])))';
      }
      default "en-US";
      description
        "The value in this field indicates the language tag
        used for the human readable fields (i.e., '../message',
        '/i2nsf-log/i2nsf-nsf-system-access-log/output', and
        '/i2nsf-log/i2nsf-system-user-activity-log/additional-info
        /cause').
        The attribute is encoded following the rules in Section 2.1
        in RFC5646. The default language tag is 'en-US'";
      reference
        "RFC5646: Tags for Identifying Languages.";
    }
  }
  grouping attack-rates {
    description
      "A set of traffic rates for monitoring
       attack traffic data.";
    leaf attack-rate {
      type uint64;
      units "pps";
      description
        "The average packets per second (pps)
         rate of attack traffic";
    }
    leaf attack-throughput {
      type uint64;
      units "Bps";
      description
        "The average bytes per second (Bps)
         throughput of attack traffic";
    }
  }
  list i2nsf-feedback-information {
    key time-stamp;
    description
      "Feedback information includes system
       feedback information about resources
        and NSF feedback information.";
    leaf time-stamp {
      type yang:date-and-time;
      description
      "Specify the time of the information
       being delivered.";
    }
    uses message;
    container system-feedback-information {
      description
        "The resources alarm about CPU, memory,
          disks or interfaces will be sent to
          I2NSF security controller.";
      choice alarm-type {
        description
           "The alarm type.";
        case memory-alarm {
           container memory-alarm {
             description
               "The container for memory alarm.";
             leaf usage {
               type uint8 {
                  range "0..100";
               }
               units "percent";
               description
                  "The average usage for the duration
                   of the alarm.";
             }
             leaf duration {
               type uint32;
               description
                  "Specify the duration of the first
                   alarm triggered until the feedback
                   information is created.";
             }
           }
        }
        case cpu-alarm {
           container cpu-alarm {
             description
               "The case for CPU alarm.";
             leaf usage {
               type uint8 {
                  range "0..100";
               }
               units "percent";
               description
                 "The average usage for the duration
                  of the alarm.";
             }
             leaf duration {
               type uint32;
                     description
                       "Specify the duration of the first
                        alarm triggered until the feedback
                        information is created.";
                 }
             }
        }
        case disk-alarm {
          container disk-alarm {
            description
              "The container for disk alarm.";
            leaf disk-id {
              type string;
              description
                "The ID of the storage disk. It is
                 free form identifier to identify
                 the storage disk.";
            }
            leaf usage {
              type uint8 {
                range "0..100";
              }
              units "percent";
              description
                "The average usage for the duration
                 of the alarm.";
            }
            leaf duration {
              type uint32;
              description
                "Specify the duration of the first
                 alarm triggered until the feedback
                 information is created.";
            }
          }
        }
        case interface-alarm {
          container interface-alarm {
            description
              "The container for interface alarm.";
            leaf interface-id {
              type string;
              description
                "The ID of the network interface. It is
                 a free form identifier to identify
                 the network interface.";
            }
            leaf interface-state {
              type enumeration {
                 enum up {
                   value 1;
                   description
                     "The interface state is up and
                      not congested. The interface is ready to
                      pass packets.";
                 }
                 enum down {
                   value 2;
                   description
                     "The interface state is down, i.e.,
                     does not pass any packets.";
                 }
                 enum congested {
                   value 3;
                   description
                     "The interface state is up but
                      congested.";
                 }
                 enum testing {
                   value 4;
                   description
                     "In some test mode. No operational
                      packets can be passed.";
                 }
                 enum unknown {
                   value 5;
                   description
                     "Status cannot be determined for
                      some reason.";
                 }
                 enum dormant {
                   value 6;
                   description
                     "Waiting for some external event.";
                 }
                 enum not-present {
                   value 7;
                   description
                     "Some component (typically hardware) is
                      missing.";
                 }
                 enum lower-layer-down {
                   value 8;
                   description
                     "Down due to state of lower-layer
                      interface(s).";
                 }
             }
                   description
                     "The state of the interface. Applicable
                      for Network Interface Failure Alarm.";
                   reference
                     "RFC 8343: A YANG Data Model for Interface
                      Management- Operational States";
                 }
                 leaf duration {
                   type uint32;
                   description
                     "Specify the duration of the first
                      alarm triggered until the feedback
                      information is created.";
                 }
             }
        }
      }
    }
    container nsf-feedback-information {
      description
        "The output of NSFs will be sent to the I2NSF
         security controller.";
      choice nsf-type {
        description
          "The NSF type.";
        case detection-module {
          container detection-module{
            description
              "The container for the detection
               module.";
            leaf detection-module-name {
              type string;
              description
                "The name of the specific
                  detection module.";
            }
            container detected-attacks {
              description
                "The information of detected attacks.";
              list attack-traffic{
                key attack-id;
                description
                "The five-tuple (src/dst ip, port and
                  protocol) and attack type information
                  of specific attack traffic.";
                leaf attack-id {
                   type string;
                   description
                   "The ID of the specific attack traffic
                      which has the same src/dst ip,
                      protocol and attack type.";
                   }
                   leaf attack-type {
                     type string;
                     description
                     "The type of the detected attack.";
                   }
                   leaf attack-src-ip {
                     type inet:ip-address-no-zone;
                     description
                       "The source IPv4 or IPv6 addresses
                        of attack traffic. It can hold
                        multiple IPv4 or IPv6 addresses.";
                   }
                   leaf attack-dst-ip {
                     type inet:ip-address-no-zone;
                     description
                       "The destination IPv4 or IPv6
                        addresses of attack traffic. It can hold
                        multiple IPv4 or IPv6 addresses.";
                   }
                   leaf-list attack-src-port {
                     type inet:port-number;
                     description
                       "The transport-layer source ports
                        of the attack.";
                   }
                   leaf-list attack-dst-port {
                     type inet:port-number;
                     description
                       "The transport-layer destination ports
                        of the attack.";
                   }
                   leaf protocol {
                     type identityref {
                       base protocol;
                     }
                     description
                       "The type of network protocol for
                        the interface counter. If this field
                        is empty, then the counter includes
                        all protocols (e.g., IPv4, IPv6,
                        TCP, and UDP)";
                   }
                   uses attack-rates;
                 }
             }
         }
       }
      }
    }
  }
  list i2nsf-reconfiguration-policy {
    description
      "The reconfiguration policy generated
       by the I2NSF Analyzer, which will
       be sent to the I2NSF security controller.";
    key name;
    leaf name {
      type string;
      description
        "The name of the reconfiguration policy.";
    }
    choice policy-type {
      case path-reconfiguration-policy{
        container path-reconfiguration-policy{
          description
            "The container for path reconfiguration
              policy.";
          list service-function-path{
            key path-id;
            description
               "Indicates the NSFs through which
                traffic passes in sequence.";
            leaf path-id{
               type string;
               description
                 "Identify the different service
                   function paths.";
            }
            container nsfs {
               description
                 "The container for the NSFs in the
                   service function chain (SFC).";
               list nsf {
                 key nsf-name;
                 description
                    "The container for the NSF.";
                 leaf nsf-name {
                    type string;
                    description
                      "Use the name to identify the NSF.";
                 }
                 leaf sequence-number {
                    type uint64;
                    description
                      "Identifies the sequence of the NSF
                         in the service function path.";
                       }
                     }
                   }
                 }
             }
         }
     }
   }
 }
