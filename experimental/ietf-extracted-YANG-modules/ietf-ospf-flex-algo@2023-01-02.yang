module ietf-ospf-flex-algo {
  yang-version 1.1;
  namespace "urn:ietf:params:xml:ns:yang:ietf-ospf-flex-algo";
  prefix ospf-flex-algo;

  import ietf-routing {
    prefix rt;
    reference "RFC 8349: A YANG Data Model for Routing
               Management (NMDA Version)";
  }

  import ietf-routing-types {
    prefix "rt-types";
    reference "RFC 8294: Common YANG Data Types for the
               Routing Area";
  }

  import ietf-te-types {
    prefix te-types;
    reference
      "RFC8776: Common YANG Data Types for Traffic Engineering.";
  }

  import ietf-ospf {
    prefix "ospf";
    reference "RFC 9129 - YANG Data Model for the OSPF
               Protocol";
  }

  import ietf-ospfv3-extended-lsa {
    prefix "ospfv3-e-lsa";
  }

  import ietf-te {
    prefix "te";
  }

  organization
    "IETF LSR - Link State Routing Working Group";
  contact
    "WG Web:   <https://datatracker.ietf.org/wg/lsr/>
     WG List:  <mailto:spring@ietf.org>
     Author:    Yingzhen Qu
               <mailto:yingzhen.qu@futurewei.com>
     Author:    Acee Lindem
               <mailto:acee.ietf@gmail.com>
     Author:    Stephane Litkowski
               <mailto:slitkows.ietf@gmail.com>
    ";

  description
    "The YANG module defines the configuration and operational
     state for OSPF Flexible Algorithm as defined in RFC xxxx.

     This YANG model conforms to the Network Management
     Datastore Architecture (NMDA) as described in RFC 8342.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  reference "RFC XXXX: YANG Data Model for OSPF Flexible Algorithm.";

  revision 2023-01-02 {
    description
      "Initial Version";
    reference "RFC XXXX: YANG Data Model for OSPF Flexible Algorithm.";
  }

  /* Identities */

  identity metric-type {
    description
      "Base identity for route metric types.";
  }

  identity igp-metric {
    base metric-type;
    description
      "Identity for the IGP metric type.";
  }

  identity min-uni-delay {
    base metric-type;
    description
      "Min unidirectional link delay metric type.";
    reference
      "RFC 7471 - OSPF Traffic Engineering (TE) Metric Extensions";
  }

  identity te-metric {
    base metric-type;
    description
      "Traffic engineering metric type.";
    reference
      "RFC 3630 - Traffic Engineering (TE) Extensions to OSPF
                  Version 2";
  }

  identity fad-flags {
    description
      "Base identity for OSPF FAD flags.";
  }

  identity m-bit {
    base fad-flags;
    description
      "M bit, when set, the fex-algo specific prefix and ASBR
       metric MUST be used for inter-area and external prefix
       calculation.";
  }

  identity fapm-flags {
    description
      "Base identity for OSPF flex-algo prefix metric flags.";
  }

  identity e-bit {
    base fapm-flags;
    description
      "External metric, if set, the metric specified is a
       type 2 external metric.";
  }

  /* Groupings */
  grouping fa-ex-ag-sub-tlv {
    container fa-ex-ag-sub-tlv {
      leaf-list extended-admin-groups {
        type uint64;
        description
          "Extended administrative group as defined in RFC 7308.";
      }
      description
        "The flex-algo exclude admin group sub-tlv.";
    }
    description
      "The flex-algo exclude admin group sub-tlv.";
  }

  grouping fa-in-any-ag-sub-tlv {
    container fa-in-any-ag-sub-tlv {
      leaf-list extended-admin-groups {
        type uint64;
        description
          "Extended administrative group as defined in RFC 7308.";
      }
      description
        "The flex-algo include-any admin group sub-tlv.";
    }
    description
      "The flex-algo include-any admin group sub-tlv.";
  }

  grouping fa-in-all-ag-sub-tlv {
    container fa-in-all-ag-sub-tlv {
      leaf-list extended-admin-groups {
        type uint64;
        description
          "Extended administrative group as defined in RFC 7308.";
      }
      description
        "The flex-algo include-all admin group sub-tlv.";
    }
    description
      "The flex-algo include-all admin group sub-tlv.";
  }

  grouping fad-flags-sub-tlv {
    container fad-flags-sub-tlv {
      leaf-list fad-flags {
        type identityref {
          base fad-flags;
        }
        description
          "Flex-algo definition flags list.";
      }
      description
        "OSPF flex-algo definition flags.";
    }
    description
      "The flex-algo definition flags sub-tlv.";
  }

  grouping fa-ex-srlg-sub-tlv {
    container fa-ex-srlg-sub-tlv {
      leaf-list srlgs {
        type uint32;
        description
          "SRLG value as defined in RFC 4203.";
      }
      description
        "The flex-algo exclude SRLG sub-tlv.";
    }
    description
      "The flex-algo exclude SRLG sub-tlv.";
  }

  grouping fad-tlvs {
    container fad-tlvs {
      list fad-tlv {
        leaf flex-algo {
          type uint8;
          description
            "Flex-algo number, value between 128 and 255 inclusive.";
        }
        leaf metric-type {
          type identityref {
            base metric-type;
          }
            description
              "Type of metric to be used during the calculation.";
        }
        leaf calc-type {
          type uint8 {
            range "0..127";
          }
          description
            "IGP algorithm types, value from 0 to 127 as
            defined under 'Interior Gateway Protocol (IGP)
            Parameter' by IANA.";
        }
        leaf priority {
          type uint8;
            description
              "Priority of the advertisement.";
        }

        uses fa-ex-ag-sub-tlv;
        uses fa-in-any-ag-sub-tlv;
        uses fa-in-all-ag-sub-tlv;
        uses fad-flags-sub-tlv;
        uses fa-ex-srlg-sub-tlv;
        uses ospf:unknown-tlvs;

        description
          "List of flex-algo definition TLVs.";
      }
      description
        "OSPF Flexible Algorithm Definition TLV.";
    }
    description
      "OSPF Flexible Algorithm Definition (FAD) TLV.";
  }

  grouping fapm-sub-tlvs {
    container fapm-sub-tlvs {
      list fapm-sub-tlv {
        leaf flex-algo {
          type uint8;
          description
            "Flex-algo number, value between 128 and 255
             inclusive.";
        }
        leaf-list fapm-flags {
          type identityref {
            base fapm-flags;
          }
          description
            "Flex-algo prefix metric flags list.";
        }
        leaf metric {
          type uint32;
          description
            "Prefix metric.";
        }
        description
          "List of flex-algo prefix sub-tlvs.";
      }
      description
        "Flex-algo prefix metric sub-tlvs.";
    }
    description
      "Flexible Algorithm Prefix Metric (FAPM) sub TLVs.";
  }

  grouping faam-sub-tlvs {
    container faam-sub-tlvs {
      list faam-sub-tlv {
        leaf flex-algo {
          type uint8;
          description
            "Flex-algo number, value between 128 and 255
             inclusive.";
        }
        leaf metric {
          type uint32;
          description
            "Prefix metric.";
        }
        description
          "List of faam sub-tlvs.";
      }
      description
         "Flexible Algorithm ASBR Metric (FAAM) Sub-TLVs.";
    }
    description
      "Flexible Algorithm ASBR Metric (FAAM) Sub-TLVs.";
  }

  /* Configurations */

  augment "/rt:routing/rt:control-plane-protocols"
     + "/rt:control-plane-protocol/ospf:ospf" {
    when "../rt:type = 'ospf:ospfv2' or "
       + "../rt:type = 'ospf:ospfv3'" {
      description
        "This augments the OSPF routing protocol when used.";
    }
    description
      "This augments OSPF protocol with Flexible
       Algorithm.";

    container ospf-flex-algo {
      list flex-algo {
        key "algo-number";

        leaf algo-number {
          type uint8 {
            range "128..255";
          }
          description
            "An identifier in the range 128-255 that's associated
            with the Flexible Algorithm Definition.";
        }

        leaf advertise-definition {
          type boolean;
          default true;
          description
            "Enable to advertise the flex-algo definition.";
        }

        container admin-groups {
          if-feature "te-types:extended-admin-groups";
          if-feature "te-types:named-extended-admin-groups";
          leaf-list exclude-admin-groups {
            type leafref {
              path "/te:te/te:globals/te:named-admin-groups/"
                 + "te:named-admin-group/te:name";
            }
            description
              "Exclude rule used during the flex-algo
              path computation.";
          }
          leaf-list include-any-admin-groups {
            type leafref {
              path "/te:te/te:globals/te:named-admin-groups/"
                 + "te:named-admin-group/te:name";
            }
            description
              "Include-any rule used during the flex-algo
              path computation.";
          }
          leaf-list include-all-admin-groups {
            type leafref {
              path "/te:te/te:globals/te:named-admin-groups/"
                 + "te:named-admin-group/te:name";
            }
            description
              "Include-all rule used during the flex-algo
              path computation.";
          }
          description
            "Specify links for the flex-algo path computation.";
        }

        leaf-list exclude-srlgs {
          if-feature "te-types:named-srlg-groups";
          type leafref {
            path "/te:te/te:globals/te:named-srlgs/te:named-srlg/"
               + "te:name";
          }
          description
            "Shared Risk Link Groups (SRLGs) to be excluded during
            the flex-algo path computation.";
        }

        leaf fast-reroute {
          type boolean;
          default true;
          description
            "Enable fast reroute.";
        }

        leaf metric-type {
          type identityref {
            base metric-type;
          }
          description
            "Type of metric to be used during the calculation.";
        }

        leaf microloop-avoidance {
          type boolean;
          default true;
          description
            "Enable microloop avoidance.";
        }

        container prefix-metric {
          presence
            "Use flex-algo specific prefix metric.";
          description
            "Use flex-algo prefix metric.";
        }

        leaf priority {
          type uint8;
          description
            "Priority of the advertisement.";
        }

        description
          "List of flex-algo configurations.";
      }
      description
        "Flexible Algorithm configuration.";
    }
  }

  /* Database */

  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque/ospf:ri-opaque" {
    when "../../../../../../../../../../../../../"
       + "rt:type = 'ospf:ospfv2'" {
      description
        "This augmentation is only valid for OSPFv2.";
    }

    description
      "Flex-algo definition TLVs for OSPFv2 type 9 opaque RI LSA.";

    uses fad-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/ospf:ri-opaque" {
    when "../../../../../../../../../../../"
       + "rt:type = 'ospf:ospfv2'" {
      description
        "This augmentation is only valid for OSPFv2.";
    }

    description
      "Flex-algo definition TLVs for OSPFv2 type 10 opaque RI LSA.";

    uses fad-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/ospf:ri-opaque" {
    when "../../../../../../../../../"
       + "rt:type = 'ospf:ospfv2'" {
      description
        "This augmentation is only valid for OSPFv2.";
    }
    description
      "Flex-algo definition TLVs for OSPFv2 type 11 opaque RI LSA.";

    uses fad-tlvs;
  }

  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv3/"
        + "ospf:ospfv3/ospf:body/ospf:router-information" {
    when "../../../../../../../../../../../../"
       + "rt:type = 'ospf:ospfv3'" {
      description
        "This augmentation is only valid for OSPFv3.";
    }

    description
      "Flex-algo definition TLVs for OSPFv3 Router Information LSA.";

    uses fad-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body/ospf:router-information" {
    when "../../../../../../../../../../"
       + "rt:type = 'ospf:ospfv3'" {
      description
        "This augmentation is only valid for OSPFv3.";
    }

    description
      "Flex-algo definition TLVs for OSPFv3 Router Information LSA.";

    uses fad-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospf:router-information" {
    when "../../../../../../../../"
       + "rt:type = 'ospf:ospfv3'" {
      description
        "This augmentation is only valid for OSPFv3.";
    }
    description
      "Flex-algo definition TLVs for OSPFv3 Router Information LSA.";

    uses fad-tlvs;
  }

  augment "/rt:routing/"
        + "rt:control-plane-protocols/rt:control-plane-protocol/"
        + "ospf:ospf/ospf:areas/ospf:area/"
        + "ospf:interfaces/ospf:interface/ospf:database/"
        + "ospf:link-scope-lsa-type/ospf:link-scope-lsas/"
        + "ospf:link-scope-lsa/ospf:version/ospf:ospfv2/"
        + "ospf:ospfv2/ospf:body/ospf:opaque/"
        + "ospf:extended-prefix-opaque/ospf:extended-prefix-tlv" {
    when "../../../../../../../../../../../../../../"
       + "rt:type = 'ospf:ospfv2'" {
      description
        "This augmentation is only valid for OSPFv2.";
    }
    description
      "Flex-algo prefix metric sub TLVs for OSPFv2 extended prefix TLV
       in type 9 opaque LSA.";
    uses fapm-sub-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-prefix-opaque/ospf:extended-prefix-tlv" {
    when "../../../../../../../../../../../../"
       + "rt:type = 'ospf:ospfv2'" {
      description
        "This augmentation is only valid for OSPFv2.";
    }
    description
      "Flex-algo prefix metric sub TLVs for OSPFv2 extended prefix TLV
       in type 10 opaque LSA.";
    uses fapm-sub-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/"
        + "ospf:extended-prefix-opaque/ospf:extended-prefix-tlv" {
    when "../../../../../../../../../../"
       + "rt:type = 'ospf:ospfv2'" {
      description
        "This augmentation is only valid for OSPFv2.";
    }
    description
      "Flex-algo prefix metric sub TLVs for OSPFv2 extended prefix TLV
       in type 11 opaque LSA.";
    uses fapm-sub-tlvs;
  }

  /* Flex-algo prefix metric Sub-TLV in OSPFv3 Inter-Area Prefix TLV */
  augment "/rt:routing/"
    + "rt:control-plane-protocols/rt:control-plane-protocol/"
    + "ospf:ospf/ospf:areas/ospf:area/ospf:database/"
    + "ospf:area-scope-lsa-type/ospf:area-scope-lsas/"
    + "ospf:area-scope-lsa/ospf:version/ospf:ospfv3/"
    + "ospf:ospfv3/ospf:body/ospfv3-e-lsa:e-inter-area-prefix/"
    + "ospfv3-e-lsa:e-inter-prefix-tlvs/ospfv3-e-lsa:inter-prefix-tlv" {
    when "../../../../../../../../../../../../"
      + "rt:type = 'ospf:ospfv3'" {
      description
        "This augmentation is only valid for OSPFv3
         E-Router LSAs";
    }
    uses fapm-sub-tlvs;
    description
      "OSPFv3 Area-Scoped Inter-Area Prefix TLV.";
  }

  /* Flex-algo prefix metric Sub-TLV in OSPFv3 External Prefix TLV */
  augment "/rt:routing/"
    + "rt:control-plane-protocols/rt:control-plane-protocol/"
    + "ospf:ospf/ospf:database/"
    + "ospf:as-scope-lsa-type/ospf:as-scope-lsas/"
    + "ospf:as-scope-lsa/ospf:version/ospf:ospfv3/"
    + "ospf:ospfv3/ospf:body/ospfv3-e-lsa:e-as-external/"
    + "ospfv3-e-lsa:e-external-tlvs/ospfv3-e-lsa:external-prefix-tlv" {
    when "'ospf:../../../../../../../../../"
      + "rt:type' = 'ospf:ospfv3'" {
      description
        "This augmentation is only valid for OSPFv3.";
    }
    uses fapm-sub-tlvs;
    description
      "OSPFv3 AS-Scoped External Prefix TLV.";
  }

  /* OSPFv2 Extended Inter-Area ASBR LSA */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque" {
    when "../../../../../../../../../../"
       + "rt:type = 'ospf:ospfv2'" {
      description
        "This augmentation is only valid for OSPFv2.";
    }
    description
      "OSPFv2 Extended Inter-Area ASBR LSA in type 10
      opaque LSA.";

    container eia-asbr-opaque {
      container eia-asbr-tlv {
        leaf asbr-rtr-id {
          type rt-types:router-id;
          description
            "The OSPF Router ID of the ASBR.";
        }
        uses faam-sub-tlvs;
        uses ospf:unknown-tlvs;
        description
          "EIA-ASBR TLV, used to advertise additional attributes
           associated with the reachability of an ASBR.";
      }
      uses ospf:unknown-tlvs;

      description
        "OSPFv2 Extended Inter-Area (EIA-ASBR) opaque LSA.";
    }
  }

  /* FAAM Sub-TLV in OSPFv3 Inter-Area-Router TLV */
  augment "/rt:routing/"
    + "rt:control-plane-protocols/rt:control-plane-protocol/"
    + "ospf:ospf/ospf:areas/ospf:area/ospf:database/"
    + "ospf:area-scope-lsa-type/ospf:area-scope-lsas/"
    + "ospf:area-scope-lsa/ospf:version/ospf:ospfv3/"
    + "ospf:ospfv3/ospf:body/ospfv3-e-lsa:e-inter-area-router/"
    + "ospfv3-e-lsa:e-inter-router-tlvs/"
    + "ospfv3-e-lsa:inter-router-tlv" {
    when "../../../../../../../../../../../../"
      + "rt:type = 'ospf:ospfv3'" {
      description
        "This augmentation is only valid for OSPFv3
         Inter-Area-Router TLV.";
    }
    uses faam-sub-tlvs;
    description
      "OSPFv3 Area-Scoped Inter-Area-Router TLV.";
  }
}
