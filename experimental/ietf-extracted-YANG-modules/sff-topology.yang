module sff-topology{
    yang-version 1;
    namespace "urn:TBD:params:xml:ns:yang:sff-topology";
    prefix "sff-topo";

    organization "TBD";

    contact
    "wangzitao@huawei.com";

    description
    "This module defines sff topology yang data model";

    import network-topology {
        prefix "nt";
    }

    import ietf-inet-types {
        prefix "inet";
    }

    import network { prefix nd; }

//import service-topologies{ prefix st;}

organization "IETF I2RS Working Group";
     contact
      "wangzitao@huawei.com";
     description
       "This module defines sfc topology yang data model";

     typedef node-id {
       type inet:uri;
     }

 augment "/nt:network-topology/nt:topology/nt:topology-types"{
  container Service-Topologies{
   container SFF-Topology{
    description
    "SFF topology.";
   }
  }
 }

 augment "/nt:network-topology/nt:topology"{
   leaf service-topo-id{
    type network-id;
  }
  container service-topology-attributes{
   leaf node-count{
    type uint32;
   }
   container topology-extension{
    description
    "can be augment/extension.";
   }
  }
 }

 augment "/nt:network-topology/nt:topology/nt:node"{
  container node-type{
   leaf classifier-node{
    type string;
    }
   leaf sf-node{
    type string;
   }
   leaf sff-node{
    type string;
   }
  }

  list next-hop{
   key "hop-id";
   leaf hop-id{
    type node-id;
   }
  }

  container node-extension{
   container classifier-extension{
       leaf classifier-id{
        type node-id;
        description
        "The identifier of the classifier.";}
      leaf sfc-policy{
       type uint32;
       description
       "Indicate the policy of sfc.";}
      container sfp{
       description
       "contains several sfps.";
       leaf sfp-id{
        type uint32;
        description
        "The identifier of the sfp.";}
       list sf-list{
        key "sf-id";
         leaf sf-id{
          type node-id;
          description
          "The identifier of the sf which include in the sfp.";}
       }
       list sff-list{
        key "sff-id";
         leaf sff-id{
          type node-id;
          description
          "The identifier of the sff which include in the sfp.";}
       }
      }//end the sfp container
     }

     container sf-node-extension{
      leaf sf-id{
       type node-id;
       description
       "The identifier of the service function(sf).";}
      leaf sf-node-locator{
       type uint32;
       description
       "To indicate the service function (sf) locator";}
      container sf-type{
       leaf firewall{
        type uint32;
        description
        "To indicate the service function (sf) is firewall.";}
       leaf loadbalancer{
        type uint32;
        description
        "To indicate the service function (sf) is loadbalancer.";}
       leaf NAT44{
        type uint32;
        description
        "To indicate the service function (sf) is NAT44.";}
       leaf NAT64{
        type uint32;
        description
        "To indicate the service function (sf) is NAT64.";}
       leaf DPI{
        type uint32;
        description
        "To indicate the service function (sf) is DPI.";}
      }//end the sf-type container
      container sf-inventory-data{
       description
       "The container of the inventory data of service function (sf).";
      }
     }

     container sff-node-extension{
      leaf sff-id{
       type node-id;
       description
       "The identifier of the service function forward (sff).";}
      choice sffn-address{
       description
       "The address of the service function forward (sff) node";
       case ipv4-address{
        leaf ipv4-address{
         type inet:ipv4-address;}
       }
       case ipv6-address{
        leaf ipv6-address{
         type inet:ipv6-address;}
       }
      }//end the choice sffn-address
      container sffn-virtual-context{
       leaf context-id{
        type uint32;
        description
        "the identifier of the sffn virtual context.";}
      }
      container Attached-service-address{
       list service-node{
        key "service-node-id";
        leaf service-node-id{
         type node-id;
         description
         "The identifier of the service node.";}
        }//end the service-node list
        list host-system{
         key "host-system-id";
         leaf host-system-id{
          type uint32;
          description
          "The identifier of the host system.";}
        }//end the service-node list
      } //end the attached-service-address container
      list customer-support{
       key "customer-id";
       leaf customer-id{
        type uint32;
        description
        "The identifier of the customer.";}
      }//end the customer-support list
      list customer-service-resource{
       key "customer-resource-id";
       leaf customer-resource-id{
        type node-id;
        description
        "The identifier of the customer resource.";}
      }//end the customer-service-resource list
      container sffn-vntopo{
       description
       "This container can be use to contain the virtual network topology of
        Sffn. And it can be augment by specific virtual network topology.";
      }
     }
    }
   }
}
