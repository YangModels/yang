module ietf-constrained-yang-library {
  yang-version 1.1;
  namespace "urn:ietf:params:xml:ns:yang:ietf-constrained-yang-library";
  prefix "yanglib";

  // RFC Ed.: update CoMI reference.

  import ietf-comi {
    prefix comi;
    reference "I-D.ietf-core-comi";
  }
  import ietf-inet-types {
    prefix inet;
    reference "RFC 6991: Common YANG Data Types.";
  }
  import ietf-datastores {
    prefix ds;
    reference "RFC 8342: Network Management Datastore Architecture (NMDA).";
  }

  organization
    "IETF NETCONF (Network Configuration) Working Group";

  contact
    "WG Web:   <http://datatracker.ietf.org/wg/core/>
     WG List:  <mailto:core@ietf.org>

     WG Chair: Carsten Bormann
               <mailto:cabo@tzi.org>

     WG Chair: Jaime Jimenez
               <mailto:jaime.jimenez@ericsson.com>

     Editor:   Michel Veillette
               <mailto:michel.veillette@trilliantinc.com>";

  description
    "This module provides information about the YANG modules,
     datastores, and datastore schemas implemented by a constrained
     network management server.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: update reference.

  revision 2018-09-21 {
    description
      "Initial revision.";
    reference
      "I-D.veillette-core-yang-library";
  }

  /*
   * Typedefs
   */

  typedef revision-identifier {
    type binary {
      length "4";
    }
    description
      "Revision date encoded as a binary string, each nibble representing
       a digit of the of revision date. For example, revision 2018-09-21
       is encoded as 0x20 0x18 0x09 0x21.";
  }

  /*
   * Groupings
   */

  grouping module-identification-leafs {
    description
      "Parameters for identifying YANG modules and submodules.";

    leaf identifier {
      type comi:sid;
      mandatory true;
      description
        "SID assigned to this module or submodule.";
    }
    leaf revision {
      type revision-identifier;
      description
        "The YANG module or submodule revision date.  If no revision
         statement is present in the YANG module or submodule, this
         leaf is not instantiated.";
    }
  }

  grouping location-leaf-list {
    description
      "Common location leaf list parameter for modules and
       submodules.";

    leaf-list location {
      type inet:uri;
      description
        "Contains a URL that represents the YANG schema resource
         for this module or submodule.

         This leaf is present in the model to keep the alignment with
         'ietf-yang-library'. Support of this leaf in constrained
         devices is not necessarily required, nor expected. It is
         recommended that clients used the module or sub-module SID
         as the handle used to retrieve the corresponding YANG module";
    }
  }

  grouping implementation-parameters {
    description
      "Parameters for describing the implementation of a module.";

    leaf-list feature {
      type comi:sid;
      description
        "List of all YANG feature names from this module that are
         supported by the server, regardless whether they are defined
         in the module or any included submodule.";
    }
    leaf-list deviation {
      type leafref {
        path "../../module/identifier";
      }
      description
        "List of all YANG deviation modules used by this server to
         modify the conformance of the module associated with this
         entry.  Note that the same module can be used for deviations
         for multiple modules, so the same entry MAY appear within
         multiple 'module' entries.

         This reference MUST NOT (directly or indirectly)
         refer to the module being deviated.

         Robust clients may want to make sure that they handle a
         situation where a module deviates itself (directly or
         indirectly) gracefully.";
    }
  }

  grouping module-set-parameters {
    description
      "A set of parameters that describe a module set.";

    leaf index {
      type uint8;
      description
        "An arbitrary number assigned of the module set.";
    }
    list module {
      key "identifier";
      description
        "An entry in this list represents a module implemented by the
         server, as per RFC 7950 section 5.6.5, with a particular set
         of supported features and deviations.";
      reference
        "RFC 7950: The YANG 1.1 Data Modeling Language.";

      uses module-identification-leafs;
      leaf namespace {
        type inet:uri;
        description
          "The XML namespace identifier for this module.
           This leaf is present in the model to keep the alignment
           with 'ietf-yang-library'. Support of this leaf in
           constrained devices is not required, nor expected.";
      }

      uses location-leaf-list;

      list submodule {
        key "identifier";
        description
          "Each entry represents one submodule within the parent
           module.";
        uses module-identification-leafs;
        uses location-leaf-list;
      }

      uses implementation-parameters;
    }
    list import-only-module {
      key "identifier revision";
      description
        "An entry in this list indicates that the server imports
         reusable definitions from the specified revision of the
         module, but does not implement any protocol accessible
         objects from this revision.

         Multiple entries for the same module name MAY exist.  This
         can occur if multiple modules import the same module, but
         specify different revision-dates in the import statements.";

      leaf identifier {
        type comi:sid;
        description
          "The YANG module name.";
      }
      leaf revision {
        type union {
          type revision-identifier;
          type string {
            length 0;
          }
        }
        description
          "The YANG module revision date.";
      }
      leaf namespace {
        type inet:uri;
        mandatory true;
        description
          "The XML namespace identifier for this module.
           This leaf is present in the model to keep the alignment
           with 'ietf-yang-library'. Support of this leaf in
           constrained devices is not required, nor expected.";
      }

      uses location-leaf-list;

      list submodule {
        key "identifier";
        description
          "Each entry represents one submodule within the
           parent module.";

        uses module-identification-leafs;
        uses location-leaf-list;
      }
    }
  }

  grouping yang-library-parameters {
    description
      "The YANG library data structure is represented as a grouping
       so it can be reused in configuration or another monitoring
       data structure.";

    list module-set {
      key index;
      description
        "A set of modules that may be used by one or more schemas.

         A module set does not have to be referentially complete,
         i.e., it may define modules that contain import statements
         for other modules not included in the module set.";

      uses module-set-parameters;
    }

    list schema {
      key "index";
      description
        "A datastore schema that may be used by one or more
         datastores.
         The schema must be valid and referentially complete, i.e.,
         it must contain modules to satisfy all used import
         statements for all modules specified in the schema.";

      leaf index {
        type uint8;
        description
          "An arbitrary reference number assigned to the schema.";
      }
      leaf-list module-set {
        type leafref {
          path "../../module-set/index";
        }
        description
          "A set of module-sets that are included in this schema.
           If a non import-only module appears in multiple module
           sets, then the module revision and the associated features
           and deviations must be identical.";
      }
    }

    list datastore {
      key "identifier";
      description
        "A datastore supported by this server.

         Each datastore indicates which schema it supports.

         The server MUST instantiate one entry in this list per
         specific datastore it supports.

         Each datstore entry with the same datastore schema SHOULD
         reference the same schema.";

      leaf identifier {
        type ds:datastore-ref;
        description
          "The identity of the datastore.";
      }
      leaf schema {
        type leafref {
          path "../../schema/index";
        }
        mandatory true;
        description
          "A reference to the schema supported by this datastore.
           All non import-only modules of the schema are implemented
           with their associated features and deviations.";
      }
    }
  }

  /*
   * Top-level container
   */

  container yang-library {
    config false;
    description
      "Container holding the entire YANG library of this server.";

    uses yang-library-parameters;

    leaf checksum {
      type binary;
      mandatory true;
      description
        "A server-generated checksum or digest of the contents of the
         'yang-library' tree.  The server MUST change the value of
         this leaf if the information represented by the
         'yang-library' tree, except 'yang-library/checksum', has
         changed.";
    }
  }

  /*
   * Notifications
   */

  notification yang-library-update {
    description
      "Generated when any YANG library information on the
       server has changed.";

    leaf checksum {
      type leafref {
        path "/yanglib:yang-library/yanglib:checksum";
      }
      mandatory true;
      description
        "Contains the YANG library checksum or digest for the updated
         YANG library at the time the notification is generated.";
    }
  }
}
