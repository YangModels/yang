module ietf-bfd-lag-ext {
  yang-version 1.1;
  namespace "urn:ietf:params:xml:ns:yang:ietf-bfd-lag-ext";
  prefix "bfd-lag-ext";

  import ietf-bfd {
    prefix "bfd";
    reference
      "RFC 9314: A YANG Data Model for Bidirectional Forwarding
       Detection (BFD)";
  }

  import ietf-routing {
    prefix "rt";
    reference
      "RFC 8349: A YANG Data Model for Routing Management
       (NMDA version)";
  }

  import ietf-bfd-lag {
    prefix "bfd-lag";
    reference
      "RFC 9314: A YANG Data Model for Bidirectional Forwarding
       Detection (BFD)";
  }

  organization "IETF BFD Working Group";
  contact
    "WG Web:   <http://tools.ietf.org/wg/bfd>
     WG List:  <rtg-bfd@ietf.org>

     Editors:  Rajaguru Veluchamy (rvelucha@cisco.com)";

  description
    "This module contains the YANG definition for BFD IP single-hop
     as per RFC 5881 with some extended info.

     Copyright (c) 2018 IETF Trust and the persons
     identified as authors of the code.  All rights reserved.

     Code Components extracted from this document must
     include Simplified BSD License text as described in Section 4.e of
     the Trust Legal Provisions and are provided without warranty as
     described in the Simplified BSD License

     This version of this YANG module is part of RFC XXXX; see
     the RFC itself for full legal notices.";

  reference
     "RFC 5881: Bidirectional Forwarding Detection (BFD)
      for IPv4 and IPv6 (Single Hop)
      RFC 9314: YANG Data Model for Bidirectional Forwarding
      Detection (BFD)";

  revision 2022-02-18 {
    description "Initial revision.";
    reference
       "RFC XXXX: A YANG data model for BFD IP single-hop extension";
  }

  /*
   * Augments
   */
  augment "/rt:routing/rt:control-plane-protocols/"
        + "rt:control-plane-protocol/bfd:bfd/bfd-lag:lag/"
        + "bfd-lag:sessions/bfd-lag:session" {
    description "BFD augmentation for LAG ext";
    leaf session-offloaded {
        type boolean;
        description
          "Indicates whether BFD session is running in hardware";
    }
  }
}
