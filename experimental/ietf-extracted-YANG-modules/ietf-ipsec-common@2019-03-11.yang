module ietf-ipsec-common{
        yang-version 1.1;
        namespace "urn:ietf:params:xml:ns:yang:ietf-ipsec-common";
        prefix "ipsec-common";

        import ietf-inet-types { prefix inet; }
        import ietf-yang-types { prefix yang; }

        import ietf-crypto-types {
                prefix ct;
                reference "draft-ietf-netconf-crypto-types-01: Common YANG Dta Types for Cryptography";
        }

        organization "IETF I2NSF (Interface to Network Security Functions) Working Group";

        contact
        " Rafael Marin Lopez
        Dept. Information and Communications Engineering (DIIC)
        Faculty of Computer Science-University of Murcia
        30100 Murcia - Spain
        Telf: +34868888501
        e-mail: rafa@um.es

        Gabriel Lopez Millan
        Dept. Information and Communications Engineering (DIIC)
        Faculty of Computer Science-University of Murcia
        30100 Murcia - Spain
        Tel: +34 868888504
        email: gabilm@um.es

        Fernando Pereniguez Garcia
        Department of Sciences and Informatics
        University Defense Center (CUD), Spanish Air Force Academy, MDE-UPCT
        30720 San Javier - Spain
        Tel: +34 968189946
        email: fernando.pereniguez@cud.upct.es
        ";

        description "Common Data model for SDN-based IPSec configuration.";

        revision "2019-03-11" {
                description "Revision";
                reference "";
        }

        typedef encryption-algorithm-t {
                type ct:encryption-algorithm-ref;
                description "typedef";
        }

        typedef integrity-algorithm-t {
                type ct:mac-algorithm-ref;
                description
                        "This typedef enables importing modules to easily define an
                        identityref to the 'asymmetric-key-encryption-algorithm'
                        base identity.";
        }

        typedef ipsec-mode {
                type enumeration {
                        enum TRANSPORT { description "Transport mode. No NAT support."; }
                        enum TUNNEL { description "Tunnel mode"; }
                }
                description "Type definition of IPsec mode";
        }

        typedef esp-encap {
                type enumeration {
                        enum ESPINTCP { description "ESP in TCP encapulation.";}
                        enum ESPINTLS { description "ESP in TCP encapsulation using TLS.";}
                        enum ESPINUDP { description "ESP in UDP encapsulation. RFC 3948 ";}
                        enum NONE { description "NOT ESP encapsulation" ; }
                }
                description "type defining types of ESP encapsulation";
        }

        grouping encap { /* This is defined by XFRM */
                description "Encapsulation container";
                leaf espencap { type esp-encap; description "ESP in TCP, ESP in UDP or ESP in TLS";}
                leaf sport {type inet:port-number; description "Encapsulation source port";}
                leaf dport {type inet:port-number; description "Encapsulation destination port"; }
                leaf-list oaddr {type inet:ip-address; description "Encapsulation Original Address ";}
        }

        typedef ipsec-protocol {
                type enumeration {
                        enum ah { description "AH Protocol"; }
                        enum esp { description "ESP Protocol"; }
                }
                description "type define of ipsec security protocol";
        }

        typedef ipsec-spi {
                type uint32 { range "0..max"; }
                description "SPI";
        }

        typedef lifetime-action {
                type enumeration {
                        enum terminate-clear {description "Terminate the IPsec SA and allow the packets through";}
                        enum terminate-hold {description "Terminate the IPsec SA and drop the packets";}
                        enum replace  {description "Replace the IPsec SA with a new one";}
                }
                description "Action when lifetime expiration";
        }

        /*################## SPD basic groupings ####################*/

        typedef ipsec-traffic-direction {
                type enumeration {
                        enum INBOUND { description "Inbound traffic"; }
                        enum OUTBOUND { description "Outbound traffic"; }
                }
                description "IPsec traffic direction";
        }

        typedef ipsec-spd-operation {
                type enumeration {
                        enum PROTECT { description "PROTECT the traffic with IPsec"; }
                        enum BYPASS { description "BYPASS the traffic"; }
                        enum DISCARD { description "DISCARD the traffic"; }
                }
                description "The operation when traffic matches IPsec security policy";
        }

        typedef ipsec-upper-layer-proto {
                type enumeration {
                        enum TCP { description "TCP traffic"; }
                        enum UDP { description "UDP traffic"; }
                        enum SCTP { description "SCTP traffic";}
                        enum DCCP { description "DCCP traffic";}
                        enum ICMP { description "ICMP traffic";}
                        enum IPv6-ICMP { description "IPv6-ICMP traffic";}
                        enum GRE {description "GRE traffic";}
                }
                description "Next layer proto on top of IP";
        }

        typedef ipsec-spd-name {
                type enumeration {
                        enum id_rfc_822_addr { description "Fully qualified user name string."; }
                        enum id_fqdn { description "Fully qualified DNS name."; }
                        enum id_der_asn1_dn { description "X.500 distinguished name."; }
                        enum id_key { description "IKEv2 Key ID."; }
                }
                description "IPsec SPD name type";
        }

        grouping lifetime {
                description "lifetime current state data";
                leaf time {type yang:timestamp; default 0; description "Time since the element is added";}
                leaf idle {type yang:timestamp; default 0; description "Time the element is in idle state";}
                leaf bytes { type uint32; default 0; description "Lifetime in bytes number";}
                leaf packets {type uint32; default 0; description "Lifetime in packets number";}
        }

        /*################## SAD and SPD common basic groupings ####################*/

        grouping port-range  {
                description "Port range grouping";
                leaf start { type inet:port-number; description "Start Port Number"; }
                leaf end { type inet:port-number; description "End Port Number"; }
        }

        grouping tunnel-grouping {
                description "Tunnel mode grouping";
                leaf local{ type inet:ip-address; description "Local tunnel endpoint"; }
                leaf remote{ type inet:ip-address; description "Remote tunnel enpoint"; }
                leaf bypass-df { type boolean; description "Bypass DF bit"; }
                leaf bypass-dscp { type boolean; description "Bypass DSCP"; }
                leaf dscp-mapping { type yang:hex-string; description "DSCP mapping"; }
                leaf ecn { type boolean; description "Bit ECN"; } /* RFC 4301 ASN1 notation. Annex C*/
        }

        grouping selector-grouping {
                description "Traffic selector grouping";

                leaf local-subnet { type inet:ip-prefix; description "Local IP address subnet"; }
                leaf remote-subnet { type inet:ip-prefix; description "Remote IP address subnet"; }

                leaf-list upper-layer-protocol { type ipsec-upper-layer-proto; description "List of Upper Layer Protocol";}

                list local-ports {
                        key "start end";
                        uses port-range;
                        description "List of local ports. When the upper-layer-protocol is ICMP this 16 bit value respresents code and type as mentioned in RFC 4301";
                }

                list remote-ports {
                        key "start end";
                        uses port-range;
                        description "List of remote ports. When the upper-layer-protocol is ICMP this 16 bit value respresents code and type as mentioned in RFC 4301";
                }
        }

        /*################## SPD ipsec-policy-grouping ####################*/

        grouping ipsec-policy-grouping {

                description "Holds configuration information for an IPSec SPD entry.";

                leaf spd-entry-id { type uint64; description "SPD entry id "; }
                leaf priority {type uint32; default 0; description "Policy priority";}
                leaf anti-replay-window { type uint16 { range "0 | 32..1024"; } description "Anti replay window size"; }

                list names {
                        key "name";
                        leaf name-type { type ipsec-spd-name; description "SPD name type."; }
                        leaf name { type string; description "Policy name"; }
                        description "List of policy names";
                }

                container condition {
                        description "SPD condition - RFC4301";
                        list traffic-selector-list {
                                key "ts-number";
                                leaf ts-number { type uint32; description "Traffic selector number"; }
                                leaf direction { type ipsec-traffic-direction; description "in/out"; }
                                uses selector-grouping;
                                ordered-by user;
                                description "List of traffic selectors";
                        }
                }

                container processing-info {
                        description "SPD processing - RFC4301";
                        leaf action{ type ipsec-spd-operation; mandatory true; description "Bypass or discard, container ipsec-sa-cfg is empty";}

                        container ipsec-sa-cfg {
                                when "../action = 'PROTECT'";

                                leaf pfp-flag { type boolean; description "Each selector has with a pfp flag."; }
                                leaf extSeqNum { type boolean; description "TRUE 64 bit counter, FALSE 32 bit"; }
                                leaf seqOverflow { type boolean; description "TRUE rekey, FALSE terminare &amp; audit"; }
                                leaf statefulfragCheck { type boolean; description "Indicates whether (TRUE) or not (FALSE) stateful fragment checking (RFC 4301) applies to the SA to be created."; }
                                leaf security-protocol { type ipsec-protocol; description "Security protocol of IPsec SA: Either AH or ESP."; }
                                leaf mode { type ipsec-mode; description "transport/tunnel"; }

                                container ah-algorithms {
                                        when "../security-protocol = 'ah'";
                                        leaf-list ah-algorithm { type integrity-algorithm-t; description "Configure Authentication Header (AH)."; }
                                        leaf trunc-length { type uint32; description "Truncation value for AH algorithm"; }
                                        description "AH algoritms ";
                                }

                                container esp-algorithms {
                                        when "../security-protocol = 'esp'";
                                        description "Configure Encapsulating Security Payload (ESP).";
                                        leaf-list authentication { type integrity-algorithm-t; description "Configure ESP authentication"; }
                                        /* With AEAD algorithms, the authentication node is not used */
                                        leaf-list encryption { type encryption-algorithm-t; description "Configure ESP encryption"; }
                                        leaf tfc_pad { type uint32; default 0; description "TFC padding for ESP encryption"; }
                                }

                                container tunnel {
                                        when "../mode = 'TUNNEL'";
                                        uses tunnel-grouping;
                                        description "tunnel grouping container";
                                }

                                description " IPSec SA configuration container";
                        }
                }

                container spd-lifetime-soft {
                        description "SPD lifetime hard state data";
                        uses lifetime;
                        leaf action {type lifetime-action; description "Action lifetime";}
                }

                container spd-lifetime-hard {
                        description "SPD lifetime hard state data. The action after the lifetime is to remove the SPD entry.";
                        uses lifetime;
                }

                // State data for an IPsec SPD entry
                container spd-lifetime-current {
                        uses lifetime;
                        config false;
                        description "SPD lifetime current state data";
                }
        } /* grouping ipsec-policy-grouping */
}
