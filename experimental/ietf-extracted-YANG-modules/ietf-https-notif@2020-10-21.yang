module ietf-https-notif {
  yang-version 1.1;
  namespace "urn:ietf:params:xml:ns:yang:ietf-https-notif";
  prefix "hn";

  import ietf-subscribed-notifications {
    prefix sn;
    reference
      "I-D.ietf-netconf-subscribed-notifications";
  }

  import ietf-http-client {
    prefix httpc;

    reference
      "I-D.ietf-netconf-http-client-server";
  }

  import ietf-sub-notif-recv-list {
    prefix snrl;

    reference
      "RFC XXXX, YANG Data Module for HTTPS Notifications.";
  }

  import ietf-x509-cert-to-name {
    prefix x509c2n;

    reference
      "RFC 7407: YANG Data Model for SNMP Configuration.";
  }

  organization
    "IETF NETCONF Working Group";

  contact
    "WG Web:   <http://tools.ietf.org/wg/netconf>
     WG List:  <netconf@ietf.org>

     Authors: Mahesh Jethanandani (mjethanandani at gmail dot com)
              Kent Watsen (kent plus ietf at watsen dot net)";
  description
    "YANG module for configuring HTTPS base configuration.

     Copyright (c) 2018 IETF Trust and the persons identified as
     the document authors.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "2020-10-21" {
    description
      "Initial Version.";
    reference
      "RFC XXXX, YANG Data Module for HTTPS Notifications.";
  }

  identity https {
    base sn:transport;
    description
      "HTTPS transport for notifications.";
  }

  augment "/sn:subscriptions/snrl:receiver-instances/" +
          "snrl:receiver-instance/snrl:transport-type" {
    case https {
      container https-receiver {
        description
          "HTTPS receiver for notification";

        uses httpc:http-client-stack-grouping {
          refine "transport/tcp" {
            // create the logical impossibility of enabling "tcp"
            // transport
            if-feature "not httpc:tcp-supported";
          }
          augment "transport/tls/tls/http-client-parameters" {
            leaf path {
              type string;
              description
                "Relative URI to the target resource.";
            }
            description
              "Augmentation to add a path to the target resource.";
          }
        }

        container receiver-identity {
          description
            "Specifies mechanism for identifying the receiver.
             The publisher MUST NOT include any content in a
             notification that the user is not authorized to view.";

          container cert-maps {
            uses x509c2n:cert-to-name;
            description
              "The cert-maps container is used by a TLS-based HTTP
               server to map the HTTPS client's presented X.509
               certificate to a 'local' username. If no matching and
               valid cert-to-name list entry is found, the publisher
               MUST close the connection, and MUST NOT
               not send any notifications over it.";
            reference
              "RFC 7407: A YANG Data Model for SNMP Configuration.";
          }
        }
      }
    }
    description
      "Augment the transport-type choice to define this transport.";
  }
}
