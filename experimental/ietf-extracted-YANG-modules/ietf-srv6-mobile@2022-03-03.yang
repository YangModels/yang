module ietf-srv6-mobile {
  yang-version "1.1";
  namespace "urn:ietf:params:xml:ns:yang:ietf-srv6-mobile";
  prefix "srv6-mob";

  import ietf-inet-types {
    prefix "inet";
    reference
      "RFC 6991: Common YANG Data Types.";
  }
  import ietf-routing {
    prefix rt;
    reference
      "RFC 8349, A YANG Data Model for Routing Management
       (NMDA Version).";
  }
  import ietf-routing-types {
    prefix rt-types;
    reference
      "RFC 8294: Common YANG Types for the Routing Area.";
  }
  import ietf-routing-policy {
    prefix rt-pol;
    reference
      "RFC 9067: A YANG Data Model for Routing Policy.";
  }
  import ietf-bgp {
    prefix bgp;
    reference
      "I-D.ietf-idr-bgp-model: BGP Model for Service Provider
       Network.";
  }
  import ietf-bgp-policy {
    prefix bp;
    reference
      "I-D.ietf-idr-bgp-model: BGP Model for Service Provider
       Network.";
  }
  import ietf-bgp-types {
    prefix bt;
    reference
      "I-D.ietf-idr-bgp-model: BGP Model for Service Provider
       Network.";
  }
  import ietf-segment-routing {
    prefix sr;
    reference
      "RFC 9020: YANG Data Model for Segment Routing.";
  }
  import ietf-srv6-base {
    prefix srv6;
    reference
      "I-D.ietf-spring-srv6-yang: YANG Data Model for SRv6 Base
       and Static.";
  }
  import ietf-srv6-types {
    prefix srv6-types;
    reference
      "RFC 9020: YANG Data Model for Segment Routing.";
  }

  organization
    "IETF SPRING Working Group";

  contact
    "WG Web:   <https://datatracker.ietf.org/wg/spring/about>
     WG List:  <spring@ietf.org>

     Editor: Mahesh Jethanandani (mjethanandani at gmail dot com)
     Author:  Tetsuya Murakami (tetsuya at arrcus dot com)";

  description
    "This module augments the BGP YANG model to add support for
     configuration in mobile networks.

     Copyright (c) 2022 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "2022-03-03" {
    description
      "Initial Version.";
    reference
      "RFC XXXX, A YANG Model for BGP configuration in mobile
       networks.";
  }

 /*
  * Features
  */

  /*
   * Typedefs
   */
  typedef srv6-mobile-function-type {
    type union {
      type identityref {
        base "srv6-types:srv6-endpoint-type";
      }
      type uint16;
    }
    description
      "Type definition for SRV6 mobile function. Unknown
       values are represented as the numeric value.";
    reference
      "draft-ietf-dmm-srv6-mobile-uplane";
  }
  /*
   * Identities
   */
  identity srv6-mup {
    base bt:afi-safi-type;
    description
      "Segment Routing for Mobile User Plane (AFI,SAFI = ?,?)";
    reference
      "RFC XXXX: A YANG Model for BGP configuration in mobile
       networks.";
  }

  identity label-allocation-mode {
    description
      "Base identity to be used to express types of label allocation
       strategies to be used within a network instance";
  }

  identity label-per-prefix {
    base label-allocation-mode;
    description
      "A label is to be allocated per prefix entry in the RIB for the
       network instance";
  }

  identity label-per-nexthop {
    base label-allocation-mode;
    description
      "A label is to be allocated per nexthop entry in the RIB for
       the network instance";
  }

  identity label-instance {
    base label-allocation-mode;
    description
      "A single label is to be used for the instance";
  }

  identity sid-allocation-mode {
    description
      "Base identity to be used to express types of SRv6 segment ID
       allocation strategies to be used within a network instance.";
  }

  identity sid-per-nexthop {
    base sid-allocation-mode;
    description
      "A segment ID is to be allocated per nexthop entry in the RIB
       for the network instance";
  }

  identity sid-instance {
    base sid-allocation-mode;
    description
      "A single segment ID is to be used for the instance";
  }

  identity sid-per-nexthop-no-transportation {
    base sid-allocation-mode;
    description
      "A segment ID is to be allocated per nexthop entry in the
       RIB for the network instance";
  }

  identity sid-instance-no-transportation {
    base sid-allocation-mode;
    description
      "A single segment ID is to be used for the instance";
  }

  identity mobile-interface-type {
    description
      "Base identity for different mobile interfaces.";
  }

  identity n4 {
    base mobile-interface-type;
    description
      "N4 interface.";
  }

  /*
   * Groupings
   */

  /*
   * BGP configuration
   */
  augment "/rt:routing/rt:control-plane-protocols" +
          "/rt:control-plane-protocol/bgp:bgp/bgp:global" {

    description
      "Augmentation of the BGP global configuration to add srv6
       mobile configuration.";

    leaf route-distinguisher {
      type rt-types:route-distinguisher;
      description
        "The route distinguisher that should be used for the local
         VRF or VSI instance when it is signalled via BGP.";
    }

    leaf label-allocation-mode {
      type identityref {
        base label-allocation-mode;
      }
      must "not(../sid-allocation-mode)" {
        error-message "label-allocation-mode and sid-allocation-mode"
                    + "cannot co-exist";
      }
      must "not(/rt:routing/rt:control-plane-protocols" +
           "/rt:control-plane-protocol" +
           "/bgp:bgp/bgp:global/srv6/mobile/encapsulation/config" +
           "/locator | " +
           "/rt:routing/rt:control-plane-protocols" +
           "/rt:control-plane-protocol/bgp:bgp/bgp:global" +
           "/srv6/locator)" {
        error-message "SRv6 configurations must be removed first";
      }
      description
        "The label allocation mode to be used for L3 entries
         in the network instance";
    }

    leaf sid-allocation-mode {
      type identityref {
        base sid-allocation-mode;
      }
      must "not(../label-allocation-mode)" {
        error-message "label-allocation-mode and sid-allocation-mode "
                    + "cannot co-exist";
      }
      must "boolean(/rt:routing/rt:control-plane-protocols" +
           "/rt:control-plane-protocol" +
           "/bgp:bgp/bgp:global/srv6/mobile/encapsulation/locator |" +
           "/rt:routing/rt:control-plane-protocols" +
           "/rt:control-plane-protocol/bgp:bgp/bgp:global/srv6" +
           "/mobile/decapsulations/decapsulation/locator |" +
           "/rt:routing/rt:control-plane-protocols" +
           "/rt:control-plane-protocol/bgp:bgp/bgp:global/srv6" +
           "/locator)" {
        error-message "SRv6 locator name must be configured";
      }
      description
        "The segment ID allocation mode to be used for L3 entries
         in the network instance";
    }

    container srv6 {
      description
        "SRv6 mobile container.";

      leaf locator {
        type leafref {
          path "/rt:routing/sr:segment-routing/" +
               "srv6:srv6/srv6:locators/srv6:locator/srv6:name";
        }
        description
          "Locator configuration.";
      }

      leaf sid-manager-connected {
        type boolean;
        config false;
        description
          "Connection with segment ID manager is active";
      }

      leaf locator-registered {
        type boolean;
        config false;
        description
          "Locator name is registered";
      }

      leaf micro-segment-enabled {
        type boolean;
        config false;
        description
          "Locator has enabled micro-segment behavior";
      }

      container mobile {
        when "derived-from-or-self(/rt:routing" +
             "/rt:control-plane-protocols" +
             "/rt:control-plane-protocol/bgp:bgp/bgp:global" +
             "/bgp:afi-safis/bgp:afi-safi/bgp:name, 'srv6-mup')" {
          description
            "This augmentation is valid only for a MUP SAFI.";
        }

        description
          "Mobile configuration of SRv6.";

        container encapsulation {
          description
            "Encapsulation configuration.";

          leaf locator {
            type leafref {
              path "/rt:routing/sr:segment-routing/" +
                   "srv6:srv6/srv6:locators/srv6:locator/srv6:name";
            }
            description
              "Reference to SRv6 locater key";
          }

          leaf function {
            type srv6-mobile-function-type;
            must "boolean(current()/../locator)" {
              error-message
                "SRv6 Mobile Locator name must be configured";
            }
            description
              "One of the SRv6 function types.";
          }

          leaf source-adress {
            type inet:ipv4-address;
            description
              "GTP source IP address";
          }

          leaf source-position {
            type uint8;
            description
              "Bit position of GTP source IP address";
          }

          container n4-network-instance {
            description
              "Definitions for the N4 interface.";

            leaf routing-policy {
              type leafref {
                path "/rt-pol:routing-policy/" +
                     "rt-pol:policy-definitions/" +
                     "rt-pol:policy-definition/rt-pol:name";
              }
              must "boolean(current()/../access)" {
                error-message
                  "SRv6 Mobile access instance name must be " +
                  "configured";
              }
              description
                "Reference to routing-policy";
            }

            leaf access {
              type string;
              description
                "Mobile access instance.";
            }
          }
        }

        container decapsulations {
          description
            "SRv6 mobile decapsulation configuration.";

          list decapsulation {
            key "id";
            description
              "SRv6 mobile Decapsulation config";

            leaf id {
              type uint16;
              description
                "SRv6 mobile decapsulation entry id";
            }

            leaf locator {
              type leafref {
              path "/rt:routing/sr:segment-routing/" +
                   "srv6:srv6/srv6:locators/srv6:locator/srv6:name";
              }
              description
                "Reference to SRv6 locater key";
            }

            leaf function {
              type srv6-mobile-function-type;
              must "boolean(current()/../locator)" {
                error-message
                  "SRv6 Mobile Locator name must be configured";
              }
              description
                "One of SRv6 function types.";
            }

            container n4-network-instance {
              description
                "Definitions for the N4 interface.";

              leaf core {
                type string;
                description
                  "Core instance";
              }
            }
          }
        }
        leaf decapsulation-source-prefix {
          type inet:ipv6-prefix;
          description
            "IPv6 prefix for GTP source address";
        }
      }
    }
  }

  augment "/rt:routing/rt:control-plane-protocols" +
          "/rt:control-plane-protocol/bgp:bgp/bgp:global" +
          "/bgp:route-selection-options" {

    description
      "Augmentation of the BGP global configuration for
       route selection options to add srv6 mobile configuration.";

    leaf selection-deferral-time {
      type uint16 {
        range 1..3600;
      }
      default 300;
      description
        "An upper-bound on the time (in seconds) that the best-path
         selection is deferred";
    }

    leaf med-missing-as-worst {
      type boolean;
      description
        "A route without MED is treated as with highest MED value";
    }

    leaf multipath-as-path-relax {
      type boolean;
      default true;
      description
        "Paths with different AS-Path but of same length can form
         ECMP";
    }

    leaf multipath-nexthop-relax {
      type boolean;
      default false;
      description
        "Enable BGP multi-path for paths with same next-hop";
    }
  }

  augment "/rt-pol:routing-policy/rt-pol:defined-sets" +
          "/bp:bgp-defined-sets" {
    description
      "Augmentation of the Routing Policy module to add
       mobile interface defined sets.";

    container n4-interface-sets {
      description
        "Enclosing container for list of n4 interface sets.";

      list interface-set {
        key "name";
        description
          "List of defined interface sets.";

        leaf name {
          type string;
          description
            "Name of interface set. This is used to reference
             the set in match conditions.";
        }

        leaf-list member {
          type identityref {
            base "mobile-interface-type";
          }
          description
            "Members of interface set.";
        }
      }
    }
  }

  augment "/rt-pol:routing-policy/rt-pol:policy-definitions" +
          "/rt-pol:policy-definition/rt-pol:statements" +
          "/rt-pol:statement/rt-pol:conditions/bp:bgp-conditions" {
    description
      "Augmentation of the Routing Policy module to add conditions.";

    container match-n4-network-interface-set {
      description
        "Match a referenced network instance.";
      leaf n4-network-instance-set {
        type leafref {
          path "/rt-pol:routing-policy/rt-pol:defined-sets/"
             + "bp:bgp-defined-sets/n4-interface-sets/"
             + "interface-set/name";
        }
        description
          "References a defined community set.";
      }
      uses rt-pol:match-set-options-group;
    }
  }

  augment "/rt-pol:routing-policy/rt-pol:policy-definitions" +
          "/rt-pol:policy-definition/rt-pol:statements" +
          "/rt-pol:statement/rt-pol:actions/bp:bgp-actions" {
    description
      "Augmentation of the Routing Policy module to add actions.";

    container set-network-interface {
      description
        "Set a referenced network instance.";
      uses rt-pol:apply-policy-group;
    }
  }
}
