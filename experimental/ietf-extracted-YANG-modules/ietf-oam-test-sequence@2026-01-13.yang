module ietf-oam-test-sequence {
  yang-version 1.1;
  namespace "urn:ietf:params:xml:ns:yang:ietf-oam-test-sequence";
  prefix "oamts";

  import ietf-oam-unitary-test {
    prefix "oamut";
  }

  import ietf-schedule { prefix "schedule"; }

  organization
    "IETF OPSAWG (Operations and Management Area Working Group)";

  contact
    "WG Web:   <https://datatracker.ietf.org/wg/opsawg/>
     WG List:  <mailto:opsawg@ietf.org>
     Author:   Luis Miguel Contreras Murillo
               <luismiguel.contrerasmurillo@telefonica.com>
     Author:   Victor Lopez
              <victor.lopez@nokia.com>
         Author:   Qin Wu
                  <bill.wu@huawei.com>";
  description
    "This module defines the 'oam-test-sequence-test' YANG model for
    management of network diagnosis procedures.

    Copyright (c) 2026 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
      (https://trustee.ietf.org/license-info).

     This version of this YANG module is part of RFC XXXX
     (https://www.rfc-editor.org/info/rfcXXXX); see the RFC itself
     for full legal notices.";

    // RFC Ed.: update the date below with the date of RFC
    // publication and remove this note.
    // RFC Ed.: replace XXXX with actual RFC number and remove
    // this note.

  revision "2026-01-13" {
    description "Initial version";
    reference "RFCXXXX";
  }

  /* Identities */
         identity test-sequence-status {
           description
             "Base identity for test-sequence-status.";
         }
         identity planned {
           base test-sequence-status;
           description
            "Identity for planned.";
         }
         identity configured {
           base test-sequence-status;
           description
            "Identity for configured.";
         }
         identity ready {
           base test-sequence-status;
           description
            "Identity for ready.";
         }
         identity on-going {
           base test-sequence-status;
           description
             "Identity for on-going.";
         }
         identity stop {
           base test-sequence-status;
           description
            "Identity for stop.";
         }
         identity success {
           base test-sequence-status;
           description
            "Identity for success.";
         }
         identity failure {
           base test-sequence-status;
           description
            "Identity for failure";
         }
         identity error {
           base test-sequence-status;
           description
            "Identity for error.";
         }
         identity resource-contention {
           base error;
           description
            "Identity for resource-contention error cause.";
         }
         identity priority {
           base error;
           description
            "Identity for priority error cause.";
         }

  /* Data model definition */
  container oam-test-sequence {
    description
      "Container for executing a sequence of ietf-oam-unitary-tests
      N times.";

    list test-sequence {
      key "name";
      description "List of test sequences.";

      leaf name {
        type string;
        description "Unique name for the test sequence.";
      }

      list test-ref {
            key "name";
        ordered-by user;
        description "References to the ietf-oam-unitary-tests.";

        uses "oamut:oam-unitary-test";
      }
   uses schedule:schedule-status;
         leaf test-sequence-status {
           type identityref {
                 base test-sequence-status;
           }
           config false;
           description
                 "Status of the test sequence execution.";
         }
  choice schedule-class {
     description
          "Choice based on the type of the time range.";
   container period {
         description
           "The OAM Test takes effect based on a precise period of
                time.";
           uses schedule:period-of-time;
   }
   container recurrence {
         description
           "The OAM test takes effect based on a recurrence rule.";
         uses schedule:recurrence-basic;
         leaf execution-count {
           type uint32;
           description
             "If set, limits how many times the test sequence is
              executed for this recurrence. If the leaf is absent, there
              is no limit: executions follow the recurrence until the
              test is removed from the system.";
           }
      }
     }
    }
  }
}
