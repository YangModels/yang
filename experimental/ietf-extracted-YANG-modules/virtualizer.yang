module virtualizer {
namespace "http://fp7-unify.eu/framework/virtualizer";
prefix virt;
organization "EU-FP7-UNIFY";
contact "Robert Szabo <robert.szabo@ericsson.com>";
description "data model for joint software and network
virtualization and resource control";

revision 2015-06-27 {
  reference "Initial version";
}

// REUSABLE GROUPS
grouping id-name {
  description "used for key (id) and naming";
  leaf id {
    type string;
    description "For unique key id";}
  leaf name {
    type string;
    description "Descriptive name";}
}

grouping node-type {
  description "For node type defintion";
  leaf type{
    type string;
    mandatory true;
    description "to identify nodes (infrastructure or NFs)";
  }
}

// PORTS
typedef port-ref {
  type string;
  description "path to a port; can refer to ports at multiple
  levels in the hierarchy";
}

grouping port {
  description "Port definition: used for infrastructure and NF
  ports";
  uses id-name;
  leaf port_type {
    type string;
    mandatory true;
    description "Port type identification: abstract is for
    technology independent ports and SAPs for technology specific
    ports";}
  leaf port_data{
    type string;
    description "Opaque data for port specific types";
  }
}

grouping ports {
  description "Collection of ports";
  container ports {
    description "see above";
    list port{
      key "id";
      uses port;
  description "see above";
    }
  }
}
// FORWARDING BEHAVIOR
grouping flowentry {
  leaf port {
    type port-ref;
    mandatory true;
    description "path to the port";
  }
  leaf match {
    type string;
    mandatory true;
    description "matching rule";
  }
  leaf action {
    type string;
    mandatory true;
    description "forwarding action";
  }
  container resources{
    uses link-resource;
    description "network resources assigned to forwarding entry";
  }
  description "SDN forwarding entry";
}

grouping flowtable {
  container flowtable {
    description "Collection of flowentries";
    list flowentry {
      key "port match action";
  description "Index list of flowentries";
      uses flowentry;
    }
  }
  description "See container description";
}

// LINKS
grouping link-resource {
  description "Core networking characteristics / resources
  (bandwidth, delay)";
  leaf delay {
    type string;
    description "Delay value with unit; e.g. 5ms";
  }
  leaf bandwidth {
    type string;
    description "Bandwithd value with unit; e.g. 10Mbps";
  }
}

grouping link {
  description "Link between src and dst ports with attributes";
  uses id-name;
  leaf src {
    type port-ref;
    description "relative path to the source port";
  }
  leaf dst {
    type port-ref;
    description "relative path to the destination port";
  }
  container resources{
    uses link-resource;
    description "Link resources (attributes)";
  }
}

grouping links {
  description "Collection of links in a virtualizer or a node";
  container links {
    description "See above";
    list link {
      key "src dst";
  description "Indexed list of links";
      uses link;
    }
  }
}

// CAPABILITIES
grouping capabilities {
  description "For capability reporting: currently supported NF
  types";
  container supported_NFs { // supported NFs are enumerated
    description "Collecction of nodes as supported NFs";
    list node{
      key "id";
  description "see above";
      uses node;
    }
  }
  // TODO: add other capabilities
}

// NODE

grouping software-resource {
  description "Core software resources";
  leaf cpu {
    type string;
    mandatory true;
    description "In virtual CPU (vCPU) units";
  }
  leaf mem {
    type string;
    mandatory true;
    description "Memory with units, e.g., 1Gbyte";
  }
  leaf storage {
    type string;
    mandatory true;
    description "Storage with units, e.g., 10Gbyte";
  }
}

grouping node {
  description "Any node: infrastructure or NFs";
  uses id-name;
  uses node-type;
  uses ports;
  uses links;
  container resources{
    description "Software resources offer/request of the node";
    uses software-resource;
  }
}

grouping infra-node {
  description "Infrastructure nodes wich can contain other nodes
  as NFs";
  uses node;
  container NF_instances {
    description "Hosted NFs";
    list node{
      key "id";
      uses node;
  description "see above";
    }
  }
  container capabilities {
    description "Supported NFs as capability reports";
    uses capabilities;
  }
  uses flowtable;
}

//======== Virtualizer  ====================

container virtualizer {
  description "Definition of a virtualizer instance";
  uses id-name;

  container nodes{
    description "infra nodes, which embeds NFs and report
    capabilities";
    list node{
      key "id";
      uses infra-node;
  description "see above";
    }
  }
  uses links;
}
}
