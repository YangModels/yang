module ietf-nwi-passive-inventory {
  yang-version 1.1;
  namespace "urn:ietf:params:xml:ns:yang:ietf-nwi-passive-inventory";
  prefix nwi-passive;

  import ietf-network-inventory {
    prefix nwi;
    reference
    "RFCXXXX: A YANG Data Model for Network Inventory";
    //RFC Editor: replace XXXX with actual RFC number
    //and remove this note
  }
  import ietf-ni-location {
    prefix nil;
    reference
    "RFCYYYY: A YANG Data Model for Network Inventory Location";
    //RFC Editor: replace YYYY with actual RFC number
    //and remove this note
  }

  organization
    "IETF Network Inventory YANG (ivy) Working Group";
  contact
    "WG Web:   <https://datatracker.ietf.org/wg/ivy/>
     WG List:  <mailto:inventory-yang@ietf.org>

     Editor:   Chaode Yu
               <yuchaode@huawei.com>

     Editor:   Aihua Guo
               <aihuaguo.ietf@gmail.com>

     Editor:   Italo Busi
               <italo.busi@huawei.com>";

  description
    "This YANG module specifies a data model for passive
     devices, such as fibers, cables, and passive sites,
     deployed within and between network elements.

    The model fully conforms to the Network Management
    Datastore Architecture (NMDA).

    Copyright (c) 2023 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  // RFC Ed.: replace XXXX with actual RFC number and remove this
  // note.
  // RFC Ed.: update the date below with the date of RFC publication
  // and remove this note.

  revision 2025-07-07 {
    description
      "Initial version";
    reference
      "RFC XXXX: A YANG Data Model for Passive Device Info in
       Network Inventory.";
      //RFC Editor: replace XXXX with actual RFC number, update date
      //information and remove this note
  }

  /* Identities */
  identity fiber-type {
    description
      "Base identity for fiber types.";
  }
  identity G652A {
    base fiber-type;
    description
      "ITU-T G.652A fiber.";
  }
  identity G652B {
    base fiber-type;
    description
      "ITU-T G.652B fiber.";
  }
  identity G652C {
    base fiber-type;
    description
      "ITU-T G.652C fiber.";
  }
  identity G652D {
    base fiber-type;
    description
      "ITU-T G.652D fiber.";
  }
  identity G653 {
    base fiber-type;
    description
      "ITU-T G.653 fiber.";
  }
  identity G654 {
    base fiber-type;
    description
      "ITU-T G.654 fiber.";
  }
  identity G655 {
    base fiber-type;
    description
      "ITU-T G.655 fiber.";
  }
  identity G656 {
    base fiber-type;
    description
      "ITU-T G.656 fiber.";
  }
  identity G657A1 {
    base fiber-type;
    description
      "ITU-T G.657A1 fiber.";
  }
  identity G657A2 {
    base fiber-type;
    description
      "ITU-T G.657A2 fiber.";
  }
  identity G657B {
    base fiber-type;
    description
      "ITU-T G.657B fiber.";
  }
  identity other {
    base fiber-type;
    description
      "Other type of fiber.";
  }

  identity cable-type {
    description
      "Base identity for cable types.";
  }
  identity optical-fiber {
    base cable-type;
    description
      "Fiber optic cable.";
  }
  identity electrical-cable {
    base cable-type;
    description
      "Electrical cable.";
  }
  identity coaxial-cable {
    base electrical-cable;
    description
      "Coaxial cable.";
  }

  identity cable-role {
    description
      "Base identity for cable roles.";
  }
  identity backbone {
    base cable-role;
    description
      "Backbone cable.";
  }
  identity aggregation {
    base cable-role;
    description
      "Aggregation cable.";
  }
  identity access {
    base cable-role;
    description
      "Access cable.";
  }
  identity trunk {
    base cable-role;
    description
      "Trunk cable.";
  }
  identity distribution {
    base cable-role;
    description
      "Distribution cable.";
  }
  identity branch {
    base cable-role;
    description
      "Branch cable.";
  }
  identity passive-port-type {
    description
      "Base identity for passive port types.";
  }
  identity service-port {
    base passive-port-type;
    description
      "Service port.";
  }
  identity input-port {
    base passive-port-type;
    description
      "Input port.";
  }
  identity output-port {
    base passive-port-type;
    description
      "Output port.";
  }
  identity p2mp-port {
    base passive-port-type;
    description
      "Input port.";
  }

  identity connected-device-type {
    description
      "Base identity for connected device types.";
  }
  identity passive-device {
    base connected-device-type;
    description
      "Passive/unmanaged device.";
  }
  identity active-device {
    base connected-device-type;
    description
      "Active device, e.g. network element.";
  }

  identity passive-device-type {
    description
      "Base identity for passive device types.";
  }
  identity ODF {
    base passive-device-type;
    description
      "Optical Distribution Frame.";
  }
  identity WDM {
    base passive-device-type;
    description
      "Wavelength Division Multiplexer.";
  }
  identity FAT {
    base passive-device-type;
    description
      "Fiber Access Terminal.";
  }
  identity FDT {
    base passive-device-type;
    description
      "Fiber Distribution Terminal.";
  }
  identity ATB {
    base passive-device-type;
    description
      "Access Terminal Box.";
  }

  /* Groupings */
  grouping connected-device-end {
    description
      "Attributes applicable to connected device end.";

    leaf device-type {
      type identityref {
        base connected-device-type;
      }
      description
        "Type of connected device.";
    }

    choice connected-device-type {
      description
        "Device end based on the type of connected device.";
      case passive {
        leaf device-id {
          type string;
          must "derived-from-or-self(../device-type,
               'nwi-passive:passive-device')";
          description
            "Connected passive device identifier.";
        }
      }
      case active {
        leaf ne-ref {
          type leafref {
            path "/nwi:network-inventory/nwi:network-elements"
               + "/nwi:network-element/nwi:ne-id";
          }
          must "derived-from-or-self(../device-type,
               'nwi-passive:active-device')";
          description
            "Referenced Network Element (NE).";
        }
        leaf component-ref {
          type leafref {
            path "/nwi:network-inventory/nwi:network-elements"
               + "/nwi:network-element[nwi:ne-id=current()/.."
               + "/ne-ref]/nwi:components/nwi:component"
               + "/nwi:component-id";
          }
          must "derived-from-or-self(../device-type,
               'nwi-passive:active-device')";
          description
            "Referenced connected active device's component,
             e.g. port component.";
        }
      }
    }
  }

  grouping connected-device-ref {
    description
      "Attributes applicable to connected devices.";

    container a-end {
      description
        "A-end device reference";
      uses connected-device-end;
    }

    container z-end {
      description
        "Z-end device reference";
      uses connected-device-end;
    }
  }

  grouping common-cable-attributes {
    description
      "Common attributes of cables applicable to the cable
       and its child cables.";
    leaf id {
      type string;
      description
        "Cable identifier.";
    }

    leaf length {
      type uint32;
      units "meter";
      description
        "Length of the cable in meter.";
    }

    uses connected-device-ref;
  }

  grouping optical-cable-attributes {
    description
      "Attributes applicable to fiber optic cables.";

    container optical-cable {
      when
        "derived-from-or-self(../cable-type, 'optical-fiber')";

      description
        "Container for attributes associated with fiber
         optic cables.";

      leaf fiber-core-num {
        type uint32;
        description
          "Number of fiber cores within the cable.";
      }
      leaf fiber-type {
        type identityref {
          base fiber-type;
        }
        description
          "Type of fiber contained in the cable.";
      }
      leaf attenuation {
        type decimal64 {
          fraction-digits 2;
        }
        units "dB";
        description
          "The fiber attenuation in dB.";
      }
    }
  }

  grouping cable-attributes {
    description
      "Attributes of cables.";

    uses common-cable-attributes;
    uses nwi:basic-common-entity-attributes;

    leaf cable-type {
      type identityref {
        base cable-type;
      }
      description
        "Type of cable.";
    }

    leaf cable-role {
      type identityref {
        base cable-role;
      }
      description
        "Role of cable.";
    }

    uses optical-cable-attributes;
  }

  grouping child-cables {
    description
      "Attributes applicable to child cables that are concatnated
       to form the cable.";

    list child-cable {
      key "index";
      min-elements 2;
      description
        "Ordered list of concatenated child cables.";

      leaf index {
        type uint8;
        description
          "An index number used to identify the concatenation
           order of the child cables.";
      }

      uses common-cable-attributes;
    }
  }

  grouping cables {
    description
      "Attributes applicable to cables.";

    list cable {
      key "id";
      description
        "List of cables.";

      uses cable-attributes;
      uses child-cables;
    }
  }

  grouping passive-device-ports {
    description
      "Attributes applicable to passive device ports.";

    list passive-port {
      key "id";
      description
        "List of ports on a passive device.";

      leaf id {
        type string;
        description
          "Port identifier.";
      }
      uses nwi:basic-common-entity-attributes;
      leaf port-type {
        type identityref {
          base passive-port-type;
        }
        description
          "Type of passive port.";
      }
      leaf fiber-core-num {
        type uint32;
        description
          "Number of fiber cores within the port.";
      }
    }
  }

  grouping passive-devices {
    description
      "Attributes applicable to passive devices.";

    list passive-device {
      key "id";
      description
        "List of passive devices.";

      leaf id {
        type string;
        description
          "Cable identifier.";
      }
      uses nwi:basic-common-entity-attributes;
      leaf device-type {
        type identityref {
          base passive-device-type;
        }
        description
          "Type of passive device.";
      }
      leaf-list custom-tags {
        type string;
        description
          "Customized tags, e.g. RFID, QR code that are
           attached to the device.";
      }
      leaf location-ref {
        type nil:ni-location-ref;
        description
          "Referenced location for the passive device.";
      }
      uses passive-device-ports;
    }
  }

  /* Augmentation */
  augment "/nwi:network-inventory" {
      description
        "Augment network inventory with information
         for optical cables and passive devices.";
      uses cables;
      uses passive-devices;
  }
}
