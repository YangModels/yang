module ietf-service-function-types {
  yang-version 1.1;

  namespace "urn:ietf:params:xml:ns:yang:ietf-service-function-types";
  prefix "service-types";

  organization "IETF SPRING Working Group";

  contact
      "WG Web:   <http://tools.ietf.org/wg/spring/>
       WG List:  <mailto:spring@ietf.org>

       Editor:   Jaganbabu Rajamanickam
                 <mailto:jrajaman@cisco.com>

       Editor:   Kamran Raza
                 <mailto:skraza@cisco.com>

       Editor:   Daniel Bernier
                 <mailto:daniel.bernier@bell.ca>

       Editor:   Gaurav Dawra
                 <mailto:gdawra.ietf@gmail.com>

       Editor:   Cheng Li
                 <mailto:c.l@huawei.com>";

  /*
   * Below are the definition for the service types
   * Any new service type could added by extending
   * this identity
   */
  identity service-function-type {
      description
        "Base identity from which specific service function
         types are derived.";
  }

  identity firewall {
      base service-function-type;
      description
        "Firewall Service type";
  }

  identity dpi {
      base service-function-type;
      description
        "Deep Packet Inspection Service type";
  }

  identity napt44 {
      base service-function-type;
      description
        "Network Address and Port Translation 44
         Service type";
  }

  identity classifier {
      base service-function-type;
      description
        "classifier Service type";
  }

  identity load-balancer {
      base service-function-type;
      description
        "load-balancer Service type";
  }

  identity ips {
      base service-function-type;
      description
        "Intrusion Prevention System Service type (Ex: Snort)";
  }

}
