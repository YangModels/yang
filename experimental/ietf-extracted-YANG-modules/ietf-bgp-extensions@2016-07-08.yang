module ietf-bgp-extensions {
  namespace "urn:ietf:params:xml:ns:yang:ietf-bgp-extensions";
  // replace with IANA namespace when assigned

  prefix bgp-ext;

  import ietf-inet-types {
    prefix inet;
  }

  import ietf-bgp {
    prefix bgp;
    revision-date 2016-01-06;
  }

  organization
    "Cisco Systems
     170 West Tasman Drive
     San Jose, CA 95134-1706
     USA";
  contact
     "Keyur Patel keyupate@cisco.com
      Dhanendra Jain   dhjain@cisco.com
      Susan Hares shares@ndzh.com";

  description
    "This YANG module defines the extensions to the base BGP yang
     model common across all of the vendor implementations of the
     protocol. It is intended that the model will be extended by
     vendors to define vendor-specific models.

     Terms and Acronyms

     AIGP (aigp): Accumulated IGP

     BGP (bgp): Border Gateway Protocol

     IGP (igp): Interior Gateway Protocol

     IP (ip): Internet Protocol

     IPv4 (ipv4):Internet Protocol Version 4

     IPv6 (ipv6): Internet Protocol Version 6

     MED(med): Multi Exit Discriminator

     MTU (mtu) Maximum Transmission Unit

    ";

  revision 2016-07-08 {
    description
      "Initial revision.";
    reference
      "RFC XXXX: A YANG Data Model for BGP extended features";
  }

  //
  // AIGP parameters used in global mode and neighbor AF mode.
  //
  grouping bgp-aigp {
    description
      "A set of configuration parameters applicable for AIGP configuration";
    container aigp {
      description "AIGP configuration parameters";
      leaf enable {
         type boolean;
         description "Enable AIGP";
      }
      leaf send-med {
         type boolean;
         description "Send AIGP value in MED";
      }
      container send-cost-community {
        description "Send AIGP value in Cost Community";
        leaf id {
          type uint32;
          description "Cost Community ID";
        }
        leaf igp-cost-transitive {
          type boolean;
          description "Enable transitive cost community";
        }
        leaf point-of-insertion {
          type enumeration {
            enum igp-cost {
              description "Cost community is used after IGP distance to next-hop";
            }
            enum pre-bestpath {
              description "Cost community is first step in best-path calculation";
            }
          }
          description "Point of insertion for best-path calculation";
        }
      }
    }
  }

  //
  // DMZ link bandwidth params
  //
  grouping bgp-dmz-link-bw {
    description
      "A set of configuration parameters for DMZ link bandwidth";
    leaf propagate-dmzlink-bw {
      type boolean;
      description
        "Propagate the DMZ link bandwidth.";
    }
  }

  //
  // BGP dampening params
  //
  grouping bgp-dampening-params {
    description "BGP dampening parameters";
    container bgp-dampening {
      description
      "BGP Route Flap Dampening.";

       leaf half-time {
         type uint8 {
           range "1..45";
         }
         description
          "Half Time (in minutes) to reduce the penalty
           assigned to a route by half.";
       }

       leaf reuse-limit {
         type uint16 {
           range "1..20000";
         }
         description
         "A configurable numeric value that is compared with the penalty.
          If the penalty is less than the reuse limit, a suppressed route
          that is up will no longer be suppressed. ";
       }

       leaf supresss-limit {
         type uint16 {
           range "1..20000";
         }
         description
         "A configurable numeric value that is compared with the penalty.
          If the penalty is greater than the suppress limit,
          the route is suppressed";
       }

       leaf max-supress-time {
         type uint8 {
           range "1..255";
         }
         description
         "The longest amount of time, in minutes, that a route can be suppressed.";
       }
       leaf policy {
         type string ; //TBD leafref to policy model
         description
          "Policy to specify criteria for dampening";
      }
    }
  }

  //
  // Grouping for Aggregate address
  //
  grouping bgp-aggregate-addr {
    description "BGP aggregate address parameters grouping";
    container aggregate-addr {
      description "Aggregate address configuration";
      leaf aggregate-address {
        type inet:ip-address;
        description
          "Configure BGP aggregate address.";
      }
      leaf summary-only {
        type boolean;
        description "Filter more specific routes from updates";
      }
      leaf as-set {
        type boolean;
        description "Generate AS set path information";
      }
      leaf as-confed-set {
        type boolean;
        description "Generate AS confed set path information";
      }
      leaf route-policy {
        type string;
        description "Policy to filter routes and specify conditions";
      }
    }
  }

  //
  // Grouping for soft reconfig
  //
  grouping soft-reconfig {
    description "Soft reconfig parameters. Configuring this enables storing
                 of routes as received by this node, prior to applying
                 inbound route-policy";
    leaf soft-reconfig {
      type enumeration {
        enum "always" {
          description "Use soft reconfig database upon neighbor reset even
                       if route refresh is configured";
        }
        enum "backup" {
          description "Use soft reconfig database as backup to route refresh";
        }
      }
      description "Enable storing of unprocessed routes as received by this node";
    }
  }

  //
  // Grouping for all AF extensions.
  //
  grouping bgp-af-extension-cfg {
    description
      "Grouping for configuration parameters which are applicable
       to all address families of the BGP router.";

    // Aggregate related
    uses bgp-aggregate-addr;

    // Aggregate Timer
    container aggregate-timer {
      description
        "Configure aggregation timer to specify time interval at which BGP routes
         will be aggregated for route aggregation.";
      leaf enable {
        type boolean;
        default "true";
        description "Enable aggregate timer";
      }
      leaf threshold {
        type uint16 {
          range "6..60";
        }
        description "Threshold value in seconds";
      }
    }

    //Network
    container network {
      description "Add networks to BGP table";
      leaf network {
         type inet:ip-address;
         description
           "Specify a network to announce via BGP.";
      }
      leaf policy {
         type string; //TBD leaf to policy model.
         description "Modify route attribute as per policy";
      }
    }

    // Dampening
    uses bgp-dampening-params;

    //Other leafs
    leaf auto-summary {
      type boolean;
      description
       "Enable automatic network number summarization";
    }
    // Best external
    leaf advertise-best-external {
      type boolean;
      description
        "Advertise best external path to the internal peers.";
    }
  }

  // Global mode extensions can go here.
  grouping bgp-gbl-extension-cfg {
     description "BGP process global extensions grouping";
     // BGP process global extensions here.
  }

  // Global address family specific extensions.
  grouping bgp-gbl-af-extension-cfg {
    description "BGP global address family specific extensions";

    //AF extensions common to all AFs
    uses bgp-af-extension-cfg;
  }

  // Neighbor mode extensions.
  grouping bgp-nbr-extension-cfg {
    description "BGP neighbor specific extensions";
    //NBR extensions go here
    uses bgp-dmz-link-bw;
  }

  // Neighbor address family specific extensions.
  grouping bgp-nbr-af-extension-cfg {
    description "BGP neighbor address-family specific extensions";
    // NBR-AF extensions go here
    uses bgp-aigp ;
    uses soft-reconfig;
  }

  //-----------------------------------
  // Augment BGP model in various places.
  //------------------------------------

  // BGP Global parameters
  augment "/bgp:bgp/bgp:global" {
     description "BGP global mode specific extensions";
     //add BGP global extensions here
     uses bgp-gbl-extension-cfg;
  }

  // BGP Global Address Family Specific
  augment "/bgp:bgp/bgp:global/bgp:afi-safis/bgp:afi-safi" {
     description "BGP global address family mode specific extensions";
      //add BGP global AF extensions here
      uses bgp-gbl-af-extension-cfg;
  }

  //BGP Neighbor Specific
  augment "/bgp:bgp/bgp:neighbors/bgp:neighbor" {
     description "BGP neighbor mode specific extensions";
      // add nbr specific extensions here
      uses bgp-nbr-extension-cfg;
  }

  //BGP Neighbor address-family Specific
  augment "/bgp:bgp/bgp:neighbors/bgp:neighbor/bgp:afi-safis/bgp:afi-safi" {
     description "BGP neighbor address family mode specific extensions";
      // add nbr AFI-SAFI specific extensions here.
      uses bgp-nbr-af-extension-cfg;
  }

  // BGP Neighbor Groups specific
  augment "/bgp:bgp/bgp:peer-groups/bgp:peer-group" {
     description "BGP peer-group mode specific extensions";
     // add nbr specific extensions here
      uses bgp-nbr-extension-cfg;
  }

  // BGP Neighbor Group address-family Specific.
  augment "/bgp:bgp/bgp:peer-groups/bgp:peer-group/bgp:afi-safis/bgp:afi-safi" {
     description "BGP peer-group address family mode specific extensions";
      // add nbr AFI-SAFI specific extensions here.
      uses bgp-nbr-af-extension-cfg;
  }
}
