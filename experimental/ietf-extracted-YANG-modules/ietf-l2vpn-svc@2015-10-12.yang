module ietf-l2vpn-svc {
  namespace "urn:ietf:params:xml:ns:yang:ietf-l2vpn-svc";

  prefix l2vpn-svc;

  import ietf-routing {
          prefix "rt";
      }

  import ietf-inet-types {
      prefix inet;
  }

  import ietf-yang-types {
      prefix yang;
  }

      import ietf-l3vpn-svc{
          prefix l3vpn-svc;
      }

  organization
   "IETF L3SM Working Group";

  contact
      "WG List:   <mailto:l3sm@ietf.org>

      Editor:

      ";

  description
      "The YANG module defines a generic service configuration
      model for Layer 2 VPN common across all of the vendor
      implementations.";

  revision 2015-10-12 {
      description
       "l2vpn first version.";
      reference "";
  }

/*identity*/
  identity bearer{
   description
       "base identity of bearer.";
  }

  identity ems{
   base bearer;
       description
       "identity of vpls ethernet mulitpoint service.";
  }

  identity emrs{
   base bearer;
   description
   "identity of vpls ethernet multipoint relay service.";
  }

  identity fr{
   base bearer;
       description
       "identity of Frame Relay";
  }

  identity ethernet{
   base bearer;
       description
       "identity of ethernet.";
  }

  identity atm{
   base bearer;
       description
       "identity of ATM.";
  }

  identity ppp-or-hdlc{
   base bearer;
       description
       "identity of PPP/HDLC.";
  }
     /* Groupings */

  container l2vpn-svc{
   description
       "this container contains several "
       +"l2vpn service parameters";
   list vpn-svc{
        key "name";
        description
        "list of layer 2 vpn service";
        uses l3vpn-svc:vpn-svc-cfg;
       }

       list sites{
        key "site-id";
        description
        "list of layer 2 vpn sites";
        leaf site-id{
         type string;
         description
         "site identifier";
        }

        // apply-template

        uses l3vpn-svc:operational-requirements;
        uses l3vpn-svc:customer-location-info;
        uses l3vpn-svc:site-diversity;
        uses l3vpn-svc:site-availability;
        uses l3vpn-svc:site-management;
        uses l3vpn-svc:site-vpn-policy;
         container customer-specific-information {
             leaf name {
                 type string;
                 description
                  "Name of the customer router.";
             }
             leaf autonomous-system {
                 type uint32;
                 description
                  "AS number.";
             }
             leaf interface {
                 type string;
                 description
                  "Interface reference of the access.";
             }
             list customer-lan-connection {
                 key "address";
                 leaf address {
                     type union {
                         type inet:ipv4-address;
                         type inet:ipv6-address;
                     }
                     description
                      "Address given by the customer on its LAN
                     for the SP router.";
                 }
                 leaf lan-protocol {
                     type identityref {
                         base rt:address-family;
                     }
                     description
                      "Transport protocol used on LAN.";
                 }
                                 leaf vc-label{
                                  type string;
                                  description
                                  "the vc label of l2vpn";
                                 }
                                 leaf mac-address{
                                  type yang:mac-address;
                              description
                              "mac address";
                                 }
                 description
                  "List of customer LAN to be connected
                  directly on the CE.";
             }
             container cascaded-lan-prefixes {
                 list ipv4-lan-prefixes {
                     key lan;

                     leaf lan {
                         type inet:ipv4-prefix;
                         description
                          "Lan prefixes.";
                     }
                     leaf lan-tag {
                         type string;
                         description
                          "Internal tag to be used in vpn
                          policies.";
                     }
                     leaf next-hop {
                         type inet:ipv4-address;
                         description
                          "Nexthop address to use at customer
                          side.";
                     }
                     description "
                         List of LAN prefixes for
                         the site.
                         ";
                 }
                 list ipv6-lan-prefixes {
                     key lan;

                     leaf lan {
                         type inet:ipv6-prefix;
                         description
                          "Lan prefixes.";
                     }
                     leaf lan-tag {
                         type string;
                         description
                          "Internal tag to be used
                          in vpn policies.";
                     }
                     leaf next-hop {
                         type inet:ipv6-address;
                         description
                          "Nexthop address to use at
                          customer side.";
                     }
                     description "
                         List of LAN prefixes for the site.
                         ";
                 }
                 description
                     "LAN prefixes from the customer.";
             }

             description
              "Customer premise configuration.";
         }

        container security{
         description
         "layer 2 vpn security parameters.";

         uses l3vpn-svc:site-security-authentication;
         uses l3vpn-svc:site-security-encryption;
         uses l3vpn-svc:site-security-acl;
        }

        container attachment{
         description
         "TBD";
         container bearer {
      leaf type {
       type identityref{
                base bearer;
               }
       description
        "Type of bearer Ethernet ...
         Operator specific.";
       }
      leaf bearer-reference {
        type string;
        description
        "This is an internal reference for the
         service provider.";
       }
      description
      "Bearer specific parameters.
       To be augmented.";
     }
         container l2-connection{
          leaf peer-id{
       type inet:ip-address;
           description
               "peer ip address.";}
                container ipv4{
         leaf address-allocation-type {
          type identityref {
           base l3vpn-svc:address-allocation-type;
          }
           description
           "Defines how addresses are allocated.
            Need to be detailed further.";
          }
         leaf subnet-prefix {
          type inet:ipv4-prefix;
           description
           "Interco subnet.";
          }
          description
          "IPv4 specific parameters";
                  }
        container ipv6 {
         leaf address-allocation-type {
          type string;
          description
           "Defines how addresses are allocated.
            Need to be detailled further.";
          }
         leaf subnet-prefix {
          type inet:ipv6-prefix;
          description
          "Interco subnet.";
                  }
          description
                  "IPv6 specific parameters";
          }
        container oam {
                 container bfd {
                 leaf bfd-enabled {
          type boolean;
          description
          "BFD activation";
         }
         choice holdtime {
          case profile {
           leaf profile-name {
           type string;
            description
            "Service provider well known profile.";
                        }
          description
                  "Service provider well
                  known profile.";
          }
          case fixed {
           leaf fixed-value {
            type uint32;
             units msec;
             description
             "Expected holdtime
              expressed
              in msec.";
           }
          }
          description
          "Choice for holdtime flavor.";}
          description
           "Container for BFD.";}
            description
                        "Define the OAM used on the connection.";}
             list routing-protocols {
              key type;
               leaf type {
                type identityref {
                base l3vpn-svc:routing-protocol-type;
                }
                                description
                                "Type of routing protocol.";
                }

               container ospf {
                when "type = 'ospf'" {
                 description
                  "Only applies
                  when protocol is OSPF.";
                  }
                 leaf-list address-family {
                  type identityref {
                                   base rt:address-family;
                  }
                  description
                   "Address family to be activated.";
                  }
                     leaf area-address {
                         type yang:dotted-quad;
                         description
                          "Area address.";
                     }
                     leaf metric {
                         type uint16;
                         description
                          "Metric of PE-CE link.";
                     }
                     list sham-link {
                         key target-site;

                         leaf target-site {
                             type leafref {
                              path "../../../../../../"
                              +"../sites/site-id";
                             }
                             description
                              "Target site for the sham link
                               connection.";
                         }
                         leaf metric {
                             type uint16;
                             description
                              "Metric of the sham link.";
                         }
                         description
                          "Creates a shamlink with another
                          site";
                     }
                     description
                      "OSPF specific configuration.";
                 }

                 container bgp {
                     when "type = 'bgp'" {
                         description
                          "Only applies when
                          protocol is BGP.";
                     }
                     leaf-list address-family {
                         type identityref {
                             base rt:address-family;
                         }
                         description
                          "Address family to be activated.";
                     }
                     description
                      "BGP specific configuration.";
                 }
                 container static {
                     when "type = 'static'" {
                         description
                          "Only applies when protocol
                          is static.";
                     }
                     leaf-list address-family {
                         type identityref {
                             base rt:address-family;
                         }
                         description
                          "Address family to be activated.";
                     }
                     description
                      "Static routing
                      specific configuration.";
                 }
                 container rip {
                     when "type = 'rip'" {
                         description
                          "Only applies when
                          protocol is RIP.";
                     }
                     leaf-list address-family {
                         type identityref {
                             base rt:address-family;
                         }
                         description
                          "Address family to be
                          activated.";
                     }

                     description
                      "RIP routing specific
                      configuration.";
                 }

                 container vrrp {
                     when "type = 'vrrp'" {
                         description
                          "Only applies when
                          protocol is VRRP.";
                     }
                     leaf-list address-family {
                         type identityref {
                             base rt:address-family;
                         }
                         description
                          "Address family to be activated.";
                     }
                     description
                      "VRRP routing specific configuration.";
                 }
                 description
                  "List of routing protocols used
                  on the site.
                  Need to be augmented.";
             }
             description
              "Defines connection parameters.";
          }
         }
        }

        container service{
         description
         "Service parameters on the attachement.";
         uses l3vpn-svc:site-service-basic;
         container qos{
          description
          "TBD.";
          container qos-classification-policy {
           description
               "QoS configuration";
       list rules {
                key id;
                description
                "list of qos rules.";
                leaf id {
         type uint16;
         description
         "ID of the rule.";
        }
                container match-flow{
                description
                "container of match flow.";
                leaf dest-mac-address{
                 type yang:mac-address;
                 description
                 "destination mac address.";
                }

                leaf src-mac-address{
                 type yang:mac-address;
                 description
                 "source mac address.";
                }

                leaf local-label{
                 type string;
                 description
                 "local label.";
                }

                leaf remote-label{
                 type string;
                 description
                 "remote label.";
                }

               leaf dot1q-vlan-bitmap {
                   type string;
           mandatory true;
           description "Dot1Q Vlan Bitmap." ;
       }

       leaf qinq-svlan-bitmap {
           type string;
                       mandatory true;
           description "QinQ svlan Bitmap." ;
       }

       leaf qinq-cvlan-bitmap {
           type string;
           mandatory true;
           description "QinQ cvlan Bitmap." ;
       }
       leaf target-class-id {
         type string;
         description
          "Identification of the
           class of service.
           This identifier is internal to
            the administration."; }
                }
             leaf std-qos-profile {
                 type string;
                 description
                  "QoS profile to be used";
             }
             container custom-qos-profile {
                 list class {
                     key class-id;

                     leaf class-id {
                         type string;
                         description
                          "Identification of the
                          class of service.
                          This identifier is internal to
                          the administration.";
                     }
                     leaf rate-limit {
                         type uint8;
                         units percent;
                         description
                          "To be used if class must
                          be rate
                          limited. Expressed as
                          percentage of the svc-bw.";
                     }
                     leaf priority-level {
                         type uint8;
                         description
                          "Defines the level of the
                          class in
                          term of priority queueing.
                           The higher the level is the
                           higher
                           is the priority.";
                     }
                     leaf guaranteed-bw-percent {
                         type uint8;
                         units percent;
                         description
                          "To be used to define the
                          guaranteed
                          BW in percent of the svc-bw
                          available at the priority-level.";
                     }
                     description
                      "List of class of services.";
                 }
                 description
                  "Custom qos profile.";
             }
       }
          }
         }
         uses l3vpn-svc:site-service-protection;
         uses l3vpn-svc:site-service-mpls;
         uses l3vpn-svc:site-service-multicast;
        }
       }

  }
