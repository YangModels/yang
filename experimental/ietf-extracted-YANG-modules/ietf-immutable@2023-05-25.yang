module ietf-immutable {
  yang-version 1.1;
  namespace "urn:ietf:params:xml:ns:yang:ietf-immutable";
  prefix im;

  import ietf-yang-metadata {
    prefix md;
  }
  import ietf-netconf {
    prefix nc;
    reference
      "RFC 6241: Network Configuration Protocol (NETCONF)";
  }
  import ietf-netconf-nmda {
    prefix ncds;
    reference
      "RFC 8526: NETCONF Extensions to Support the Network
       Management Datastore Architecture";
  }
  organization
    "IETF Network Modeling (NETMOD) Working Group";

  contact
    "WG Web: <https://datatracker.ietf.org/wg/netmod/>

     WG List: <mailto:netmod@ietf.org>

     Author: Qiufang Ma
             <mailto:maqiufang1@huawei.com>

     Author: Qin Wu
             <mailto:bill.wu@huawei.com>
     Author: Balazs Lengyel
             <mailto:balazs.lengyel@ericsson.com>

     Author: Hongwei Li
             <mailto:flycoolman@gmail.com>";

  description
    "This module defines a YANG extension and a metadata annotation
     both called 'immutable', to allow the server to formally
     document existing behavior on the mutability of some
     configuration nodes. Clients may use 'immutable' extension
     statements in the YANG, and annotations provided by the server
     to know beforehand when certain otherwise valid configuration
     requests will cause the server to return an error.

     Copyright (c) 2023 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC HHHH
     (https://www.rfc-editor.org/info/rfcHHHH); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2023-05-25 {
    description
      "Initial revision.";
    // RFC Ed.: replace XXXX and remove this comment
    reference
      "RFC XXXX: YANG Extension and Metadata Annotation for
       Immutable Flag";
  }

  extension immutable {
    argument value;
    description
      "If servers always reject client modification attempts to
       some data node that can only be created, modified and
       deleted by the device itself, an 'immutable' YANG extension
       can be used to formally indicate to the client.

       The statement MUST only be a substatement to a 'config true'
       leaf, leaf-list, container, list, anydata or anyxml
       statement. Zero or one immutable statement per parent
       statement is allowed.

       No substatements are allowed.

       The argument of the 'immutable' statement defines the value,
       indicating whether the node is immutable or not.

       Adding immutable of an existing immutable statement
       is non-backwards compatible changes.
       Other changes to immutable are backwards compatible.";
  }

  md:annotation immutable {
    type boolean;
    description
      "If servers always reject clients modification to some
       particular instance that can only be created, modified and
       deleted by the device itself, an 'immutable' metadata
       annotation can be used to formally indicate to the clients.
       The 'immutable' annotation indicates the immutability of an
       instantiated data node.

       The 'immutable' metadata annotation takes as a value 'true'
       or 'false'. If the 'immutable' metadata annotation for data
       node instances is not specified, the default value is false.
       Explicitly annotating instances as immutable=true has the
       same effect as not specifying this value.";
  }

  grouping with-immutable-grouping {
    description
      "define the with-immutable grouping.";
    leaf with-immutable {
      type empty;
      description
        "If this parameter is present, the server will return the
         'immutable' annotation for configuration that it
         internally thinks it immutable. When present, this
         parameter allows the server to formally document existing
         behavior on the mutability of some configuration nodes.";
    }
  }
  augment "/ncds:get-data/ncds:input" {
    description
      "Allows the server to include 'immutable' metadata
       annotations in its response to get-data operation.";
    uses with-immutable-grouping;
  }
  augment "/nc:get-config/nc:input" {
    description
      "Allows the server to include 'immutable' metadata
       annotations in its response to get-config operation.";
    uses with-immutable-grouping;
  }
  augment "/nc:get/nc:input" {
    description
      "Allows the server to include 'immutable' metadata
       annotations in its response to get operation.";
    uses with-immutable-grouping;
  }
}
