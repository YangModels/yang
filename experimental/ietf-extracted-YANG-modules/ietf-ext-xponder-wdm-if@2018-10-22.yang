module ietf-ext-xponder-wdm-if {
    namespace "urn:ietf:params:xml:ns:yang:ietf-ext-xponder-wdm-if";
    prefix ietf-ext-xponder-wdm-if;

    import ietf-interfaces {
      prefix if;
     }

     organization
       "IETF CCAMP
       Working Group";

     contact
       "WG Web:   <http://tools.ietf.org/wg/ccamp/>
        WG List:  <mailto:ccamp@ietf.org>

        Editor:   Dharini Hiremagalur
                  <mailto:dharinih@juniper.net>";

     description
       "This module contains a collection of YANG definitions for
        configuring Optical interfaces.

        Copyright (c) 2016 IETF Trust and the persons identified
        as authors of the code.  All rights reserved.

        Redistribution and use in source and binary forms, with or
        without modification, is permitted pursuant to, and
        subject to the license terms contained in, the Simplified
        BSD License set forth in Section 4.c of the IETF Trust's
        Legal Provisions Relating to IETF Documents
        (http://trustee.ietf.org/license-info).";

    revision "2018-10-22" {
           description
               "Revision 1.2";
           reference
               "";
    }

    revision "2018-03-06" {
           description
               "Revision 1.1";
           reference
               "";
    }

    revision "2017-03-06" {
           description
               "Revision 1.0";
           reference
               "";
    }
    revision "2016-03-17" {
           description
               "Initial revision.";
           reference
               "";
    }

     typedef dbm-t {
       type decimal64 {
         fraction-digits 2;
         range "-50..-30 | -10..5 | 10000000";
       }
       description "
         Amplifier Power in dBm ";
     }
     typedef opt-if-och-tca-types {

         type enumeration {
             enum max-laser-linewdt {
               description " The maximum laser linewidth";
             }
             enum min-tx-power-tca {
               description " The min tx power tca";
             }
             enum max-tx-power-tca {
               description " The min tx power tca";
             }
             enum min-rx-power-tca{
               description " The min tx power tca";
             }
             enum max-rx-power-tca{
               description " The min tx power tca";
             }
             enum max-pol-power-diff-tca{
               description " The power diff. between polariz. tca";
             }
             enum max-pol-skew-diff-tca{
               description " The Skew between the two polariz. tca";
             }
             enum min-frequency-offset-tca{
               description " Min Frequency offset tca";
             }
             enum max-frequency-offset-tca{
               description " Max Frequency offset tca";
             }
             enum min-osnr-tca{
               description " Min OSNR tca";
             }
             enum max-osnr-tca{
               description " Max OSNR tca";
             }
             enum min-laser-temperature-tca{
               description " The min tx power tca";
             }
             enum max-laser-temperature-tca{
               description " Temperature tca";
             }
             enum min-fec-ber-tca{
               description " Min Pre Fec BER tca";
             }
             enum max-fec-ber-tca{
               description " Max Pre Fec BER tca";
             }
             enum min-q-tca{
               description "Min Q tca";
             }
             enum max-q-tca {
               description "Max Q tca";
             }
         }
         description " The different types of TCA's";
     }

     grouping opt-if-och-power {
        description "Interface optical Power";
        leaf output-power {
            type int32;
            units ".01dbm";
            description "The output power for this interface
                          in .01 dBm.
                          The setting of the output power is
                           optional";
        }

        leaf input-power {
             type int32;
             units ".01dbm";
             config false;
             description "The current input power of this
                   interface";
        }
    }

     grouping opt-if-och-tca-thresholds {
          description "Thresholds for TCA's";
          leaf  tca-type {
             type opt-if-och-tca-types;
             description  "type of the TCA eg TX Power";
          }
          leaf  min-threshold {
            type int32;
            description " A TCA is generated if the variable is
                          less than this value";

           }
           leaf  max-threshold {
            type int32;
            description " A TCA is generated if the variable is
                          more than this value";
           }
      }

      grouping opt-if-och-fec {
          description "Fec info";
          leaf fec-info {
             type string {
                length "1..255";
             }
             config false;
             description
                      "Fec Type - eg GFEC";
         }
         leaf fec-bitrate {
             type string {
                 length "1..255";
             }
             config false;
             description
                      "Fec Overhead rate ";
         }
         leaf fec-gain {
            type string {
                length "1..255";
            }
            config false;
            description
                      "Fec Overhead rate ";
          }
          leaf  fec-ber-mantissa-threshold {
            type uint32;
            description " Mantissa of the FEC BER threshold";

           }
           leaf  fec-ber-exponent-threshold {
             type int32;
             description " Exponent of the FEC BER threshold";
           }
      }

      grouping opt-if-och-central-frequency {
          description "Interface Central Frequency";
          leaf  central-frequency {
            type uint32;
            description " This parameter indicates the frequency
                          of this interface ";
           }
      }

      }
