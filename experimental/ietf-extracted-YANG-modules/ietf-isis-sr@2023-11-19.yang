module ietf-isis-sr {
  yang-version 1.1;
  namespace "urn:ietf:params:xml:ns:yang:ietf-isis-sr";

  prefix isis-sr;

  import ietf-routing {
    prefix rt;
    reference
      "RFC 8349 - A YANG Data Model for Routing
                  Management (NMDA Version)";
  }

  import ietf-inet-types {
    prefix inet;
    reference
      "RFC 6991 - Common YANG Data Types";
  }

  import ietf-segment-routing-common {
    prefix sr-cmn;
    reference
      "RFC 9020 - YANG Data Model for Segment Routing";
  }

  import ietf-segment-routing-mpls {
    prefix sr-mpls;
    reference
      "RFC 9020 - YANG Data Model for Segment Routing";
  }

  import ietf-isis {
    prefix isis;
    reference
      "RFC 9130 - YANG Data Model for IS-IS Protocol";
  }

  import iana-routing-types {
    prefix iana-rt-types;
    reference
      "RFC 8294 - Common YANG Data Types for the Routing Area";
  }

  import ietf-routing-types {
    prefix rt-types;
    reference
      "RFC 8294 - Common YANG Data Types for the Routing Area";
  }

  organization
    "IETF LSR - Link State Routing Working Group";
  contact
    "WG Web:   <https://datatracker.ietf.org/wg/lsr/>
     WG List:  <mailto:lsr@ietf.org>

     Author:    Stephane Litkowski
                <mailto:slitkows.ietf@gmail.com>
     Author:    Yingzhen Qu
                <mailto:yingzhen.ietf@gmail.com.com>
     Author:    Acee Lindem
                <mailto:acee.ietf@gmail.com>
     Author:    Pushpasis Sarkar
                <mailto:pushpasis.ietf@gmail.com>
     Author:    Ing-Wher Chen
                <mailto:ingwherchen@mitre.org>
     Author:    Jeff Tantsura
                <mailto:jefftant.ietf@gmail.com>
    ";
  description
    "The YANG module defines the generic configuration and
     operational state for Segment Routing ISIS extensions, which is
     common across all of the vendor implementations.

     This YANG model conforms to the Network Management
     Datastore Architecture (NMDA) as described in RFC 8342.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     This version of this YANG module is part of RFC XXXX;
     see the RFC itself for full legal notices.";
  reference
    "RFC XXXX";

  revision 2023-11-19 {
    description
      "Initial revision.";
    reference
      "RFC XXXX: A YANG Data Model for IS-IS Segment Routing";
  }

  /* Identities */

  identity sr-capability {
    description
      "Base identity for ISIS SR-Capabilities sub-TLV flgs";
  }

  identity mpls-ipv4 {
    base sr-capability;
    description
      "If set, then the router is capable of
       processing SR MPLS encapsulated IPv4 packets
       on all interfaces.";
  }
  identity mpls-ipv6 {
    base sr-capability;
    description
      "If set, then the router is capable of
       processing SR MPLS encapsulated IPv6 packets
       on all interfaces.";
  }

  identity prefix-sid-bit {
    description
      "Base identity for prefix sid sub-tlv bits.";
  }

  identity r-bit {
    base prefix-sid-bit;
    description
      "Re-advertisement Flag.";
  }

  identity n-bit {
    base prefix-sid-bit;
    description
      "Node-SID Flag.";
  }

  identity p-bit {
    base prefix-sid-bit;
    description
      "No-PHP (No Penultimate Hop-Popping) Flag.";
  }

  identity e-bit {
    base prefix-sid-bit;
    description
      "Explicit NULL Flag.";
  }

  identity v-bit {
    base prefix-sid-bit;
    description
      "Value Flag.";
  }

  identity l-bit {
    base prefix-sid-bit;
    description
      "Local Flag.";
  }
  identity adj-sid-bit {
    description
      "Base identity for adj sid sub-tlv bits.";
  }

  identity f-bit {
    base adj-sid-bit;
    description
      "Address-Family flag.";
  }

  identity b-bit {
    base adj-sid-bit;
    description
      "Backup flag.";
  }

  identity vi-bit {
    base adj-sid-bit;
    description
      "Value/Index flag.";
  }

  identity lo-bit {
    base adj-sid-bit;
    description
      "Local flag.";
  }

  identity s-bit {
    base adj-sid-bit;
    description
      "Group flag.";
  }

  identity pe-bit {
    base adj-sid-bit;
    description
      "Persistent flag.";
  }

  identity sid-binding-bit {
    description
      "Base identity for sid binding tlv bits.";
  }

  identity af-bit {
    base sid-binding-bit;
    description
      "Address-Family flag.";
  }

  identity m-bit {
    base sid-binding-bit;
    description
      "Mirror Context flag.";
  }

  identity sf-bit {
    base sid-binding-bit;
    description
      "S flag. If set, the binding label tlv should be flooded
       across the entire routing domain.";
  }

  identity d-bit {
    base sid-binding-bit;
    description
      "Leaking flag.";
  }

  identity a-bit {
    base sid-binding-bit;
    description
      "Attached flag.";
  }

  /* Features */

  feature remote-lfa-sr {
    description
      "Enhance rLFA to use SR path.";
    reference
      "RFC 8102: Remote-LFA Node Protection and Manageability";
  }

  feature ti-lfa {
    description
      "Topology-Independent Loop-Free Alternate (TI-LFA)
       computation using segment routing.";
  }

  /* Groupings */

  grouping sid-sub-tlv {
    description
      "SID/Label sub-TLV grouping.";
    container sid-sub-tlv {
      description
        "Used to advertise the SID/Label associated with a
         prefix or adjacency.";
      leaf sid {
        type uint32;
        description
          "Segment Identifier (SID) - A 20 bit label or
           32 bit SID.";
      }
    }
  }

  grouping sr-capability {
    description
      "SR capability grouping.";
    container sr-capability {
      description
        "Segment Routing capability.";
      container sr-capability {
        leaf-list sr-capability-bits {
          type identityref {
            base sr-capability;
          }
          description
            "SR Capability sub-tlv flags list.";
        }
        description
          "SR Capability Flags.";
      }
      container global-blocks {
        description
          "Segment Routing Global Blocks.";
        list global-block {
          description
            "Segment Routing Global Block.";
          leaf range-size {
            type uint32;
            description
              "The SID range.";
          }
          uses sid-sub-tlv;
        }
      }
    }
  }

  grouping sr-algorithm {
    description
      "SR algorithm grouping.";
    container sr-algorithms {
      description
        "All SR algorithms.";
      leaf-list sr-algorithm {
        type identityref {
          base sr-cmn:prefix-sid-algorithm;
        }
        description
          "The Segment Routing (SR) algorithms that the router is
           currently using.";
      }
    }
  }

  grouping srlb {
    description
      "SR Local Block grouping.";
    container local-blocks {
      description
        "List of SRLBs.";
      list local-block {
        description
          "Segment Routing Local Block.";
        leaf range-size {
          type rt-types:uint24;
          description
            "The SID range.";
        }
        uses sid-sub-tlv;
      }
    }
  }

  grouping srms-preference {
    description
      "The SRMS preference TLV is used to advertise
       a preference associated with the node that acts
       as an SR Mapping Server.";
    container srms-preference {
      description
        "SRMS Preference TLV.";
      leaf preference {
        type uint8 {
          range "0 .. 255";
        }
        description
          "SRMS preference TLV, value from 0 to 255.";
      }
    }
  }

  grouping adjacency-state {
    description
      "This group will extend adjacency state.";
    list adjacency-sid {
      key "value";
      config false;
      leaf value {
        type uint32;
        description
          "Value of the Adj-SID.";
      }
      leaf af {
        type iana-rt-types:address-family;
        description
          "Address-family associated with the
           segment ID";
      }
      leaf weight {
        type uint8;
        description
          "Weight associated with
           the adjacency SID.";
      }
      leaf protection-requested {
        type boolean;
        description
          "Describe if the adjacency SID
           must be protected.";
      }
      description
        "List of adjacency Segment IDs.";
    }
  }

  grouping prefix-segment-id {
    description
      "This group defines segment routing extensions
       for prefixes.";
    list sid-list {
      key "value";
      leaf value {
        type uint32;
        description
          "Value of the prefix-SID.";
      }
      container perfix-sid-flags {
        leaf-list bits {
          type identityref {
            base prefix-sid-bit;
          }
          description
            "Prefix SID Sub-TLV flag bits list.";
        }
        description
          "Describes flags associated with the
           segment ID.";
      }
      leaf algorithm {
        type identityref {
          base sr-cmn:prefix-sid-algorithm;
        }
        description
          "Algorithm to be used for path computation.";
      }
      description
        "List of segments.";
    }
  }

  grouping adjacency-segment-id {
    description
      "This group defines segment routing extensions
       for adjacencies.";
    list sid-list {
      key "value";
      leaf value {
        type uint32;
        description
          "Value of the Adj-SID.";
      }
      container adj-sid-flags {
        leaf-list bits {
          type identityref {
            base adj-sid-bit;
          }
          description
            "Adj sid sub-tlv flags list.";
        }
        description
          "Adj-sid sub-tlv flags.";
      }
      leaf weight {
        type uint8;
        description
          "The value represents the weight of the Adj-SID
           for the purpose of load balancing.";
      }
      leaf neighbor-id {
        type isis:system-id;
        description
          "Describes the system ID of the neighbor
           associated with the SID value. This is only
           used on LAN adjacencies.";
      }
      description
        "List of segments.";
    }
  }

  grouping segment-routing-binding-tlv {
    list segment-routing-bindings {
      key "prefix range";
      leaf prefix {
        type inet:ip-prefix;
        description
          "The prefix represents the Forwarding Equivalence
           Class at the tail end of the advertised path.";
      }
      leaf range {
        type uint16;
        description
          "Describes number of elements to assign
           a binding to.";
      }
      container sid-binding-flags {
        leaf-list bits {
          type identityref {
            base sid-binding-bit;
          }
          description
            "SID Binding TLV flag bits list.";
        }
        description
          "Binding flags.";
      }
      container binding {
        container prefix-sid {
          uses prefix-segment-id;
          description
            "Binding prefix SID to the range.";
        }
        description
          "Bindings associated with the range.";
      }
      description
        "This container describes list of SID/Label bindings.
         ISIS reference is TLV 149.";
    }
    description
      "Defines binding TLV for database.";
  }

  /* Configuration */

  augment "/rt:routing/"
        + "rt:control-plane-protocols/rt:control-plane-protocol"
        + "/isis:isis" {
    when "derived-from-or-self(../rt:type, 'isis:isis')" {
      description
        "This augment ISIS routing protocol when used";
    }
    description
      "This augments ISIS protocol configuration
       with segment routing.";
    uses sr-mpls:sr-control-plane;
    container protocol-srgb {
      if-feature "sr-mpls:protocol-srgb";
      uses sr-cmn:srgb;
      description
        "Per-protocol SRGB.";
    }
  }

  augment "/rt:routing/"
        + "rt:control-plane-protocols/rt:control-plane-protocol"
        + "/isis:isis/isis:interfaces/isis:interface" {
    when "derived-from-or-self(../../../rt:type, 'isis:isis')" {
      description
        "This augment ISIS routing protocol when used";
    }
    description
      "This augments ISIS protocol configuration
       with segment routing.";
    uses sr-mpls:igp-interface;
  }

  augment "/rt:routing/"
        + "rt:control-plane-protocols/rt:control-plane-protocol"
        + "/isis:isis/isis:interfaces/isis:interface"
        + "/isis:fast-reroute/isis:lfa" {
    when "derived-from-or-self(../../../../../rt:type,"
        + "'isis:isis')" {
      description
        "This augment ISIS routing protocol when used";
    }
    description
      "This augments ISIS interface IP FRR with TILFA.";
    container ti-lfa {
      if-feature "ti-lfa";
      leaf enable {
        type boolean;
        default false;
        description
          "Enables TI-LFA computation.";
      }
      container selection-tie-breakers {
        container node-protection {
          presence "Presence of container enables the node
                    protection tie-breaker";
          leaf priority {
            type uint8;
            default 128;
            description
              "Priority for node protection tie-breaker with
               a lower priority being more preferred.";
          }
          description
            "Enable node protection as a TI-LFA path
             selection tie-breaker. A path providing node
             protection will be selected over one that
             doesn't provide node protection.";
        }
        container srlg-disjoint {
          presence "Presence of container enables the SRLG
                    disjoint tie-breaker";
          leaf priority {
            type uint8;
            default 128;
            description
              "Priority for SRLG disjoint tie-breaker with
               a lower priority being more preferred.";
          }
          description
            "Enable SRLG (Shared Resource Link Group)
             disjoint  as a TI-LFA path selection tie-breaker.
             A path providing node a disjoint path for SRLG
             links from the primary path will be selected over
             one that doesn't provide an SRLG disjoint path.";
        }
        description
          "Configure path selection tie-breakers and their
           respective priorities for the TI-LFA computation.";
      }
      description
        "Topology Independent Loop Free Alternate
         (TI-LFA) support.";
    }
  }

  augment "/rt:routing/"
        + "rt:control-plane-protocols/rt:control-plane-protocol"
        + "/isis:isis/isis:interfaces/isis:interface"
        + "/isis:fast-reroute/isis:lfa/isis:level-1" {
    when "derived-from-or-self(../../../../../../rt:type,"
        + "'isis:isis')" {
      description
        "This augment ISIS routing protocol when used";
    }
    description
      "This augments ISIS interface level-1 IP FRR with TILFA.";
    container ti-lfa {
      if-feature "ti-lfa";
      leaf enable {
        type boolean;
        default false;
        description
          "Enables TI-LFA computation.";
      }
      description
        "TI-LFA configuration.";
    }
  }

  augment "/rt:routing/"
        + "rt:control-plane-protocols/rt:control-plane-protocol"
        + "/isis:isis/isis:interfaces/isis:interface"
        + "/isis:fast-reroute/isis:lfa/isis:level-2" {
    when "derived-from-or-self(../../../../../../rt:type,"
        + "'isis:isis')" {
      description
        "This augment ISIS routing protocol when used";
    }
    description
      "This augments ISIS IP interface level-2 FRR with TILFA.";
    container ti-lfa {
      if-feature "ti-lfa";
      leaf enable {
        type boolean;
        default false;
        description
          "Enables TI-LFA computation.";
      }
      description
        "TI-LFA configuration.";
    }
  }

  augment "/rt:routing/"
        + "rt:control-plane-protocols/rt:control-plane-protocol"
        + "/isis:isis/isis:interfaces/isis:interface"
        + "/isis:fast-reroute/isis:lfa/isis:remote-lfa" {
    when "derived-from-or-self(../../../../../../rt:type,"
          + "'isis:isis')" {
      description
        "This augment ISIS routing protocol when used";
    }
    description
      "This augments ISIS remoteLFA config with
       use of segment-routing path.";
    leaf use-segment-routing-path {
      if-feature "remote-lfa-sr";
      type boolean;
      default false;
      description
        "Force remote LFA to use segment routing path instead of LDP
         path. The value of this leaf is in effect only when
         remote-lfa is enabled.";
    }
  }

  /* Operational states */

  augment "/rt:routing/"
        + "rt:control-plane-protocols/rt:control-plane-protocol"
        + "/isis:isis/isis:interfaces/isis:interface"
        + "/isis:adjacencies/isis:adjacency" {
    when "derived-from-or-self(../../../../../rt:type, 'isis:isis')" {
      description
        "This augment ISIS routing protocol when used";
    }
    description
      "This augments ISIS protocol configuration
       with segment routing.";
    uses adjacency-state;
  }

  augment "/rt:routing/"
        + "rt:control-plane-protocols/rt:control-plane-protocol"
        + "/isis:isis/isis:database/isis:levels/isis:lsp"
        + "/isis:router-capabilities" {
    when "derived-from-or-self(../../../../../rt:type, 'isis:isis')" {
      description
        "This augment ISIS routing protocol when used";
    }
    description
      "This augments ISIS protocol LSDB router capability.";
    uses sr-capability;
    uses sr-algorithm;
    uses srlb;
    uses srms-preference;
  }

  augment "/rt:routing/"
        + "rt:control-plane-protocols/rt:control-plane-protocol"
        + "/isis:isis/isis:database/isis:levels/isis:lsp"
        + "/isis:extended-is-neighbor/isis:neighbor" {
    when "derived-from-or-self(../../../../../../rt:type,"
          + "'isis:isis')" {
      description
        "This augment ISIS routing protocol when used";
    }
    description
      "This augments ISIS protocol LSDB neighbor.";
    uses adjacency-segment-id;
  }

  augment "/rt:routing/"
        + "rt:control-plane-protocols/rt:control-plane-protocol"
        + "/isis:isis/isis:database/isis:levels/isis:lsp"
        + "/isis:mt-is-neighbor/isis:neighbor" {
    when "derived-from-or-self(../../../../../../rt:type,"
          + "'isis:isis')" {
      description
        "This augment ISIS routing protocol when used";
    }
    description
      "This augments ISIS protocol LSDB neighbor.";
    uses adjacency-segment-id;
  }

  augment "/rt:routing/"
        + "rt:control-plane-protocols/rt:control-plane-protocol"
        + "/isis:isis/isis:database/isis:levels/isis:lsp"
        + "/isis:extended-ipv4-reachability/isis:prefixes" {
    when "derived-from-or-self(../../../../../../rt:type,"
          + "'isis:isis')" {
      description
        "This augment ISIS routing protocol when used";
    }
    description
      "This augments ISIS protocol LSDB prefix.";
    uses prefix-segment-id;
  }

  augment "/rt:routing/"
        + "rt:control-plane-protocols/rt:control-plane-protocol"
        + "/isis:isis/isis:database/isis:levels/isis:lsp"
        + "/isis:mt-extended-ipv4-reachability/isis:prefixes" {
    when "derived-from-or-self(../../../../../../rt:type,"
          + "'isis:isis')" {
      description
        "This augment ISIS routing protocol when used";
    }
    description
      "This augments ISIS protocol LSDB prefix.";
    uses prefix-segment-id;
  }

  augment "/rt:routing/"
        + "rt:control-plane-protocols/rt:control-plane-protocol"
        + "/isis:isis/isis:database/isis:levels/isis:lsp"
        + "/isis:ipv6-reachability/isis:prefixes" {
    when "derived-from-or-self(../../../../../../rt:type,"
          + "'isis:isis')" {
      description
        "This augment ISIS routing protocol when used";
    }
    description
      "This augments ISIS protocol LSDB prefix.";
    uses prefix-segment-id;
  }

  augment "/rt:routing/"
        + "rt:control-plane-protocols/rt:control-plane-protocol"
        + "/isis:isis/isis:database/isis:levels/isis:lsp"
        + "/isis:mt-ipv6-reachability/isis:prefixes" {
    when "derived-from-or-self(../../../../../../rt:type,"
          + "'isis:isis')" {
      description
        "This augment ISIS routing protocol when used";
    }
    description
      "This augments ISIS protocol LSDB prefix.";
    uses prefix-segment-id;
  }

  augment "/rt:routing/"
        + "rt:control-plane-protocols/rt:control-plane-protocol"
        + "/isis:isis/isis:database/isis:levels/isis:lsp" {
    when "derived-from-or-self(../../../../rt:type,"
          + "'isis:isis')" {
      description
        "This augment ISIS routing protocol when used";
    }
    description
      "This augments ISIS protocol LSDB.";
    uses segment-routing-binding-tlv;
  }

  /* Notifications */
}
