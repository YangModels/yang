module ietf-i2nsf-capability {
  yang-version 1.1;
  namespace
    "urn:ietf:params:xml:ns:yang:ietf-i2nsf-capability";
  prefix
    nsfcap;

  organization
    "IETF I2NSF (Interface to Network Security Functions)
     Working Group";

  contact
    "WG Web: <http://tools.ietf.org/wg/i2nsf>
     WG List: <mailto:i2nsf@ietf.org>

     WG Chair: Linda Dunbar
     <mailto:ldunbar@futurewei.com>

     WG Chair: Yoav Nir
     <mailto:ynir.ietf@gmail.com>

     Editor: Susan Hares
     <mailto:shares@ndzh.com>

     Editor: Jaehoon Paul Jeong
     <mailto:pauljeong@skku.edu>
     Editor: Jinyong Tim Kim
     <mailto:timkim@skku.edu>";

  description
    "This module describes a capability model for I2NSF devices.

    Copyright (c) 2020 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8341; see
    the RFC itself for full legal notices.";

  revision "2020-07-13"{
    description "Initial revision.";
    reference
      "RFC XXXX: I2NSF Capability YANG Data Model";
  }

  /*
   * Identities
   */

  identity event {
    description
      "Base identity for I2NSF policy events.";
    reference
      "draft-ietf-i2nsf-nsf-monitoring-data-model-03
       - Event";
  }

  identity system-event-capability {
    base event;
    description
      "Identity for system events";
    reference
      "draft-ietf-i2nsf-nsf-monitoring-data-model-03
       - System alarm";
  }

  identity system-alarm-capability {
    base event;
    description
      "Identity for system alarms";
    reference
      "draft-ietf-i2nsf-nsf-monitoring-data-model-03
       - System alarm";
  }

  identity access-violation {
    base system-event-capability;
    description
      "Identity for access violation events";
    reference
      "draft-ietf-i2nsf-nsf-monitoring-data-model-03
       - System event";
  }

  identity configuration-change {
    base system-event-capability;
    description
      "Identity for configuration change events";
    reference
      "draft-ietf-i2nsf-nsf-monitoring-data-model-03
       - System event";
  }

  identity memory-alarm {
    base system-alarm-capability;
    description
      "Identity for memory alarm events";
    reference
      "draft-ietf-i2nsf-nsf-monitoring-data-model-03
       - System alarm";
  }

  identity cpu-alarm {
    base system-alarm-capability;
    description
      "Identity for CPU alarm events";
    reference
      "draft-ietf-i2nsf-nsf-monitoring-data-model-03
       - System alarm";
  }

  identity disk-alarm {
    base system-alarm-capability;
    description
      "Identity for disk alarm events";
    reference
      "draft-ietf-i2nsf-nsf-monitoring-data-model-03
       - System alarm";
  }

  identity hardware-alarm {
    base system-alarm-capability;
    description
      "Identity for hardware alarm events";
    reference
      "draft-ietf-i2nsf-nsf-monitoring-data-model-03
       - System alarm";
  }

  identity interface-alarm {
    base system-alarm-capability;
    description
      "Identity for interface alarm events";
    reference
      "draft-ietf-i2nsf-nsf-monitoring-data-model-03
       - System alarm";
  }

  identity condition {
    description
      "Base identity for policy conditions";
  }

  identity context-capability {
    base condition;
    description
      "Identity for context condition capabilities";
  }

  identity acl-number {
    base context-capability;
    description
      "Identity for ACL number condition capability";
  }

  identity application {
    base context-capability;
    description
      "Identity for application condition capability";
  }

  identity target {
    base context-capability;
    description
      "Identity for target condition capability";
  }

  identity user {
    base context-capability;
    description
      "Identity for user condition capability";
  }

  identity group {
    base context-capability;
    description
      "Identity for group condition capability";
  }

  identity geography {
    base context-capability;
    description
      "Identity for geography condition capability";
  }

  identity ipv4-capability {
    base condition;
    description
      "Identity for IPv4 condition capabilities";
    reference
      "RFC 791: Internet Protocol";
  }

  identity exact-ipv4-header-length {
    base ipv4-capability;
    description
      "Identity for exact-match IPv4 header-length
      condition capability";
    reference
      "RFC 791: Internet Protocol - Header Length";
  }

  identity range-ipv4-header-length {
    base ipv4-capability;
    description
      "Identity for range-match IPv4 header-length
      condition capability";
    reference
      "RFC 791: Internet Protocol - Header Length";
  }

  identity ipv4-tos {
    base ipv4-capability;
    description
      "Identity for IPv4 Type-Of-Service (TOS)
      condition capability";
    reference
      "RFC 791: Internet Protocol - Type of Service";
  }

  identity exact-ipv4-total-length {
    base ipv4-capability;
    description
      "Identity for exact-match IPv4 total length
      condition capability";
    reference
      "RFC 791: Internet Protocol - Total Length";
  }

  identity range-ipv4-total-length {
    base ipv4-capability;
    description
      "Identity for range-match IPv4 total length
      condition capability";
    reference
      "RFC 791: Internet Protocol - Total Length";
  }

  identity ipv4-id {
    base ipv4-capability;
    description
      "Identity for identification condition capability";
    reference
      "RFC 791: Internet Protocol - Identification";
  }

  identity ipv4-fragment-flags {
    base ipv4-capability;
    description
      "Identity for IPv4 fragment flags condition capability";
    reference
      "RFC 791: Internet Protocol - Fragmentation Flags";
  }

  identity exact-ipv4-fragment-offset {
    base ipv4-capability;
    description
      "Identity for exact-match IPv4 fragment offset
      condition capability";
    reference
      "RFC 791: Internet Protocol - Fragmentation Offset";
  }

  identity range-ipv4-fragment-offset {
    base ipv4-capability;
    description
      "Identity for range-match IPv4 fragment offset
      condition capability";
    reference
      "RFC 791: Internet Protocol - Fragmentation Offset";
  }

  identity exact-ipv4-ttl {
    base ipv4-capability;
    description
      "Identity for exact-match IPv4 Time-To-Live (TTL)
      condition capability";
    reference
      "RFC 791: Internet Protocol - Time To Live (TTL)";
  }

  identity range-ipv4-ttl {
    base ipv4-capability;
    description
      "Identity for range-match IPv4 Time-To-Live (TTL)
      condition capability";
    reference
      "RFC 791: Internet Protocol - Time To Live (TTL)";
  }

  identity ipv4-protocol {
    base ipv4-capability;
    description
      "Identity for IPv4 protocol condition capability";
    reference
      "RFC 790: Assigned numbers - Assigned Internet
       Protocol Number
       RFC 791: Internet Protocol - Protocol";
  }

  identity exact-ipv4-address {
    base ipv4-capability;
    description
      "Identity for exact-match IPv4 address
      condition capability";
    reference
      "RFC 791: Internet Protocol - Address";
  }
  identity range-ipv4-address {
    base ipv4-capability;
    description
      "Identity for range-match IPv4 address condition
       capability";
    reference
      "RFC 791: Internet Protocol - Address";
  }

  identity ipv4-ip-opts {
    base ipv4-capability;
    description
      "Identity for IPv4 option condition capability";
    reference
      "RFC 791: Internet Protocol - Options";
  }

  identity ipv4-geo-ip {
    base ipv4-capability;
    description
      "Identity for geography condition capability";
    reference
      "draft-ietf-i2nsf-capability-05: Information Model
       of NSFs Capabilities - Geo-IP";
  }

  identity ipv6-capability {
    base condition;
    description
      "Identity for IPv6 condition capabilities";
    reference
      "RFC 8200: Internet Protocol, Version 6 (IPv6)
      Specification";
  }

  identity ipv6-traffic-class {
    base ipv6-capability;
    description
      "Identity for IPv6 traffic class
      condition capability";
    reference
      "RFC 8200: Internet Protocol, Version 6 (IPv6)
      Specification - Traffic Class";
  }

  identity exact-ipv6-flow-label {
    base ipv6-capability;
    description
      "Identity for exact-match IPv6 flow label
      condition capability";
    reference
      "RFC 8200: Internet Protocol, Version 6 (IPv6)
      Specification - Flow Label";
  }

  identity range-ipv6-flow-label {
    base ipv6-capability;
    description
      "Identity for range-match IPv6 flow label
      condition capability";
    reference
      "RFC 8200: Internet Protocol, Version 6 (IPv6)
      Specification - Flow Label";
  }

  identity exact-ipv6-payload-length {
    base ipv6-capability;
    description
      "Identity for exact-match IPv6 payload length
      condition capability";
    reference
      "RFC 8200: Internet Protocol, Version 6 (IPv6)
      Specification - Payload Length";
  }

  identity range-ipv6-payload-length {
    base ipv6-capability;
    description
      "Identity for range-match IPv6 payload length
      condition capability";
    reference
      "RFC 8200: Internet Protocol, Version 6 (IPv6)
      Specification - Payload Length";
  }

  identity ipv6-next-header {
    base ipv6-capability;
    description
      "Identity for IPv6 next header condition capability";
    reference
      "RFC 8200: Internet Protocol, Version 6 (IPv6)
      Specification - Next Header";
  }

  identity exact-ipv6-hop-limit {
    base ipv6-capability;
    description
      "Identity for exact-match IPv6 hop limit condition
      capability";
    reference
      "RFC 8200: Internet Protocol, Version 6 (IPv6)
      Specification - Hop Limit";
  }

  identity range-ipv6-hop-limit {
    base ipv6-capability;
    description
      "Identity for range-match IPv6 hop limit condition
      capability";
    reference
      "RFC 8200: Internet Protocol, Version 6 (IPv6)
      Specification - Hop Limit";
  }

  identity exact-ipv6-address {
    base ipv6-capability;
    description
      "Identity for exact-match IPv6 address condition
       capability";
    reference
      "RFC 8200: Internet Protocol, Version 6 (IPv6)
      Specification - Address";
  }

  identity range-ipv6-address {
    base ipv6-capability;
    description
      "Identity for range-match IPv6 address condition
      capability";
    reference
      "RFC 8200: Internet Protocol, Version 6 (IPv6)
      Specification - Address";
  }

  identity tcp-capability {
    base condition;
    description
      "Identity for TCP condition capabilities";
    reference
      "RFC 793: Transmission Control Protocol";
  }

  identity exact-tcp-port-num {
    base tcp-capability;
    description
      "Identity for exact-match TCP port number condition
       capability";
    reference
      "RFC 793: Transmission Control Protocol - Port Number";
  }

  identity range-tcp-port-num {
    base tcp-capability;
    description
      "Identity for range-match TCP port number condition
       capability";
    reference
      "RFC 793: Transmission Control Protocol - Port Number";
  }

  identity exact-tcp-seq-num {
    base tcp-capability;
    description
      "Identity for exact-match TCP sequence number condition
      capability";
    reference
      "RFC 793: Transmission Control Protocol - Sequence Number";
  }

  identity range-tcp-seq-num {
    base tcp-capability;
    description
      "Identity for range-match TCP sequence number condition
       capability";
    reference
      "RFC 793: Transmission Control Protocol - Sequence Number";
  }

  identity exact-tcp-ack-num {
    base tcp-capability;
    description
      "Identity for exact-match TCP acknowledgement number condition
       capability";
    reference
      "RFC 793: Transmission Control Protocol - Acknowledgement Number";
  }

  identity range-tcp-ack-num {
    base tcp-capability;
    description
      "Identity for range-match TCP acknowledgement number condition
       capability";
    reference
      "RFC 793: Transmission Control Protocol - Acknowledgement Number";
  }

  identity exact-tcp-window-size {
    base tcp-capability;
    description
      "Identity for exact-match TCP window size condition capability";
    reference
      "RFC 793: Transmission Control Protocol - Window Size";
  }

  identity range-tcp-window-size {
    base tcp-capability;
    description
      "Identity for range-match TCP window size condition capability";
    reference
      "RFC 793: Transmission Control Protocol - Window Size";
  }

  identity tcp-flags {
    base tcp-capability;
    description
      "Identity for TCP flags condition capability";
    reference
      "RFC 793: Transmission Control Protocol - Flags";
  }

  identity udp-capability {
    base condition;
    description
      "Identity for UDP condition capabilities";
    reference
      "RFC 768: User Datagram Protocol";
  }

  identity exact-udp-port-num {
    base udp-capability;
    description
      "Identity for exact-match UDP port number condition capability";
    reference
      "RFC 768: User Datagram Protocol - Port Number";
  }

  identity range-udp-port-num {
    base udp-capability;
    description
      "Identity for range-match UDP port number condition capability";
    reference
      "RFC 768: User Datagram Protocol - Port Number";
  }

  identity exact-udp-total-length {
    base udp-capability;
    description
      "Identity for exact-match UDP total-length condition capability";
    reference
      "RFC 768: User Datagram Protocol - Total Length";
  }

  identity range-udp-total-length {
    base udp-capability;
    description
      "Identity for range-match UDP total-length condition capability";
    reference
      "RFC 768: User Datagram Protocol - Total Length";
  }

  identity icmp-capability {
    base condition;
    description
      "Identity for ICMP condition capabilities";
    reference
      "RFC 792: Internet Control Message Protocol";
  }

  identity icmp-type {
    base icmp-capability;
    description
      "Identity for ICMP type condition capability";
    reference
      "RFC 792: Internet Control Message Protocol";
  }

  identity icmpv6-capability {
    base condition;
    description
      "Identity for ICMPv6 condition capabilities";
    reference
      "RFC 4443: Internet Control Message Protocol (ICMPv6)
       for the Internet Protocol Version 6 (IPv6) Specification
       - ICMPv6";
  }

  identity icmpv6-type {
    base icmpv6-capability;
    description
      "Identity for ICMPv6 type condition capability";
    reference
      "RFC 4443: Internet Control Message Protocol (ICMPv6)
       for the Internet Protocol Version 6 (IPv6) Specification
       - ICMPv6";
  }

  identity url-capability {
    base condition;
    description
      "Identity for URL condition capabilities";
  }

  identity pre-defined {
    base url-capability;
    description
      "Identity for URL pre-defined condition capabilities";
  }

  identity user-defined {
    base url-capability;
    description
      "Identity for URL user-defined condition capabilities";
  }

  identity log-action-capability {
    description
      "Identity for log-action capabilities";
  }

  identity rule-log {
    base log-action-capability;
    description
      "Identity for rule log log-action capability";
  }

  identity session-log {
    base log-action-capability;
    description
      "Identity for session log log-action capability";
  }

  identity ingress-action-capability {
    description
      "Identity for ingress-action capabilities";
    reference
      "RFC 8329: Framework for Interface to Network Security
       Functions - Ingress action";
  }

  identity egress-action-capability {
    description
      "Base identity for egress-action capabilities";
    reference
      "RFC 8329: Framework for Interface to Network Security
       Functions - Egress action";
  }

  identity default-action-capability {
    description
      "Identity for default-action capabilities";
    reference
      "draft-ietf-i2nsf-capability-05: Information Model of
       NSFs Capabilities - Default action";
  }

  identity pass {
    base ingress-action-capability;
    base egress-action-capability;
    base default-action-capability;
    description
      "Identity for pass action capability";
    reference
      "RFC 8329: Framework for Interface to Network Security
       Functions - Ingress, egress, and pass actions
           draft-ietf-i2nsf-capability-05: Information Model of
       NSFs Capabilities - Actions and default action";
  }

  identity drop {
    base ingress-action-capability;
    base egress-action-capability;
    base default-action-capability;
    description
      "Identity for drop action capability";
    reference
      "RFC 8329: Framework for Interface to Network Security
       Functions - Ingress, egress, and drop actions
       draft-ietf-i2nsf-capability-05: Information Model of
       NSFs Capabilities - Actions and default action";
  }

  identity alert {
    base ingress-action-capability;
    base egress-action-capability;
    base default-action-capability;
    description
      "Identity for alert action capability";
    reference
      "RFC 8329: Framework for Interface to Network Security
       Functions - Ingress, egress, and alert actions
       draft-ietf-i2nsf-nsf-monitoring-data-model-03: I2NSF
       NSF Monitoring YANG Data Model - Alarm (i.e., alert)
       draft-ietf-i2nsf-capability-05: Information Model of
       NSFs Capabilities - Actions and default action";
  }

  identity mirror {
    base ingress-action-capability;
    base egress-action-capability;
    base default-action-capability;
    description
      "Identity for mirror action capability";
    reference
      "RFC 8329: Framework for Interface to Network Security
       Functions - Ingress, egress, and mirror actions
       draft-ietf-i2nsf-capability-05: Information Model of
       NSFs Capabilities - Actions and default action";
  }

  identity invoke-signaling {
    base egress-action-capability;
    description
      "Identity for invoke signaling action capability";
    reference
      "RFC 8329: Framework for Interface to Network Security
       Functions - Invoke-signaling action";
  }

  identity tunnel-encapsulation {
    base egress-action-capability;
    description
      "Identity for tunnel encapsulation action capability";
    reference
      "RFC 8329: Framework for Interface to Network Security
       Functions - Tunnel-encapsulation action";
  }

  identity forwarding {
    base egress-action-capability;
    description
      "Identity for forwarding action capability";
    reference
      "RFC 8329: Framework for Interface to Network Security
       Functions - Forwarding action";
  }

  identity redirection {
    base egress-action-capability;
    description
      "Identity for redirection action capability";
    reference
      "RFC 8329: Framework for Interface to Network Security
       Functions - Redirection action";
  }

  identity resolution-strategy-capability {
    description
      "Base identity for resolution strategy capability";
    reference
      "draft-ietf-i2nsf-capability-05: Information Model of
       NSFs Capabilities - Resolution Strategy";
  }

  identity fmr {
    base resolution-strategy-capability;
    description
      "Identity for First Matching Rule (FMR) resolution
       strategy capability";
    reference
      "draft-ietf-i2nsf-capability-05: Information Model of
       NSFs Capabilities - Resolution Strategy";
  }

  identity lmr {
    base resolution-strategy-capability;
    description
      "Identity for Last Matching Rule (LMR) resolution
       strategy capability";
    reference
      "draft-ietf-i2nsf-capability-05: Information Model of
       NSFs Capabilities - Resolution Strategy";
  }

  identity pmr {
    base resolution-strategy-capability;
    description
      "Identity for Prioritized Matching Rule (PMR) resolution
       strategy capability";
    reference
      "draft-ietf-i2nsf-capability-05: Information Model of
       NSFs Capabilities - Resolution Strategy";
  }

  identity pmre {
    base resolution-strategy-capability;
    description
      "Identity for Prioritized Matching Rule with Errors (PMRE)
       resolution strategy capability";
    reference
      "draft-ietf-i2nsf-capability-05: Information Model of NSFs
      Capabilities - Resolution Strategy";
  }

  identity pmrn {
    base resolution-strategy-capability;
    description
      "Identity for Prioritized Matching Rule with No Errors (PMRN)
       resolution strategy capability";
    reference
      "draft-ietf-i2nsf-capability-05: Information Model of NSFs
       Capabilities - Resolution Strategy";
  }

  identity advanced-nsf-capability {
    description
      "Base identity for advanced network security function (NSF)
       capabilities";
    reference
      "RFC 8329: Framework for Interface to Network Security
       Functions - Differences from ACL Data Models
       draft-dong-i2nsf-asf-config-01: Configuration of Advanced
       Security Functions with I2NSF Security Controller -
       Advanced NSF Capability";
  }

  identity anti-virus-capability {
    base advanced-nsf-capability;
    description
      "Identity for advanced NSF anti-virus capabilities";
       reference
      "RFC 8329: Framework for Interface to Network Security
       Functions - Differences from ACL Data Models
       draft-dong-i2nsf-asf-config-01: Configuration of Advanced
       Security Functions with I2NSF Security Controller -
       Anti-Virus";
  }

  identity anti-ddos-capability {
    base advanced-nsf-capability;
    description
      "Identity for advanced NSF anti-ddos capabilities";
    reference
      "RFC 8329: Framework for Interface to Network Security
       Functions - Differences from ACL Data Models
       draft-dong-i2nsf-asf-config-01: Configuration of Advanced
       Security Functions with I2NSF Security Controller -
       Anti-DDoS";
  }

  identity ips-capability {
    base advanced-nsf-capability;
    description
      "Identity for advanced NSF Intrusion Prevention System
      (IPS) capabilities";
    reference
      "RFC 8329: Framework for Interface to Network Security
       Functions - Differences from ACL Data Models
       draft-dong-i2nsf-asf-config-01: Configuration of Advanced
       Security Functions with I2NSF Security Controller -
       Intrusion Prevention System";
  }

  identity voip-volte-capability {
    base advanced-nsf-capability;
    description
      "Identity for advanced NSF VoIP/VoLTE capabilities";
    reference
      "RFC 3261: SIP: Session Initiation Protocol
       RFC 8329: Framework for Interface to Network Security
       Functions - Differences from ACL Data Models
       draft-dong-i2nsf-asf-config-01: Configuration of Advanced
       Security Functions with I2NSF Security Controller";
  }

  identity detect {
    base anti-virus-capability;
    description
      "Identity for advanced NSF Anti-Virus detection capability";
    reference
      "draft-dong-i2nsf-asf-config-01: Configuration of Advanced
       Security Functions with I2NSF Security Controller -
       Anti-Virus";
  }

  identity exception-application {
    base anti-virus-capability;
    description
      "Identity for advanced NSF Anti-Virus exception application
       capability";
    reference
      "draft-dong-i2nsf-asf-config-01: Configuration of Advanced
       Security Functions with I2NSF Security Controller -
       Anti-Virus";
  }

  identity exception-signature {
    base anti-virus-capability;
    description
      "Identity for advanced NSF Anti-Virus exception signature
       capability";
    reference
      "draft-dong-i2nsf-asf-config-01: Configuration of Advanced
       Security Functions with I2NSF Security Controller -
       Anti-Virus";
  }

  identity whitelists {
    base anti-virus-capability;
    description
      "Identity for advanced NSF Anti-Virus whitelists capability";
    reference
      "draft-dong-i2nsf-asf-config-01: Configuration of Advanced
       Security Functions with I2NSF Security Controller -
       Anti-virus";
  }

  identity syn-flood-action {
    base anti-ddos-capability;
    description
      "Identity for advanced NSF Anti-DDoS syn flood action
       capability";
    reference
      "draft-dong-i2nsf-asf-config-01: Configuration of Advanced
       Security Functions with I2NSF Security Controller -
       Anti-DDoS";
  }

  identity udp-flood-action {
    base anti-ddos-capability;
    description
      "Identity for advanced NSF anti-DDoS UDP flood action
       capability";
    reference
      "draft-dong-i2nsf-asf-config-01: Configuration of Advanced
       Security Functions with I2NSF Security Controller -
       Anti-DDoS";
  }

  identity http-flood-action {
    base anti-ddos-capability;
    description
      "Identity for advanced NSF anti-DDoS http flood action
       capability";
    reference
      "draft-dong-i2nsf-asf-config-01: Configuration of Advanced
       Security Functions with I2NSF Security Controller -
       Anti-DDoS";
  }

  identity https-flood-action {
    base anti-ddos-capability;
    description
      "Identity for advanced NSF Anti-DDoS https flood action
       capability";
    reference
      "draft-dong-i2nsf-asf-config-01: Configuration of Advanced
       Security Functions with I2NSF Security Controller -
       Anti-DDoS";
  }

  identity dns-request-flood-action {
    base anti-ddos-capability;
    description
      "Identity for advanced NSF anti-DDoS dns request
      flood action capability";
    reference
      "draft-dong-i2nsf-asf-config-01: Configuration of Advanced
       Security Functions with I2NSF Security Controller -
       Anti-DDoS";
  }

  identity dns-reply-flood-action {
    base anti-ddos-capability;
    description
      "Identity for advanced NSF Anti-DDoS DNS reply flood action
       capability";
    reference
      "draft-dong-i2nsf-asf-config-01: Configuration of Advanced
       Security Functions with I2NSF Security Controller -
       Anti-DDoS";
  }

  identity icmp-flood-action {
    base anti-ddos-capability;
    description
      "Identity for advanced NSF Anti-DDoS ICMP flood action
       capability";
    reference
      "draft-dong-i2nsf-asf-config-01: Configuration of Advanced
       Security Functions with I2NSF Security Controller -
       Anti-DDoS";
  }

  identity icmpv6-flood-action {
    base anti-ddos-capability;
    description
      "Identity for advanced NSF Anti-DDoS ICMPv6 flood action
       capability";
    reference
      "draft-dong-i2nsf-asf-config-01: Configuration of Advanced
       Security Functions with I2NSF Security Controller -
       Anti-DDoS";
  }

  identity sip-flood-action {
    base anti-ddos-capability;
    description
      "Identity for advanced NSF Anti-DDoS SIP flood action
       capability";
    reference
      "draft-dong-i2nsf-asf-config-01: Configuration of Advanced
       Security Functions with I2NSF Security Controller -
       Anti-DDoS";
  }

  identity detect-mode {
    base anti-ddos-capability;
    description
      "Identity for advanced NSF Anti-DDoS detection mode
       capability";
    reference
      "draft-dong-i2nsf-asf-config-01: Configuration of Advanced
       Security Functions with I2NSF Security Controller -
       Anti-DDoS";
  }

  identity baseline-learning {
    base anti-ddos-capability;
    description
      "Identity for advanced NSF Anti-DDoS baseline learning
       capability";
    reference
      "draft-dong-i2nsf-asf-config-01: Configuration of Advanced
       Security Functions with I2NSF Security Controller -
       Anti-DDoS";
  }

  identity signature-set {
    base ips-capability;
    description
      "Identity for advanced NSF IPS signature set capability";
    reference
      "draft-dong-i2nsf-asf-config-01: Configuration of Advanced
       Security Functions with I2NSF Security Controller -
       Intrusion Prevention System";
  }

  identity ips-exception-signature {
    base ips-capability;
    description
      "Identity for advanced NSF IPS exception signature
       capability";
    reference
      "draft-dong-i2nsf-asf-config-01: Configuration of Advanced
       Security Functions with I2NSF Security Controller -
       Intrusion Prevention System";
  }

  identity voice-id {
    base voip-volte-capability;
    description
      "Identity for advanced NSF VoIP/VoLTE voice-id capability";
    reference
      "RFC 3261: SIP: Session Initiation Protocol";
  }

  identity user-agent {
    base voip-volte-capability;
    description
      "Identity for advanced NSF VoIP/VoLTE user agent capability";
    reference
      "RFC 3261: SIP: Session Initiation Protocol";
  }

  identity ipsec-capability {
    description
      "Base identity for an IPsec capabilities";
  }
  identity ike {
    base ipsec-capability;
    description
      "Identity for an IPSec Internet Key Exchange (IKE)
      capability";
  }

  identity ikeless {
    base ipsec-capability;
    description
      "Identity for an IPSec without Internet Key Exchange (IKE)
      capability";
  }

  /*
   *  Grouping
   */

  grouping nsf-capabilities {
    description
      "Network Security Function (NSF) Capabilities";
    reference
      "RFC 8329: Framework for Interface to Network Security
       Functions - I2NSF Flow Security Policy Structure
       draft-ietf-i2nsf-capability-05: Information Model of
       NSFs Capabilities - Capability Information Model Design";

    leaf-list time-capabilities {
      type enumeration {
        enum absolute-time {
          description
            "absolute time capabilities.
             If a network security function has the absolute time
             capability, the network security function supports
             rule execution according to absolute time.";
        }
        enum periodic-time {
          description
            "periodic time capabilities.
             If a network security function has the periodic time
             capability, the network security function supports
             rule execution according to periodic time.";
        }
      }
      description
        "Time capabilities";
    }

    container event-capabilities {
      description
        "Capabilities of events.
         If a network security function has the event capabilities,
         the network security function supports rule execution
         according to system event and system alarm.";

      reference
        "RFC 8329: Framework for Interface to Network Security
         Functions - I2NSF Flow Security Policy Structure
         draft-ietf-i2nsf-capability-05: Information Model of
         NSFs Capabilities - Design Principles and ECA Policy
         Model Overview
         draft-ietf-i2nsf-nsf-monitoring-data-model-03: I2NSF
         NSF Monitoring YANG Data Model - System Alarm and
         System Events";

      leaf-list system-event-capability {
        type identityref {
          base system-event-capability;
        }
        description
          "System event capabilities";
      }

      leaf-list system-alarm-capability {
        type identityref {
          base system-alarm-capability;
        }
        description
          "System alarm Capabilities";
      }
    }

    container condition-capabilities {
      description
        "Conditions capabilities.";

      container generic-nsf-capabilities {
        description
          "Conditions capabilities.
           If a network security function has the condition
           capabilities, the network security function
           supports rule execution according to conditions of
           IPv4, IPv6, TCP, UDP, ICMP, ICMPv6, and payload.";
        reference
          "RFC 791: Internet Protocol - IPv4
           RFC 792: Internet Control Message Protocol - ICMP
           RFC 793: Transmission Control Protocol - TCP
           RFC 768: User Datagram Protocol - UDP
           RFC 8200: Internet Protocol, Version 6 (IPv6)
           Specification - IPv6
           RFC 4443: Internet Control Message Protocol (ICMPv6)
           for the Internet Protocol Version 6 (IPv6) Specification
           - ICMPv6
           RFC 8329: Framework for Interface to Network Security
           Functions - I2NSF Flow Security Policy Structure
           draft-ietf-i2nsf-capability-05: Information Model of
           NSFs Capabilities - Design Principles and ECA Policy
           Model Overview";

        leaf-list ipv4-capability {
          type identityref {
            base ipv4-capability;
          }
          description
            "IPv4 packet capabilities";
          reference
            "RFC 791: Internet Protocol";
        }

        leaf-list icmp-capability {
          type identityref {
            base icmp-capability;
          }
          description
            "ICMP packet capabilities";
          reference
            "RFC 792: Internet Control Message Protocol - ICMP";
        }

        leaf-list ipv6-capability {
          type identityref {
            base ipv6-capability;
          }
          description
            "IPv6 packet capabilities";
          reference
            "RFC 8200: Internet Protocol, Version 6 (IPv6)
             Specification - IPv6";
        }

        leaf-list icmpv6-capability {
          type identityref {
            base icmpv6-capability;
          }
          description
            "ICMPv6 packet capabilities";
          reference
            "RFC 4443: Internet Control Message Protocol (ICMPv6)
             for the Internet Protocol Version 6 (IPv6) Specification
             - ICMPv6";
        }

        leaf-list tcp-capability {
          type identityref {
            base tcp-capability;
          }
          description
            "TCP packet capabilities";
          reference
            "RFC 793: Transmission Control Protocol - TCP";
        }

        leaf-list udp-capability {
          type identityref {
            base udp-capability;
          }
          description
            "UDP packet capabilities";
          reference
            "RFC 768: User Datagram Protocol - UDP";
        }
      }

      container advanced-nsf-capabilities {
        description
          "Advanced Network Security Function (NSF) capabilities,
           such as Anti-Virus, Anti-DDoS, IPS, and VoIP/VoLTE.";
        reference
          "RFC 8329: Framework for Interface to Network Security
           Functions - Differences from ACL Data Models
           draft-dong-i2nsf-asf-config-01: Configuration of
           Advanced Security Functions with I2NSF Security
           Controller";

        leaf-list anti-virus-capability {
          type identityref {
            base anti-virus-capability;
          }
          description
            "Anti-virus capabilities";
          reference
            "draft-dong-i2nsf-asf-config-01: Configuration of
             Advanced Security Functions with I2NSF Security
             Controller";
        }

        leaf-list anti-ddos-capability {
          type identityref {
            base anti-ddos-capability;
          }
          description
            "Anti-ddos capabilities";
          reference
            "draft-dong-i2nsf-asf-config-01: Configuration of
             Advanced Security Functions with I2NSF Security
             Controller";
        }

        leaf-list ips-capability {
          type identityref {
            base ips-capability;
          }
          description
            "Intrusion Prevention System (IPS) capabilities";
          reference
            "draft-dong-i2nsf-asf-config-01: Configuration of
             Advanced Security Functions with I2NSF Security
             Controller";
        }

        leaf-list url-capability {
          type identityref {
            base url-capability;
          }
          description
            "URL capabilities";
          reference
            "draft-dong-i2nsf-asf-config-01: Configuration of
             Advanced Security Functions with I2NSF Security
             Controller";
        }

        leaf-list voip-volte-capability {
          type identityref {
            base voip-volte-capability;
         }
          description
            "VoIP and VoLTE capabilities";
          reference
            "draft-dong-i2nsf-asf-config-01: Configuration of
             Advanced Security Functions with I2NSF Security
             Controller";
        }
      }

      leaf-list context-capabilities {
        type identityref {
          base context-capability;
        }
        description
          "Security context capabilities";
      }
    }

    container action-capabilities {
      description
        "Action capabilities.
         If a network security function has the action
         capabilities, the network security function supports
         the attendant actions for policy rules.";

      leaf-list ingress-action-capability {
        type identityref {
          base ingress-action-capability;
        }
        description
          "Ingress-action capabilities";
      }

      leaf-list egress-action-capability {
        type identityref {
          base egress-action-capability;
        }
        description
          "Egress-action capabilities";
      }

      leaf-list log-action-capability {
        type identityref {
          base log-action-capability;
        }
        description
          "Log-action capabilities";
      }
    }

    leaf-list resolution-strategy-capabilities {
      type identityref {
        base resolution-strategy-capability;
      }
      description
        "Resolution strategy capabilities.
         The resolution strategies can be used to specify how
         to resolve conflicts that occur between the actions
         of the same or different policy rules that are matched
         for the same packet and by particular NSF";
      reference
        "draft-ietf-i2nsf-capability-05: Information Model of
         NSFs Capabilities - Resolution strategy";
    }

    leaf-list default-action-capabilities {
      type identityref {
        base default-action-capability;
      }
      description
        "Default action capabilities.
         A default action is used to execute I2NSF policy rules
         when no rule matches a packet. The default action is
         defined as pass, drop, alert, or mirror.";
      reference
        "RFC 8329: Framework for Interface to Network Security
         Functions - Ingress and egress actions
         draft-ietf-i2nsf-capability-05: Information Model of
         NSFs Capabilities - Default action";
    }

    leaf-list ipsec-method {
      type identityref {
        base ipsec-capability;
      }
      description
        "IPsec method capabilities";
      reference
        "draft-ietf-i2nsf-sdn-ipsec-flow-protection-08:
         Software-Defined Networking (SDN)-based IPsec Flow
         Protection - IPsec methods such as IKE and IKE-less";
    }
  }

  /*
   * Data nodes
   */

  list nsf {
    key "nsf-name";
    description
      "The list of Network Security Function (NSF) capabilities";
    leaf nsf-name {
      type string;
      mandatory true;
      description
        "The name of network security function";
    }
  }
}
