module ietf-transport-network-slice {
  yang-version 1.1;
  namespace
    "urn:ietf:params:xml:ns:yang:ietf-transport-network-slice";
  prefix "tns";

  import ietf-inet-types {
    prefix inet;
    reference
      "RFC 6991: Common YANG Data Types";
  }

  import ietf-te-types {
    prefix "te-types";
    reference
      "RFC 8776: Traffic Engineering Common YANG Types";
  }

  organization
    "IETF CCAMP Working Group";
  contact
    "WG Web: <http://tools.ietf.org/wg/ccamp/>
     WG List: <mailto:ccamp@ietf.org>

     Editor: Haomian Zheng
             <mailto:zhenghaomian@huawei.com>

     Editor: Italo Busi
             <mailto:italo.busi@huawei.com>

     Editor: Aihua Guo
             <mailto:aihuaguo.ietf@gmail.com>

     Editor: Victor Lopez
             <mailto:victor.lopez@nokia.com>";

  description
    "This module defines a base YANG data model for configuring
     generic network slices in optical transport networks, e.g.,
     Optical Transport Network (OTN).

     The model fully conforms to the Network Management Datastore
     Architecture (NMDA).

     Copyright (c) 2022 IETF Trust and the persons
     identified as authors of the code.  All rights reserved.

     Redistribution and use in source and binary forms, with or
     without modification, is permitted pursuant to, and subject
     to the license terms contained in, the Simplified BSD
     License set forth in Section 4.c of the IETF Trust's Legal
     Provisions Relating to IETF Documents
     (https://trustee.ietf.org/license-info).
     This version of this YANG module is part of RFC XXXX; see
     the RFC itself for full legal notices.";

  revision "2022-03-04" {
    description
      "Latest revision of NBI YANG model for OTN slicing.";
    reference
      "draft-ietf-ccamp-yang-otn-slicing-01: Framework and Data
       Model for OTN Network Slicing";
  }

  /*
   * Identities
   */
  identity isolation-level {
    description
      "Base identity for the isolation-level.";
    reference
      "GSMA-NS-Template: Generic Network Slice Template,
       Version 3.0.";
  }
  identity no-isolation {
    base isolation-level;
    description
      "Network slices are not separated.";
  }
  identity physical-isolation {
    base isolation-level;
    description
      "Network slices are physically separated (e.g. different
       rack, different hardware, different location, etc.).";
  }
  identity logical-isolation {
    base isolation-level;
    description
      "Network slices are logically separated.";
  }
  identity process-isolation {
    base physical-isolation;
    description
      "Process and threads isolation.";
  }
  identity physical-memory-isolation {
    base physical-isolation;
    description
      "Process and threads isolation.";
  }
  identity physical-network-isolation {
    base physical-isolation;
    description
      "Process and threads isolation.";
  }
  identity virtual-resource-isolation {
    base logical-isolation;
    description
      "A network slice has access to specific range of resources
       that do not overlap with other network slices
       (e.g. VM isolation).";
  }
  identity network-functions-isolation {
    base logical-isolation;
    description
      "NF (Network Function) is dedicated to the network slice,
       but virtual resources are shared.";
  }
  identity service-isolation {
    base logical-isolation;
    description
      "NSC data are isolated from other NSCs, but virtual
       resources and NFs are shared.";
  }

  /*
   * Groupings
   */

  grouping ns-generic-info {
    description
      "Generic configuration of a network slice";
      leaf ns-name {
        type string;
        description
          "Name of the specific network slice";
      }
      leaf ns-description {
        type string;
        description
          "Description regarding the specific network slice";
      }
      leaf-list customer-name {
        type string;
        description
          "List of customers using the slice";
      }
  }

  grouping ns-slo {
    description
      "SLO configuration of a network slice";

    container slo {
      description
        "SLO configuration of a network slice";

    leaf optimization-criterion {
        type identityref {
          base te-types:objective-function-type;
        }
        description
          "Optimization criterion applied to this topology.";
      }
      leaf delay-tolerance {
        type boolean;
        description
          "'true' if is not too critical how long it takes to
           deliver the amount of data.";
        reference
          "GSMA-NS-Template: Generic Network Slice Template,
           Version 3.0.";
      }
      leaf-list periodicity {
        type uint64;
        units seconds;
        description
          "A list of periodicities supported by the network
           slice.";
        reference
          "GSMA-NS-Template: Generic Network Slice Template,
           Version 3.0.";
      }
      leaf isolation-level {
        type identityref {
          base isolation-level;
        }
        description
          "A network slice instance may be fully or partly,
           logically and/or physically, isolated from another
           network slice instance. This attribute describes
           different types of isolation:";
      }
    }
  }

  grouping node-slo {
    description
      "Node SLO";
    container slo {
      description
        "SLO configuration of a node";
      leaf isolation-level {
        type identityref {
          base isolation-level;
        }
        description
          "A network slice instance may be fully or partly,
           logically and/or physically, isolated from another
           network slice instance. This attribute describes
           different types of isolation:";
      }
    }
  }

  grouping link-slo {
    description
      "Link SLO";
    container slo {
      description
        "SLO configuration of a link";
      leaf delay-tolerance {
        type boolean;
        description
          "'true' if is not too critical how long it takes to
           deliver the amount of data.";
        reference
          "GSMA-NS-Template: Generic Network Slice Template,
           Version 3.0.";
      }
      leaf-list periodicity {
        type uint64;
        units seconds;
        description
          "A list of periodicities supported by the network
           slice.";
        reference
          "GSMA-NS-Template: Generic Network Slice Template,
           Version 3.0.";
      }
      leaf isolation-level {
        type identityref {
          base isolation-level;
        }
        description
          "A network slice instance may be fully or partly,
           logically and/or physically, isolated from another
           network slice instance. This attribute describes
           different types of isolation:";
      }
    }
  }

  grouping connectivity-matrix-slo {
    description
      "SLO configuration of a path within a network slice";

    container slo {
      description
        "Path SLO configuration";
    }
    leaf delay-tolerance {
      type boolean;
      description
        "'true' if is not too critical how long it takes to
         deliver the amount of data.";
      reference
        "GSMA-NS-Template: Generic Network Slice Template,
         Version 3.0.";
    }
    leaf-list periodicity {
      type uint64;
      units seconds;
      description
        "A list of periodicities supported by the network
         slice.";
      reference
        "GSMA-NS-Template: Generic Network Slice Template,
         Version 3.0.";
    }
    leaf isolation-level {
      type identityref {
        base isolation-level;
      }
      description
        "A network slice instance may be fully or partly,
         logically and/or physically, isolated from another
         network slice instance. This attribute describes
         different types of isolation:";
    }
  }

  grouping connectivity-matrix-entry-slo {
    description
      "SLO configuration of a connectivity matrix entry within a
       network slice";

    container slo {
      description
        "SLO configuration of a connectivity matrix entry";
    }
  }

  grouping explicit-path {
    description
      "Explicit path for a connectivity matrix entry";
    list explicit-path {
      key "tp-id";
      description
        "List of TPs within a network topology that form a
         path.";
      leaf tp-id {
        type leafref {
          path "/network-slices/network-slice[ns-id=current()"+
               "/../../../../ns-id]/network-topologies"+
               "/network-topology[topology-id=current()"+
               "/../../topology-id]/node/termination-point"+
               "/tp-id";
        }
        description
          "Relative reference to TP id.";
      }
    }
  }

  grouping network-topology-def {
    description
      "Network topology definition";
    list node {
      key "node-id";
      description
      "The inventory of nodes of this topology.";
      leaf node-id {
        type inet:uri;
        description
          "Node identifier.";
      }
      uses node-slo;
      list termination-point {
        key "tp-id";
        description
          "TP identifier";
        leaf tp-id {
          type inet:uri;
          description
            "Termination point identifier.";
        }
        leaf endpoint-id {
          type leafref {
            path "/network-slices/network-slice[ns-id=current()"+
                 "/../../../../../ns-id]/endpoints/endpoint/"+
                 "endpoint-id";
          }
          description
            "Relative reference to TP id.";
        }
      }
    }
    list link {
      key "link-id";
      description
        "Link identifier.";
      leaf link-id {
        type inet:uri;
        description
          "Link identifier.";
      }
      uses link-slo;
      container source {
        description
          "Link source node";
        leaf source-node {
          type leafref {
            path "../../../node/node-id";
          }
          description
            "Source node identifier, must be in same topology.";
        }
        leaf source-tp {
          type leafref {
            path "../../../node[node-id=current()/../"+
                 "source-node]/termination-point/tp-id";
          }
          description
            "Termination point within source node that terminates
             the link.";
        }
      }
      container destination {
        description
          "Link destination node";
        leaf dest-node {
          type leafref {
            path "../../../node/node-id";
          }
          description
            "Destination node identifier, must be in same
             topology.";
        }
        leaf dest-tp {
          type leafref {
            path "../../../node[node-id=current()/../"+
                 "dest-node]/termination-point/tp-id";
          }
          description
            "Termination point within destination node that
             terminates the link.";
        }
      }
    }
  }

  /*
   * Configuration data nodes
   */
  container network-slices {
    description
      "Generic network slice configurations";
    list network-slice {
      key "ns-id";
      description
        "Network slice identifier";
      leaf ns-id {
        type string;
        description
          "A unique network slice identifier across a slice
           controller";
      }
      uses ns-generic-info;
      uses ns-slo;

      container endpoints {
        description
          "Endpoints of a network slice";

        list endpoint {
          key "endpoint-id";
          description
            "List of endpoints";
          leaf endpoint-id {
            type string;
            description
              "Endpoint identifier";
          }
        }
      }
      container network-topologies {
        description
          "A network slice is described as a network topology";

        list network-topology {
          key "topology-id";
          description
            "List of network topologies";
          leaf topology-id {
            type string;
            description
              "Topology identifier";
          }
          uses network-topology-def;
        }
      }
      container connectivity-matrices {
        description
          "Connectivity matrices";

        list connectivity-matrix {
          key "connectivity-matrix-id";
          description
            "List of connectivity matrix entities";
          leaf connectivity-matrix-id {
            type uint32;
            description
              "Connectivity matrix identifier";
          }
          leaf topology-id {
            type leafref {
              path "../../../network-topologies/network-topology"+
                   "/topology-id";
            }
            description
              "Relative reference to network topology id.";
          }
          leaf src-endpoint {
            type leafref {
              path "../../../endpoints/endpoint/endpoint-id";
            }
            description
              "Relative reference to endpoint id.";
          }
          leaf dst-endpoint {
            type leafref {
              path "../../../endpoints/endpoint/endpoint-id";
            }
            description
              "Relative reference to endpoint id.";
          }
          uses connectivity-matrix-entry-slo;
          uses explicit-path;
        } //connectivity-matrix
      } //connectivity-matrices
    } //network-slice
  } //network slices
}
