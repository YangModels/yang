module ietf-yang-architecture {
  namespace "urn:ietf:params:xml:ns:yang:ietf-yang-architecture";
  prefix arch;

  import ietf-yang-metadata {
    prefix md;
  }

  organization
    "IETF NETMOD (NETCONF Data Modeling Language) Working Group";

  contact
    "WG Web:   <https://datatracker.ietf.org/wg/netmod/>

     WG List:  <mailto:netmod@ietf.org>

     Editor:   Martin Bjorklund
               <mailto:mbj@tail-f.com>";

  description
    "This YANG module defines an 'origin' metadata annotation,
     and a set of identities for the origin value.  The 'origin'
     metadata annotation is used to mark data in the applied
     and operational state datastores with information on where
     the data originated.

     Copyright (c) 2016 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX
     (http://www.rfc-editor.org/info/rfcxxxx); see the RFC itself
     for full legal notices.";

  revision 2016-10-13 {
    description
      "Initial revision.";
    reference
      "RFC XXXX: A Revised Conceptual Model for YANG Datastores";
  }

  /*
   * Identities
   */

  identity origin {
    description
      "Abstract base identitiy for the origin annotation.";
  }

  identity static {
    base origin;
    description
      "Denotes data from static configuration (e.g., <intended>).";
  }

  identity dynamic {
    base origin;
    description
      "Denotes data from dynamic configuration protocols
       or dynamic datastores (e.g., DHCP).";
  }

  identity system {
    base origin;
    description
      "Denotes data created by the system independently of what
       has been configured.";
  }

  identity data-model {
    base origin;
    description
      "Denotes data that does not have an explicitly configured
       value, but has a default value in use.  Covers both simple
       defaults and complex defaults.";
  }

  /*
   * Metadata annotations
   */

  md:annotation origin {
    type identityref {
      base origin;
    }
  }

}
