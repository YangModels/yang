module ietf-ucpe-node-type {
  yang-version 1.1;
  namespace "urn:ietf:params:xml:ns:yang:ietf-ucpe-node-type";
  prefix node-type;
  import ietf-network{
    prefix nw;
    reference
      "RFC 8345: YANG Data Model for Network Topologies";
  }

  organization
    "SFR";
  contact
    "Dmytro Shytyi
     EMail:ietf.dmytro@shytyi.net";
  description
    "This is a YANG data model that extends node-type.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-02-14 {
    description
      "Added node type";
    reference
      "draft-shytyi-opsawg-vysm-08";
  }
  identity node-type {
    description
      "Base identity for node-type.";
  }
  identity ucpe {
    base node-type;
    description
      "Identity for mail application.";
  }
  augment "/nw:networks/nw:network/nw:node" {
  leaf node-type {
    type identityref{
      base node-type;
    }

    description
    "Properties of network instance";
  }
  }
}
