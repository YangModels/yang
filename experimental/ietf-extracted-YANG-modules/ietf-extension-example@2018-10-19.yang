module ietf-extension-example {
  yang-version 1.1;

  namespace "urn:ietf:params:xml:ns:yang:ietf-extension-example";
  prefix example;

  import ietf-inet-types {
    prefix inet;
    reference
      "Section 4 of RFC 6991";
  }

  import ietf-interfaces {
    prefix if;
    reference
      "RFC 8343: A YANG Data Model for Interface Management";
  }

  import iana-tunnel-type  {
    prefix iana-tunnel-type;
    reference
      "RFC XXXX:  A Tunnel Extension to the Interface Management
                  YANG Module";
  }

  import ietf-interface-tunnel  {
    prefix ift;
    reference
      "RFC XXXX:  A Tunnel Extension to the Interface Management
                  YANG Module";
  }
  organization "IETF xxxx Working Group";

  contact

    "WG Web:   <https://datatracker.ietf.org/wg/xxx/>
     WG List:  <mailto:xxx@ietf.org>

     Editor:  Mohamed Boucadair
              <mailto:mohamed.boucadair@orange.com>";

   description
      "This is an exampel YANG module.

      Copyright (c) 2018 IETF Trust and the persons identified as
      authors of the code.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC XXXX; see
      the RFC itself for full legal notices.";

  revision 2018-10-19 {
    description
      "Initial revision.";
    reference
      "RFC XXXX:  A Tunnel Extension to the Interface Management
                  YANG Module";
  }

  augment "/if:interfaces/if:interface" {
    when "derived-from(ift:tunnel-type, 'iana-tunnel-type:gre')";
    description
      "Augments Interface module with specific tunnel parameters.";

    leaf remote-endpoint {
      type inet:ipv6-address;
      description
        "IPv6 address of the local GRE endpoint.";
    }
  }
}
