module ietf-i2nsf-reg-interface{
yang-version 1.1;
namespace
"urn:ietf:params:xml:ns:yang:ietf-i2nsf-reg-interface";
prefix "iiregi";

    import ietf-inet-types{
       prefix inet;
       reference "RFC 6991";
    }
    import ietf-i2nsf-capability{
      prefix capa;
      reference "draft-ietf-i2nsf-capability
              -data-model-04";
     }
    organization
      "IETF I2NSF (Interface to Network Security Functions)
      Working Group";

    contact
   "WG Web: <http://tools.ietf.org/wg/i2nsf>

      WG List: <mailto:i2nsf@ietf.org>

      WG Chair: Linda Dunbar
      <mailto:Linda.duhbar@huawei.com>

      Editor: Sangwon Hyun
      <mailto:swhyun77@skku.edu>
      Editor: Jaehoon Paul Jeong
      <mailto:pauljeong@skku.edu>

      Editor: Taekyun Roh
      <mailto:tkroh0198@skku.edu>

      Editor: Sarang Wi
      <mailto:dnl9795@skku.edu>

      Editor: Jung-Soo Park
      <mailto:pjs@etri.re.kr>";

    description

     "It defines a YANG data model for Registration Interface.
     Copyright (c) 2018 IETF Trust and the persons identified as
     authors of the code. All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

    revision 2019-06-12 {
      description "The third revision";
      reference
        "RFC XXXX: I2NSF Registration Interface YANG Data Model";
    }
    rpc i2nsf-nsf-capability-query {
       description
         "Capability information that the
          Security Controller
          sends to the DMS";
       input{
          container query-i2nsf-capability-info {
            description
            "i2nsf capability information";
            uses "capa:nsf-capabilities";
            reference
              "draft-ietf-i2nsf-capability
                    -data-model-04";
            }
        }
        output{
            container nsf-access-info {
              description
              "nsf access information";
              uses i2nsf-nsf-access-info;

             }
         }
    }
    container i2nsf-nsf-registrations{
    description
     "i2nsf-nsf-registrations";
     list i2nsf-nsf-capability-registration {
       key "nsf-name";
       description
        "Requeired information for registration";
        leaf nsf-name {
          type string;
          mandatory true;
          description
            "nsf-name";
        }
        container nsf-capability-info {
          description
            "nsf-capability-information";
            uses i2nsf-nsf-capability-info;
        }
        container nsf-access-info {
          description
            "nsf-access-info";
            uses i2nsf-nsf-access-info;
        }
      }
    }

    grouping i2nsf-nsf-performance-capability {
       description
        "NSF performance capailities";
       container processing{
         description
          "processing info";
         leaf processing-average{
          type uint16;
          description
           "processing-average";
         }
         leaf processing-peak{
          type uint16;
          description
           "processing peak";
         }
      }
      container bandwidth{
        description
          "bandwidth info";

        container outbound{
          description
             "outbound";
          leaf outbound-average{
              type uint16;
              description
               "outbound-average";
          }
          leaf outbound-peak{
               type uint16;
               description
                "outbound-peak";
           }
       }
       container inbound{
         description
          "inbound";
         leaf inbound-average{
            type uint16;
            description
             "inbound-average";
         }
         leaf inbound-peak{
             type uint16;
             description
              "inbound-peak";
         }
       }
     }
   }
   grouping i2nsf-nsf-capability-info {
     description
      "Detail information of an NSF";
     container i2nsf-capability {
       description
        "ietf i2nsf capability information";
       uses "capa:nsf-capabilities";
       reference "draft-ietf-i2nsf-capability
            -data-model-04";
     }
     container nsf-performance-capability {
        description
         "performance capability";
        uses i2nsf-nsf-performance-capability;
     }
   }

   grouping i2nsf-nsf-access-info {
     description
      "NSF access information";
     leaf nsf-instance-name {
       type string;
       description
         "nsf-instance-name";
     }
     leaf nsf-address {
       type inet:ipv4-address;
       mandatory true;
       description
         "nsf-address";
      }
      leaf nsf-port-address {
       type inet:port-number;
       description
        "nsf-port-address";
      }
   }
}
