submodule ietf-bgp-rib-tables {
  yang-version 1.1;
  belongs-to ietf-bgp {
    prefix br;
  }

  // import some basic types

  import ietf-inet-types {
    prefix inet;
    reference
      "RFC 6991: Common YANG Data Types.";
  }
  import ietf-yang-types {
    prefix yang;
    reference
      "RFC 6991: Common YANG Data Types.";
  }
  import ietf-routing {
    prefix rt;
    reference
      "RFC 8022: A YANG Data Model for Routing Management.";
  }
  import ietf-bgp-types {
    prefix bt;
    reference
      "RFC XXXX: BGP YANG Model for Service Provider Network.";
  }
  include ietf-bgp-rib-attributes;

  organization
    "IETF IDR Working Group";
  contact
    "WG Web:   <http://tools.ietf.org/wg/idr>
     WG List:  <idr@ietf.org>

     Authors: Mahesh Jethanandani (mjethanandani at gmail.com),
              Keyur Patel (keyur at arrcus.com),
              Susan Hares (shares at ndzh.com,
              Jeffrey Haas (jhaas at juniper.net).";

  description
    "This submodule contains structural data definitions for
     BGP routing tables.

     Copyright (c) 2021 IETF Trust and the persons identified as
     authors of the code. All rights reserved.
     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2021-07-11 {
    description
      "Initial Version";
    reference
      "RFC XXXX, BGP YANG Model for Service Provider Network.";
  }

  grouping bgp-common-route-annotations-state {
    description
      "Data definitions for flags and other information attached
       to routes in both LOC-RIB and Adj-RIB";
    leaf last-modified {
      type yang:timeticks;
      description
        "Timestamp when this path was last modified.

         The value is the timestamp in seconds relative to
         the Unix Epoch (Jan 1, 1970 00:00:00 UTC).";
    }
    leaf eligible-route {
      type boolean;
      description
        "Indicates that the route is eligible for selection for the
         best route in the Loc-Rib in BGP's Decision Process.";
      reference
        "RFC 4271, Section 9.1.";
    }
    leaf ineligible-reason {
      type identityref {
        base ineligible-route-reason;
      }
      description
        "If the route is ineligible for selection for the best route
         in the Loc-Rib in BGP's Decision process, this indicates the
         reason.";
      reference
        "RFC 4271, Section 9.1.";
    }
  }

  grouping bgp-adj-rib-in-post-route-annotations-state {
    description
      "Data definitions for information attached to routes in the
       Adj-RIB-in post-policy table";
    leaf best-path {
      type boolean;
      description
        "Current path was selected as the best path.";
    }
  }

  grouping rib-ext-route-annotations {
    description
      "Extended annotations for routes in the routing tables";
    leaf reject-reason {
      type union {
        type identityref {
          base bgp-not-selected-bestpath;
        }
        type identityref {
          base bgp-not-selected-policy;
        }
      }
      description
        "Indicates the reason the route is not used, either due to
         policy filtering or bestpath selection";
    }
  }

  grouping bgp-adj-rib-common-attr-refs {
    description
      "Definitions of common references to attribute sets for
       multiple AFI-SAFIs for Adj-RIB tables.";
    leaf attr-index {
      type leafref {
        path "../../../../../../../../../attr-sets/"
           + "attr-set/index";
      }
      description
        "Reference to the common attribute group for the
         route.";
    }
    leaf community-index {
      type leafref {
        path "../../../../../../../../../communities/community/"
           + "index";
      }
      description
        "Reference to the community attribute for the route.";
    }
    leaf ext-community-index {
      type leafref {
        path "../../../../../../../../../ext-communities/"
           + "ext-community/index";
      }
      description
        "Reference to the extended community attribute for the
         route.";
    }
  }

  grouping bgp-loc-rib-common-attr-refs {
    description
      "Definitions of common references to attribute sets for
       multiple AFI-SAFIs for LOC-RIB tables.";
    leaf attr-index {
      type leafref {
        path "../../../../../../../attr-sets/attr-set/"
           + "index";
      }
      description
        "Reference to the common attribute group for the
         route.";
    }
    leaf community-index {
      type leafref {
        path "../../../../../../../communities/community/"
           + "index";
      }
      description
        "Reference to the community attribute for the route.";
    }
    leaf ext-community-index {
      type leafref {
        path "../../../../../../../ext-communities/"
           + "ext-community/index";
      }
      description
        "Reference to the extended community attribute for the
         route.";
    }
  }

  grouping bgp-loc-rib-common-keys {
    description
      "Common references used in keys for IPv4 and IPv6
       LOC-RIB entries.";
    leaf origin {
      type union {
        type inet:ip-address;
        type identityref {
          base rt:routing-protocol;
        }
      }
      description
        "Indicates the origin of the route.  If the route is learned
         from a neighbor, this value is the neighbor address.  If
         the route was injected or redistributed from another
         protocol, the origin indicates the source protocol for the
         route.";
    }
    leaf path-id {
      type uint32;
      description
        "If the route is learned from a neighbor, the path-id
         corresponds to the path-id for the route in the
         corresponding adj-rib-in-post table.  If the route is
         injected from another protocol, or the neighbor does not
         support BGP add-paths, the path-id should be set
         to zero, also the default value.

         However, YANG does not allow default values to be set
         for parameters that form the key, so a default value
         cannot be set here.";
    }
  }

  grouping clear-routes {
    description
      "Action to clear BGP routes.";
    container clear-routes {
      if-feature "bt:clear-routes";
      action clear {
        input {
          leaf clear-at {
            type yang:date-and-time;
            description
              "The time, in the future when the clear operation will
               be initiated.";
          }
        }
        output {
          leaf clear-finished-at {
            type yang:date-and-time;
            description
              "The time when the clear operation finished.";
          }
        }
      }
      description
        "Action commands to clear routes governed by a if-feature.";
    }
  }

  grouping ipv4-loc-rib {
    description
      "Top-level grouping for IPv4 routing tables.";
    container loc-rib {
      config false;
      description
        "Container for the IPv4 BGP LOC-RIB data.";
      container routes {
        description
          "Enclosing container for list of routes in the routing
           table.";
        list route {
          key "prefix origin path-id";
          description
            "List of routes in the table, keyed by the route
             prefix, the route origin, and path-id.  The route
             origin can be either the neighbor address from which
             the route was learned, or the source protocol that
             injected the route.  The path-id distinguishes routes
             for the same prefix received from a neighbor (e.g.,
             if add-paths is enabled).";
          leaf prefix {
            type inet:ipv4-prefix;
            description
              "The IPv4 prefix corresponding to the route.";
          }
          uses bgp-loc-rib-common-keys;
          uses bgp-loc-rib-common-attr-refs;
          uses bgp-common-route-annotations-state;
          uses bgp-unknown-attr-top;
          uses rib-ext-route-annotations;
        }
        uses clear-routes;
      }
    }
  }

  grouping ipv6-loc-rib {
    description
      "Top-level grouping for IPv6 routing tables.";
    container loc-rib {
      config false;
      description
        "Container for the IPv6 BGP LOC-RIB data.";
      container routes {
        description
          "Enclosing container for list of routes in the routing
           table.";
        list route {
          key "prefix origin path-id";
          description
            "List of routes in the table, keyed by the route
             prefix, the route origin, and path-id.  The route
             origin can be either the neighbor address from which
             the route was learned, or the source protocol that
             injected the route.  The path-id distinguishes routes
             for the same prefix received from a neighbor (e.g.,
             if add-paths is enabled).";
          leaf prefix {
            type inet:ipv6-prefix;
            description
              "The IPv6 prefix corresponding to the route.";
          }
          uses bgp-loc-rib-common-keys;
          uses bgp-loc-rib-common-attr-refs;
          uses bgp-common-route-annotations-state;
          uses bgp-unknown-attr-top;
          uses rib-ext-route-annotations;
        }
        uses clear-routes;
      }
    }
  }

  grouping ipv4-adj-rib-common {
    description
      "Common structural grouping for each IPv4 adj-RIB table.";
    container routes {
      config false;
      description
        "Enclosing container for list of routes in the routing
         table.";
      list route {
        key "prefix path-id";
        description
          "List of routes in the table, keyed by a combination of
           the route prefix and path-id to distinguish multiple
           routes received from a neighbor for the same prefix,
           e.g., when BGP add-paths is enabled.";
        leaf prefix {
          type inet:ipv4-prefix;
          description
            "Prefix for the route.";
        }
        uses bgp-adj-rib-attr-state;
        uses bgp-adj-rib-common-attr-refs;
        uses bgp-common-route-annotations-state;
        uses bgp-unknown-attr-top;
        uses rib-ext-route-annotations;
      }
      uses clear-routes;
    }
  }

  grouping ipv4-adj-rib-in-post {
    description
      "Common structural grouping for the IPv4 adj-rib-in
       post-policy table.";
    container routes {
      config false;
      description
        "Enclosing container for list of routes in the routing
         table.";
      list route {
        key "prefix path-id";
        description
          "List of routes in the table, keyed by a combination of
           the route prefix and path-id to distinguish multiple
           routes received from a neighbor for the same prefix,
           e.g., when BGP add-paths is enabled.";
        leaf prefix {
          type inet:ipv4-prefix;
          description
            "Prefix for the route.";
        }
        uses bgp-adj-rib-attr-state;
        uses bgp-adj-rib-common-attr-refs;
        uses bgp-common-route-annotations-state;
        uses bgp-adj-rib-in-post-route-annotations-state;
        uses bgp-unknown-attr-top;
        uses rib-ext-route-annotations;
      }
    }
  }

  grouping ipv4-adj-rib {
    description
      "Top-level grouping for Adj-RIB table.";
    container neighbors {
      config false;
      description
        "Enclosing container for neighbor list.";
      list neighbor {
        key "neighbor-address";
        description
          "List of neighbors (peers) of the local BGP speaker.";
        leaf neighbor-address {
          type inet:ip-address;
          description
            "IP address of the BGP neighbor or peer.";
        }
        container adj-rib-in-pre {
          description
            "Per-neighbor table containing the NLRI updates
             received from the neighbor before any local input
             policy rules or filters have been applied.  This can
             be considered the 'raw' updates from the neighbor.";
          uses ipv4-adj-rib-common;
        }
        container adj-rib-in-post {
          description
            "Per-neighbor table containing the paths received from
             the neighbor that are eligible for best-path selection
             after local input policy rules have been applied.";
          uses ipv4-adj-rib-in-post;
        }
        container adj-rib-out-pre {
          description
            "Per-neighbor table containing paths eligible for
             sending (advertising) to the neighbor before output
             policy rules have been applied.";
          uses ipv4-adj-rib-common;
        }
        container adj-rib-out-post {
          description
            "Per-neighbor table containing paths eligible for
             sending (advertising) to the neighbor after output
             policy rules have been applied.";
          uses ipv4-adj-rib-common;
        }
      }
    }
  }

  grouping ipv6-adj-rib-common {
    description
      "Common structural grouping for each IPv6 adj-RIB table.";
    container routes {
      config false;
      description
        "Enclosing container for list of routes in the routing
         table.";
      list route {
        key "prefix path-id";
        description
          "List of routes in the table.";
        leaf prefix {
          type inet:ipv6-prefix;
          description
            "Prefix for the route.";
        }
        uses bgp-adj-rib-attr-state;
        uses bgp-adj-rib-common-attr-refs;
        uses bgp-common-route-annotations-state;
        uses bgp-unknown-attr-top;
        uses rib-ext-route-annotations;
      }
      uses clear-routes;
    }
  }

  grouping ipv6-adj-rib-in-post {
    description
      "Common structural grouping for the IPv6 adj-rib-in
       post-policy table.";
    container routes {
      config false;
      description
        "Enclosing container for list of routes in the routing
         table.";
      list route {
        key "prefix path-id";
        description
          "List of routes in the table.";
        leaf prefix {
          type inet:ipv6-prefix;
          description
            "Prefix for the route.";
        }
        uses bgp-adj-rib-attr-state;
        uses bgp-adj-rib-common-attr-refs;
        uses bgp-common-route-annotations-state;
        uses bgp-adj-rib-in-post-route-annotations-state;
        uses bgp-unknown-attr-top;
        uses rib-ext-route-annotations;
      }
    }
  }

  grouping ipv6-adj-rib {
    description
      "Top-level grouping for Adj-RIB table.";
    container neighbors {
      config false;
      description
        "Enclosing container for neighbor list.";
      list neighbor {
        key "neighbor-address";
        description
          "List of neighbors (peers) of the local BGP speaker.";
        leaf neighbor-address {
          type inet:ip-address;
          description
            "IP address of the BGP neighbor or peer.";
        }
        container adj-rib-in-pre {
          description
            "Per-neighbor table containing the NLRI updates
             received from the neighbor before any local input
             policy rules or filters have been applied.  This can
             be considered the 'raw' updates from the neighbor.";
          uses ipv6-adj-rib-common;
        }
        container adj-rib-in-post {
          description
            "Per-neighbor table containing the paths received from
             the neighbor that are eligible for best-path selection
             after local input policy rules have been applied.";
          uses ipv6-adj-rib-in-post;
        }
        container adj-rib-out-pre {
          description
            "Per-neighbor table containing paths eligible for
             sending (advertising) to the neighbor before output
             policy rules have been applied.";
          uses ipv6-adj-rib-common;
        }
        container adj-rib-out-post {
          description
            "Per-neighbor table containing paths eligible for
             sending (advertising) to the neighbor after output
             policy rules have been applied.";
          uses ipv6-adj-rib-common;
        }
      }
    }
  }
}
