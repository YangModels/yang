module ietf-dots-access-control-list {
      yang-version 1.1;

      namespace "urn:ietf:params:xml:ns:yang:ietf-dots-access-control-list";
      prefix "dots-acl";

      import ietf-access-control-list {
       prefix "ietf-acl";
      }

    organization "IETF DOTS Working Group";

    contact
      "Konda, Tirumaleswar Reddy <TirumaleswarReddy_Konda@McAfee.com>
       Mohamed Boucadair <mohamed.boucadair@orange.com>
       Kaname Nishizuka <kaname@nttv6.jp>
       Liang Xia <frank.xialiang@huawei.com>
       Prashanth Patil <praspati@cisco.com>
       Andrew Mortensen <amortensen@arbor.net>
       Nik Teague <nteague@verisign.com>";

     description
       "This module contains YANG definition for configuring
        filtering rules using DOTS data channel.

        Copyright (c) 2017 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

     revision 2017-11-29 {
       description
         "Initial revision.";
       reference
         "RFC XXXX: Distributed Denial-of-Service Open Threat
                    Signaling (DOTS) Data Channel";
     }

    augment "/ietf-acl:access-lists" {

      description "client-identifier parameter.";

      leaf-list client-identifier {
          type binary;
          description  "A client identifier conveyed by a DOTS gateway
                        to a remote DOTS server.";
       }
    }

    augment "/ietf-acl:access-lists/ietf-acl:acl/ietf-acl:aces" +
            "/ietf-acl:ace/ietf-acl:actions" {
        description "rate-limit action";
        leaf rate-limit {
           when "/ietf-acl:access-lists/ietf-acl:acl/ietf-acl:aces/" +
                "ietf-acl:ace/ietf-acl:actions/" +
                "ietf-acl:forwarding = 'ietf-acl:accept'" {
              description
                "rate-limit valid only when accept action is used";
           }
           type decimal64 {
             fraction-digits 2;
           }
           description "rate-limit traffic";
       }
    }

    augment "/ietf-acl:access-lists/ietf-acl:acl/ietf-acl:aces" +
            "/ietf-acl:ace/ietf-acl:matches/ietf-acl:ipv4-acl" {

      description
          "Handle non-initial and initial fragments for IPv4 packets.";

      leaf fragments {
          type empty;
          description "Handle fragments.";
      }
    }

    augment "/ietf-acl:access-lists/ietf-acl:acl/ietf-acl:aces" +
            "/ietf-acl:ace/ietf-acl:matches/ietf-acl:ipv6-acl" {

      description
          "Handle non-initial and initial fragments for IPv6 packets.";

      leaf fragments {
          type empty;
          description "Handle fragments.";
      }
    }

    augment "/ietf-acl:access-lists" {
      description "Handle ordering of ACLs
                   from a DOTS client";

      container dots-acl-order {
         description
            "Enclosing container for ordering
             the ACLs from a DOTS client";

          list acl-set {
             key "set-name type";
             ordered-by user;
             description
                "List of ACLs";

             leaf set-name {
                type leafref {
                   path "/ietf-acl:access-lists/ietf-acl:acl" +
                        "/ietf-acl:acl-name";
             }
             description
                "Reference to the ACL set name";
             }

             leaf type {
                type leafref {
                   path "/ietf-acl:access-lists/ietf-acl:acl" +
                        "/ietf-acl:acl-type";
             }
             description
                 "Reference to the ACL set type";
             }
          }
      }
    }
}
