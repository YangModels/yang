module ietf-example-dhcpv6-options-sip-server {
  yang-version 1.1;
  namespace "urn:ietf:params:xml:ns:yang:" +
    "ietf-example-dhcpv6-options-sip-server";
  prefix "sip-srv";

  import ietf-inet-types {
    prefix inet;
  }

  import ietf-dhcpv6-server {
    prefix dhcpv6-server;
  }

  organization
    "IETF DHC (Dynamic Host Configuration) Working Group";
  contact
    "WG Web:   <http://datatracker.ietf.org/wg/dhc/>
     WG List:  <mailto:dhcwg@ietf.org>
     Author:   Yong Cui <yong@csnet1.cs.tsinghua.edu.cn>
     Author:   Linhui Sun <lh.sunlinh@gmail.com>
     Editor:   Ian Farrer <ian.farrer@telekom.de>
     Author:   Sladjana Zeichlin <sladjana.zechlin@telekom.de>
     Author:   Zihao He <hezihao9512@gmail.com>
     Author:   Michal Nowikowski <godfryd@isc.org>";

  description "This YANG module contains DHCPv6 options defined
    in RFC 3319 that can be used by DHCPv6 servers.

    Copyright (c) 2021 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see
    the RFC itself for full legal notices.";

  revision 2021-02-22 {
    description "Version update for draft -18 publication.";
    reference "I-D: draft-ietf-dhc-dhcpv6-yang-18";
  }

  revision 2021-01-29 {
    description "Version update for draft -17 publication.";
    reference "I-D: draft-ietf-dhc-dhcpv6-yang-17";
  }

  revision 2021-01-06 {
    description "Version update for draft -16 publication.";
    reference "I-D: draft-ietf-dhc-dhcpv6-yang-16";
  }

  revision 2020-12-22 {
    description "Version update for draft -13 publication.";
    reference "I-D: draft-ietf-dhc-dhcpv6-yang-15";
  }

  revision 2020-12-10 {
    description "Version update for draft -13 publication.";
    reference "I-D: draft-ietf-dhc-dhcpv6-yang-13";
  }

  revision 2020-12-01 {
    description "Version update for draft -12 publication.";
    reference "I-D: draft-ietf-dhc-dhcpv6-yang-12";
  }

  revision 2020-05-26 {
    description "Version update for draft -11 publication and
      to align revisions across the different modules.";
    reference "I-D: draft-ietf-dhc-dhcpv6-yang-11";
  }

  revision 2019-10-18 {
    description "Initial version.";
    reference "I-D: draft-ietf-dhc-dhcpv6-yang";
  }

  /*
   * Groupings
   */

  grouping sip-server-domain-name-list-option-group {
    description "OPTION_SIP_SERVER_D (21) SIP Servers Domain Name
      List";
    reference "RFC 3319: Dynamic Host Configuration Protocol
      (DHCPv6) Options for Session Initiation Protocol (SIP)
      Servers";
    container sip-server-domain-name-list-option {
     description "OPTION_SIP_SERVER_D (21) SIP Servers Domain Name
       List container.";
     list sip-server {
        key sip-serv-id;
        description "SIP server information.";
        leaf sip-serv-id {
          type uint8;
          description "SIP server list identifier identifier.";
        }
        leaf sip-serv-domain-name {
          type inet:domain-name;
          description "SIP server domain name.";
        }
      }
    }
  }

  grouping sip-server-address-list-option-group {
    description "OPTION_SIP_SERVER_A (22) SIP Servers IPv6 Address
      List";
    reference "RFC 3319: Dynamic Host Configuration Protocol
      (DHCPv6) Options for Session Initiation Protocol (SIP)
      Servers";
    container sip-server-address-list-option {
      description "OPTION_SIP_SERVER_A (22) SIP Servers IPv6 Address
        List container.";
     list sip-server {
        key sip-serv-id;
        description "SIP server information.";
        leaf sip-serv-id {
          type uint8;
          description "SIP server list entry identifier.";
        }
        leaf sip-serv-addr {
          type inet:ipv6-address;
          description "SIP server IPv6 address.";
        }
      }
    }
  }

  /*
   * Augmentations
   */

  augment "/dhcpv6-server:dhcpv6-server/dhcpv6-server:option-sets/" +

    "dhcpv6-server:option-set" {
    description "Augment the option definition groupings to the
      server module.";
    uses sip-server-domain-name-list-option-group;
    uses sip-server-address-list-option-group;
  }
}
