module ietf-flexi-grid-ted {
   yang-version 1;

   namespace 
      "urn:ietf:params:xml:ns:yang:ietf-flexi-grid-ted";

   prefix fg-ted;

   import ietf-inet-types {
         prefix inet;
   }

   import ietf-network {
         prefix nd;
   }

   import ietf-network-topology {
         prefix nt;
   }

   organization
      "IETF CCAMP Working Group";

   contact
      "Editor: Jorge Lopez de Vergara 
               <jorge.lopez_vergara@uam.es>";

   description
      "This module contains a collection of YANG definitions for
      a Flexi-Grid Traffic Engineering Database (TED).

      Copyright (c) 2016 IETF Trust and the persons identified as
      authors of the code.  All rights reserved.

      Redistribution and use in source and binary forms, with or
      without modification, is permitted pursuant to, and subject
      to the license terms contained in, the Simplified BSD
      License set forth in Section 4.c of the IETF Trust's Legal
      Provisions Relating to IETF Documents
      (http://trustee.ietf.org/license-info).";

   revision 2016-02-04 {
      description
         "version 3.";

      reference
          "RFC XXX: A Yang Data Model for 
          Flexi-Grid Optical Networks ";
   }
   typedef flexi-grid-node-type {
        type enumeration {
         enum flexi-grid-node {
            description
               "Flexi-grid node";
         }
         enum flexi-grid-transponder {
            description
               "Flexi-grid transponder";
         }
         enum flexi-grid-sliceable-transponder {
            description
               "Flexi-grid sliceable transponder";
         }
     }
     description "Determines the node type: 
         flexi-grid-node,
         flexi-grid-transponder or 
         flexi-grid-sliceable-transponder";
     }

   typedef modulation {
      type enumeration {
         enum QPSK {
             description 
             "QPSK (Quadrature Phase Shift Keying) modulation";
             }
         enum DP_QPSK {
             description "DP-QPSK (Dual Polarization Quadrature
             Phase Shift Keying) modulation";
             }
         enum QAM16 {
             description "QAM16 (Quadrature Amplitude Modulation
             - 4 bits per symbol) modulation";
             }
         enum DP_QAM16 {
             description "DP-QAM16 (Dual Polarization 
             Quadrature Amplitude Modulation - 4 bits per
             symbol) modulation";
             }
         enum DC_DP_QAM16 {
             description "DC DP-QAM16 (Dual Polarization
             Quadrature Amplitude Modulation - 4 bits per
             symbol) modulation";
             }
      }
      description 
         "Enumeration that defines the type of wave modulation";
   }
   typedef FEC {
      type enumeration {
         enum reed-solomon {
             description "Reed-Solomon error correction";
         }
         enum hamming-code{
             description "Hamming Code error correction";
         }
         enum golay{
             description "Golay error correction";
         }
      }
      description "Enumeration that defines the type of 
      Forward Error Correction";
   }

   typedef interface-type {
      type enumeration{
         enum numbered-interface {
             description "The interface is numbered";
         }
         enum unnumbered-interface {
             description "The interface is unnumbered";
         }
      }
      description 
         "Enumeration that defines if an interface is numbered or
         unnumbered";
   }

   typedef flexi-grid-transponder-ref {
      type leafref {
         path 
          "/nd:networks/nd:network/nd:node/nd:node-id";
      }
      description
         "This type is used by data models that need to reference
         a flexi-grid optical transponder.";
   }

   typedef flexi-grid-node-ref {
      type leafref {
         path 
          "/nd:networks/nd:network/nd:node/nd:node-id";
      }
      description
         "This type is used by data models that need to reference
         a flexi-grid optical node.";
   }
   typedef flexi-grid-link-ref {
      type leafref {
         path 
            "/nd:networks/nd:network/nt:link/nt:link-id";
      }

      description
         "This type is used by data models that need to reference
         a flexi-grid optical link.";
   }

   typedef flexi-grid-node-port-ref {
      type leafref {
         path "/nd:networks/nd:network/nd:node/fg-ted:interfaces/"+
         "fg-ted:port-number";
      }
      description
         "This type is used by data models that need to reference
         a flexi-grid optical link.";
   }

   grouping flexi-grid-network-type {
      container flexi-grid-network {
         presence "indicates a flexi-grid optical network";
         description "flexi-grid optical network";
      }
      description "If present, it indicates a a flexi-grid
      optical TED network";
   }

   grouping flexi-grid-network-attributes {
      container flexi-grid-network-attributes {
         leaf name {
            type string;
            description "Name of the topology";
         }
         description "The attributes of the flexi-grid
         TED topology";
      }
      description "The attributes of the flexi-grid
      TED topology";
   }

   grouping flexi-grid-node-attributes {

      description "Set of attributes of an optical node.";

      leaf node-type {
         type flexi-grid-node-type;
         description "Type of flexi-grid node";
      }
      list interfaces {
         key "name";
         unique "port-number";
         description "List of interfaces contained in the node";
         leaf name {
            type string;
            description "Interface name";
         }
         leaf port-number {
            type uint32;
            description "Number of the port used by the interface";
         }
         leaf input-port {
            type boolean;
            description "Determines if the port is an input port";
         }
         leaf output-port {
            type boolean;
            description "Determines if the port is an output port";
         }
         leaf description {
            type string;
            description "Description of the interface";
         }
         leaf type {
            type interface-type;
            description "Determines the type of the interface";
         }
         container numbered-interface {
            when "type == numbered-interface" {
              description "If the interface is a numbered interface";
            }
            description "Container that defines an numbered
            interface with an ip-address";
            leaf n-i-ip-address{
               type inet:ip-address;
               description "IP address of the numbered interface";
            }
         }
         container unnumbered-interface {
            when "type == unnumbered-interface" {
              description 
                "If the interface is an unnumbered interface";
            }
            description "Container that defines an unnumbered 
            interface with an ip-address and a label";
            leaf u-i-ip-address{
               type inet:ip-address;
               description "IP address of the interface";
            }
            leaf label {
               type uint32;
               description "Number as label for the interface";
            }
         }
      }

      container connectivity-matrix {
         description "Connectivity matrix bentween the input and 
             output ports";
         list connections {
            key "input-port-id";
            leaf input-port-id {
               type flexi-grid-node-port-ref;
               description "Identifier of the input port";
            }
            leaf output-port-id {
               type flexi-grid-node-port-ref;
               description "Identifier of the output port";
            }
            description "List of connections between input and
             output ports";
         }
      }
   }

   grouping flexi-grid-transponder-attributes {
      description "Set of attributes of an optical transponder.";
      leaf-list available-modulation {
         type modulation;
         description 
            "List determining all the available modulations";
      }
      leaf modulation-type {
         type modulation;
         description "Modulation type of the wave";
      }
      leaf-list available-FEC {
         type FEC;
         description "List determining all the available FEC";
      }
      leaf FEC-enabled {
         type boolean;
         description 
            "Determines whether the FEC is enabled or not";
      }
      leaf FEC-type {
         type FEC;
         description "FEC type of the transponder";
      }
      //uses flexi-grid-node-attributes;
   }

   grouping flexi-grid-sliceable-transponder-attributes {
      description
         "Grouping that defines a sliceable transponder which is
         composed by several transponders.";
            list transponder-list {
               key "carrier-id";
               description "List of carriers";
               leaf carrier-id {
                  type uint32;
                  description "Identifier of the carrier";
               }
               uses flexi-grid-transponder-attributes;
            }
   }

   grouping flexi-grid-link-attributes {
      description "Set of attributes of an optical link";
         leaf-list available-label-flexi-grid {
            type bits {
               bit is-available{
                 description "Set to 1 when it is available";
               }
            }
            description 
               "Array of bits that determines whether a spectral 
               slot is available or not.";
         }

         leaf N-max {
            type int32;
            description "Maximum number of channels available.";
         }
         leaf base-frequency {
            type decimal64 {
               fraction-digits 5;
            }
            units THz;
            default 193.1;
            description "Default central frequency";
            reference "draft-ietf-ccamp-flexi-grid-fwk-07";
         }

         leaf nominal-central-frequency-granularity {
            type decimal64 {
               fraction-digits 5;
            }
            units GHz;
            default 6.25;
            description 
               "It is the spacing between allowed nominal central
               frequencies and it is set to 6.25 GHz";
            reference "draft-ietf-ccamp-flexi-grid-fwk-07";
         }

         leaf slot-width-granularity {
            type decimal64 {
               fraction-digits 5;
            }
            units GHz;
            description "Minimum space between slot widths";
            reference "draft-ietf-ccamp-flexi-grid-fwk-07";
         }

      }

      augment "/nd:networks/nd:network/nd:network-types" {
         uses flexi-grid-network-type;
          description "Augment network-types including flexi-grid 
          topology";
     }

      augment "/nd:networks/nd:network" {
         when "/nd:networks/nd:network/"+
             "nd:network-types/fg-ted:flexi-grid-network" {
             description "When it is a flexi-grid network";
         }
         uses flexi-grid-network-attributes;
         description "Augment with flexi-grid network attributes";
      }
      augment "/nd:networks/nd:network/nd:node"  {
         when "/nd:networks/nd:network/"+
           "nd:network-types/fg-ted:flexi-grid-network"{
             description "When the node is part of a flexi-grid
             topology";
         }
         uses flexi-grid-node-attributes;
         description "Augment node with flexi-grid attributes";
      }

      augment "/nd:networks/nd:network/nd:node" {
         when "fg-ted:node-type/
                 fg-ted:flexi-grid-transponder"{
             description "When it is a flexi-grid transponder";
         }
         uses flexi-grid-transponder-attributes;
         description "Augment node with transponder attributes";
      }

      augment "/nd:networks/nd:network/nd:node" {
         when "fg-ted:node-type/
                 fg-ted:optical-sliceable-transponder"{
             description 
                 "When it is a flexi-grid sliceable transponder";
         }
         uses flexi-grid-sliceable-transponder-attributes;
         description "Augment node with sliceable transponder 
             attributes";
      }

      augment "/nd:networks/nd:network/nt:link" {
         when "/nd:networks/nd:network/"+
           "nd:network-types/fg-ted:flexi-grid-network"{
             description "When it is a flexi-grid TED";
         }
         uses flexi-grid-link-attributes;
         description "Augment network link attributes when it
             is a flexi-grid topology";
      }
}
