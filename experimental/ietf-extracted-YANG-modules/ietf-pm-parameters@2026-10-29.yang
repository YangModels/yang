module ietf-pm-parameters {
  yang-version 1.1;
  namespace "urn:ietf:params:xml:ns:yang:ietf-pm-parameters";
  prefix pm-pa;

  import ietf-pm-collection {
    prefix pm-co;
    reference
      "RFC YYYY: A YANG Data Model for Performance Monitoring (PM)
       Collection";
  }

  organization
    "IETF Common Control and Measurement Plane (ccamp)
     Working Group";
  contact
    "WG Web: <https://datatracker.ietf.org/wg/ccamp/>
     Editor: Bin Yeong Yoon
       <mailto:byyun@etri.re.kr>";
  description
    "This YANG module defines the performance monitoring (PM)
     parameters of common transport equipment, based on ITU-T
     G.7710, as identities derived from the performance-parameter
     base identity of ietf-pm-collection.  The three transport
     parameter profiles (itu-transport-maintenance-15min,
     itu-transport-maintenance-24hr, and itu-transport-qos-24hr)
     are instances of the parameter-profile list of
     ietf-pm-collection.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); see the RFC
     itself for full legal notices.";

  revision 2026-10-29 {
    description
      "Initial revision.";
    reference
      "RFC XXXX: A YANG Data Model for Performance Monitoring
       Streaming on Common Transport Equipment";
  }

  /*
   * IDENTITIES: transport performance parameters
   */
  identity es {
    base pm-co:performance-parameter;
    description
      "Errored Second (ES).";
    reference
      "ITU-T G.7710";
  }

  identity ses {
    base pm-co:performance-parameter;
    description
      "Severely Errored Second (SES).";
    reference
      "ITU-T G.7710";
  }

  identity bbe {
    base pm-co:performance-parameter;
    description
      "Background Block Error (BBE).";
    reference
      "ITU-T G.7710";
  }

  identity bbc {
    base pm-co:performance-parameter;
    description
      "Background Block Count (BBC).";
    reference
      "ITU-T G.7710";
  }

  identity uas {
    base pm-co:performance-parameter;
    description
      "Unavailable Second (UAS).";
    reference
      "ITU-T G.7710";
  }

  identity pje {
    base pm-co:performance-parameter;
    description
      "Pointer Justification Event (PJE).";
    reference
      "ITU-T G.7710";
  }

  identity sep {
    base pm-co:performance-parameter;
    description
      "Severely Errored Period (SEP).";
    reference
      "ITU-T G.7710";
  }
}
