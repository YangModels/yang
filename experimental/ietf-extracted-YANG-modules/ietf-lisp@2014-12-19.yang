module ietf-lisp {
  namespace "urn:ietf:params:xml:ns:yang:ietf-lisp";
  prefix lisp;
  import ietf-interfaces {
    prefix if;
  }
  import ietf-lisp-address-types {
    prefix lcaf;
  }
  organization
    "IETF LISP (Locator/ID Separation Protocol) Working Group";
  contact
    "lisp@ietf.org";
  description
    "This YANG module defines the generic configuration
     and operational data for LISP. The module can be extended by
     vendors to define vendor-specific LISP configuration
     parameters and policies.

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";

  revision 2014-12-19 {
    description
      "Initial revision.";
    reference
      "https://tools.ietf.org/html/rfc6830";
  }
  identity lisp-device {
    description
      "LISP network device.";
  }
  typedef device-ref {
    type identityref {
      base lisp-device;
    }
    description
      "LISP device reference";
  }
  typedef map-reply-action {
    type enumeration {
      enum no-action {
        value 0;
        description
          "Mapping is kept alive and no encapsulation occurs.";
      }
      enum natively-forward {
        value 1;
        description
          "Matching packets are not encapsulated or dropped but
           natively forwarded.";
      }
      enum send-map-request {
        value 2;
        description
          "Matching packets invoke Map-Requests.";
      }
      enum drop {
        value 3;
        description
          "Matching packets are dropped.";
      }
    }
    description
      "Defines the lisp map-cache ACT type";
    reference "https://tools.ietf.org/html/rfc6830#section-6.1.4";
  }
  typedef eid-id {
    type string;
    description
      "Type encoding of lisp-addresses to be generally used in EID
       keyed lists.";
  }
  typedef auth-key-type {
    type enumeration {
      enum none {
        value 0;
        description
          "No authentication.";
      }
      enum hmac-sha-1-96 {
        value 1;
        description
          "HMAC-SHA-1-96 (RFC2404) authentication is used.";
      }
      enum hmac-sha-256-128 {
        value 2;
        description
          "HMAC-SHA-256-128 (RFC4868) authentication is used.";
      }
    }
    description
      "Enumeration of the authentication mechansms supported by
       LISP.";
    reference
      "https://tools.ietf.org/html/rfc6830#section-6.1.6";
  }
  grouping locators {
    description
      "Group that defines a list of LISP locators.";
    list rloc {
      key "id";
      description
        "List of routing locators";
      leaf id {
        type string;
        description
          "Locator id";
      }
      // FC need to be sure we don't use interface-name in itr
      // cached mappings
      choice address-type {
        description
          "The address type of the locator";
        case interface-name {
          leaf interface {
            type if:interface-state-ref;
            description
              "The name of the interface supporting the locator.";
          }
        }
        case address {
          container locator-address {
            uses lcaf:lisp-address;
            description
              "The locator address provided in LISP canonincal
               address format.";
          }
        }
      }
      leaf priority {
        type uint8;
        description
          "Locator priority.";
      }
      leaf weight {
        type uint8;
        description
          "Locator weight.";
      }
      leaf multicast-priority {
        type uint8;
        description
          "Locator's multicast priority";
      }
      leaf multicast-weight {
        type uint8;
        description
          "Locator's multicast weight";
      }
    }
  }
  grouping mappings {
    description
      "Group that defines a list of LISP mappings.";
    list mapping {
      key "id";
      description
        "List of EID to RLOCs mappings.";
      leaf id {
        type eid-id;
        description
          "Id that uniquely identifies a mapping.";
      }
      container eid {
        uses lcaf:lisp-address;
        description
          "End-host Identifier (EID) to be mapped to a list of
           locators";
      }
      leaf ttl {
        type uint32;
        description
          "Mapping validity period.";
      }
      leaf authoritative {
        type bits {
          bit A {
            description
              "Authoritative bit.";
          }
        }
        description
          "Bit that indicates if mapping comes from an
           authoritative source.";
      }
      choice locator-list {
        case negative-mapping {
          leaf map-reply-action {
            type map-reply-action;
            description
              "Forwarding action for a negative mapping.";
          }
        }
        case positive-mapping {
          container rlocs {
            uses locators;
            description
              "List of locators for a positive mapping.";
          }
        }
        default "positive-mapping";
        description
          "Choice of locator list based on type of mapping.";
      }
    }
  }
  /* Configuration Data */
  container lisp {
    description
      "Configuration parameters for LISP subsystem.";
    container devices {
      description
        "Configuration of LISP devices.";
      list device {
        key "type id";
        description
          "Each entry contains configuration of a lisp-device.";
        leaf type {
          type device-ref;
          description
            "The type of LISP device - identity derived from the
             'lisp-device' base identity.";
        }
        leaf id {
          type string;
          description
            "Arbitrary device name.";
        }
        leaf enabled {
          type boolean;
          default "true";
          description
            "Enable/disable the lisp-device.";
        }
      }
    }
  }

  /* Operational state data */
  container lisp-state {
    config false;
    description
      "Operational state of the LISP subsystem.";
    container devices {
      description
        "Operational state of lisp-devices.";
      list device {
        key "type id";
        description
          "Each entry contains operational data of a lisp-device.";
        leaf type {
          type device-ref;
          description
            "Type of LISP device.";
        }
        leaf id {
          type string;
          description
            "Name of LISP device.";
        }
      }
    }
  }

}
