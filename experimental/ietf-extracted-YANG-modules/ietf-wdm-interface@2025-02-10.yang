module ietf-wdm-interface {
  yang-version 1.1;
  namespace "urn:ietf:params:xml:ns:yang:ietf-wdm-interface";
  prefix wdm-if;

  import ietf-interfaces {
    prefix if;
  }

  import ietf-layer0-types {
    prefix "l0-types";
  }

  organization
    "IETF CCAMP Working Group";

  contact
   "WG Web:   <https://datatracker.ietf.org/wg/ccamp/>
    WG List:  <mailto:ccamp@ietf.org>

    Editor:   Dharini Hiremagalur <mailto:dharinih@juniper.net>
    Editor:   Gabriele Galimberti <mailto:ggalimbe56@gmail.com>
    Editor:   Gert Grammel <mailto:ggrammel@juniper.net>
    Editor:   Roberto Manzotti <mailto:rmanzott@cisco.com>";

  description
     "This module contains a collection of YANG definitions for
     configuring DWDM Optical interfaces.

     Copyright (c) 2024 IETF Trust and the persons identified as
     authors of the code.  All rights reserved.

     Redistribution and use in source and binary forms, with or
     without modification, is permitted pursuant to, and subject
     to the license terms contained in, the Revised BSD
     License set forth in Section 4.c of the IETF Trust's Legal
     Provisions Relating to IETF Documents
     (https://trustee.ietf.org/license-info).

     This version of this YANG module is part of RFC XXXX; see
     the RFC itself for full legal notices.";

// RFC Ed.: replace XXXX with actual RFC number and remove
// this note
// replace the revision date with the module publication date
// the format is (year-month-day)

  revision "2025-02-10" {
    description
      "v1.0 Initial Version";
    reference
      "RFC XXXX: YANG model to manage the optical interface
       parameters for an external transponder in a WDM network";
    // RFC Ed.: replace XXXX with actual RFC number, update date
    // information and remove this note

  }

  // Need to verify if the enumeration is the proper approach for
  // the tca-types, since the list is not fully standardized adn
  // subject to change.
  typedef wdm-if-tca-types {
    type enumeration {
      enum laser-linewdt-tca {
        description "The laser linewidth TCA";
      }
      enum tx-power-tca {
        description "The tx power TCA";
      }
      enum rx-power-tca {
        description "The tx power TCA";
      }
      enum pol-power-diff-tca {
        description
          "The power difference between polarization TCA";
      }
      enum pol-skew-diff-tca {
        description
          "The skew between the two polarization TCA";
      }
      enum cd-tca {
        description "The chromatic dispersion TCA";
      }
      enum frequency-offset-tca {
        description "Frequency offset TCA";
      }
      enum osnr-tca {
        description "OSNR TCA";
      }
      enum laser-temperature-tca {
        description "Laser temperature TCA";
      }
      enum pre-fec-ber-tca {
        description "Pre Fec BER TCA";
      }
      enum uncorrected-words-tca {
        description "Uncorrected words TCA";
      }
      enum q-factor-tca{
        description "Q Factor TCA";
      }
    }
    description
      "The different types of TCA's for DWDM Interfaces";
  }

  grouping wdm-if-tca-thresholds {
    description "Thresholds for TCA's";
    leaf tca-type {
      type wdm-if-tca-types;
      description
        "type of the TCA that identify the
        performance measurement, eg TX Power";
    }
    leaf tca-name {
      type string;
      description
        "A name of the TCA that explain the TCA scope
        eg 'Low TX Power'";
    }
    leaf raise-threshold {
      type int32;
      description
        "A TCA is raised if the variable cross this threshold:
        - if raise-threshold is greater than clear-threshold
        (or clear threshold is not defined), the TCA
        is raised when the value exceed the threshold
        - if raise-threshold is smaller that clear-threshold, the
        TCA is raised when the value fall below the threshold";
    }
    leaf clear-threshold {
      type int32;
      description
        "A TCA cleared when the variable cross the threshold in the
        direction defined for raise-threshold";
    }
  }

  grouping wdm-if-tca-list {
    description "List of TCA's";
    leaf number-of-tcas-supported {
      type uint32;
      config false;
      description "Number of TCAs supported by this interface";
    }
    list tca-list {
      key "tca-type";
      description "List of the TCAs";
      uses wdm-if-tca-thresholds;
    }
  }

  grouping wdm-if-mode-params {
    description "OCh mode parameters";

    leaf min-osnr-margin {
      type l0-types:snr-or-null;
      units "dB";
      config false;
      description "OSNR margin to FEC threshold";
    }
    leaf q-margin {
      type int32;
      units "dB";
      config false;
      description "Q-Factor margin to FEC threshold";
    }
    leaf central-frequency {
      type l0-types:frequency-thz;
      description
        "This parameter indicates the interface Central Frequency";
    }
//    uses wdm-if-fec-tca-thresholds;
    uses wdm-if-tca-list;
  }

  grouping wdm-if-statistics {
    description "OCh statistics";
    leaf cur-osnr {
      type l0-types:snr;
      units "dB";
      config false;
      description "OSNR margin to FEC threshold";
    }
    leaf cur-q-factor {
      type int32;
      units "dB";
      config false;
      description "Q-Factor of the interface";
    }
    leaf uncorrected-words {
      type uint64;
      config false;
      description "Post-FEC errored words";
    }
    leaf pre-fec-ber {
      type decimal64 {
        fraction-digits 18;
      }
      config false;
      description "Pre-FEC errored words";
    }
  }

  notification wdm-if-tca {
    description "A output TCA notification";

    leaf "if-name" {
      type leafref { path "/if:interfaces/if:interface/if:name"; }
      mandatory true;
      description "Interface name";
    }
    leaf tca-type {
      type wdm-if-tca-types;
      mandatory true;
      description "Type of TCA for eg min tx power TCA";
    }
    leaf tca-name {
      type string;
      description
        "A name of the TCA that explain the TCA scope
        eg 'Low TX Power'";
    }
  }

  augment "/if:interfaces" {
    description
      "Template definition for Optical Interface explicit-modes";
    container "wdm-if-templates" {
      config false;
      description "Optical Interface explicit-mode templates";
      container explicit-transceiver-modes {
        description
          "The top level container for the list of the
          transceivers' explicit modes.";
        list explicit-transceiver-mode {
          key explicit-transceiver-mode-id;
          description
            "The list of the transceivers' explicit modes.";
          leaf explicit-transceiver-mode-id {
            type string;
            description
              "The identifier of the transceivers' explicit mode.";
          }
          uses l0-types:explicit-mode;
        } // list explicit-transceiver-mode
      } // container explicit-transceiver-modes
    }  // container dwdm-if-templates
  }  // augment interfaces

  augment "/if:interfaces/if:interface" {
    description "Parameters for an optical interface";

    container wdm-interface {
      description
        "Container for capabilities, configuration,
        current operational data for a DWDM interface";

      uses l0-types:transceiver-capabilities {
        augment "supported-modes/supported-mode/mode/"
        + "explicit-mode/explicit-mode" {
          description
            "Augment the explicit-mode container with the
            proper leafref.";
          leaf explicit-transceiver-mode-ref {
            type leafref {
              path "../../../../../../wdm-if:wdm-if-templates"
                   + "/wdm-if:explicit-transceiver-modes"
                   + "/wdm-if:explicit-transceiver-mode"
                   + "/wdm-if:explicit-transceiver-mode-id";
            }
            description
              "The reference to the explicit transceiver
              mode template.";
          }
        }
      }

      container current-wdm-if-parameters {
        leaf configured-mode {
          type union {
            type empty;
            type leafref {
              path "../../supported-modes/supported-mode/mode-id";
            }
          }
          description
            "Reference to the configured mode for transceiver
            compatibility approach.

            The empty value is used to report that no mode has
            been configured and there is no default mode.

            When not present, the configured-mode is not reported
            by the server.";
        }
        uses l0-types:common-transceiver-param;
        description "Current parameters of this interface";
        uses wdm-if-mode-params;
        uses wdm-if-statistics;
      }
    }
  }
}
