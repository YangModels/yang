submodule ietf-snmp-proxy {

  belongs-to ietf-snmp {
    prefix snmp;
  }

  include ietf-snmp-common;
  include ietf-snmp-target;

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";

  description
    "This submodule contains a collection of YANG definitions
     for configuring SNMP proxies.

     Copyright (c) 2011 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  reference
    "RFC3413: Simple Network Management Protocol (SNMP)
              Applications";

  // RFC Ed.: update the date below with the date of RFC publication
  // and remove this note.

  revision 2012-03-07 {
    description
      "Initial revision.";
    reference
      "RFC XXXX: A YANG Data Model for SNMP Configuration";
  }

  augment /snmp:snmp {
    if-feature snmp:proxy;

    list proxy {
      key name;

      description
        "List of proxy parameters.";
      reference "SNMP-PROXY-MIB.snmpProxyTable";

      leaf name {
        type snmp:identifier;
        description
          "Identifies the proxy parameter entry.";
        reference "SNMP-PROXY-MIB.snmpProxyName";
      }
      leaf type {
        type enumeration {
          enum read;
          enum write;
          enum trap;
          enum inform;
        }
        mandatory true;
        reference "SNMP-PROXY-MIB.snmpProxyType";
      }
      leaf context-engine-id {
        type snmp:engine-id;
        mandatory true;
        reference "SNMP-PROXY-MIB.snmpProxyContextEngineID";
      }
      leaf context-name {
        type snmp:context-name;
        reference "SNMP-PROXY-MIB.snmpProxyContextName";
      }
      container params-in {
        choice params {
          mandatory true;
          description
            "This choice is augmented with case nodes containing
             security model specific configuration parameters.  Each
             such case represents one entry in the
             snmpTargetParamsTable.

             When the snmpProxyTargetParamsIn object contains a
             reference to a non-existing snmpTargetParamsEntry, this
             choice does not contain any case, and vice versa.";
        }
        reference "SNMP-PROXY-MIB.snmpProxyTargetParamsIn";
      }
      leaf single-target-out {
        when "../type = read or ../type = write";
        type leafref {
          path "/snmp:snmp/snmp:target/snmp:name";
        }
        description
          "When the snmpProxySingleTargetOut object contains
           a value which does not select an snmpTargetAddrEntry,
           this leaf does not exist.";
        reference "SNMP-PROXY-MIB.snmpProxySingleTargetOut";
      }
      leaf multiple-target-out {
        when "../type = trap or ../type = inform";
        type leafref {
          path "/snmp:snmp/snmp:target/snmp:tag";
        }
        description
          "When the snmpProxyMultipleTargetOut object contains
           a value which does not select any snmpTargetAddrEntries,
           this leaf does not exist.";
        reference "SNMP-PROXY-MIB.snmpProxyMultipleTargetOut";
      }
    }
  }
}
