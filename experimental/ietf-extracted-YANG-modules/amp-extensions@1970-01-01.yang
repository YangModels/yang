submodule "amp-extensions" {
        belongs-to "amp-adm" {
                prefix "amp";
        }

        description
                "This submodule contains the set of core extensions necessary to "
                +"define an Asynchronous Management Protocol data model.";
        reference "draft Asynchronous Management Protocol";

        extension fulloid {
                argument "value";
                description
                        "This extension defines the complete OID for the parent "
                        +"statement. ";
        }
        extension suboid {
                argument "value";
                description
                        "This extension defines a sub-OID of a statement relative "
                        +"to a parent-statement OID.";
        }

        extension nickname {
                argument "id";
                description
                        "A nickname is a single integer ID which correpsonds to a "
                        +"full OID value.";
        }
        extension compressoid {
                argument "value";
                description
                        "This extension allows using an ADM nickname within the "
                        +"ADM itself.";
        }

        extension "group" {
                argument "name";
                description
                        "A logical grouping of ADM items under a parent OID.";
        }

        extension "primitive" {
                argument "name";
                description "A single typed value associated with an OID.";
        }

        extension "computed" {
                argument "name";
                description "A single typed value-expression associated with an OID.";
        }

        extension "report" {
                argument "name";
                description "Definition of a report within an ADM.";
        }
        extension "reportitem" {
                argument "name";
                description
                        "A reference to a primitive within a report definition.";
        }

        extension "control" {
                argument "name";
                description "Definition of a control within an ADM.";
        }
        extension "parameter" {
                argument "name";
                description
                        "An individual parameter to a \"control\" statement. "
                        +"Order of parameters is signifigant within a control.";
        }
        extension "result" {
                argument "name";
                description
                        "An individual result value reported as a response to "
                        +"a \"control\" statement. "
                        +"Order of results is signifigant within a control.";
        }
}
