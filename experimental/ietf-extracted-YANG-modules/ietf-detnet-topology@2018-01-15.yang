module ietf-detnet-topology {
  namespace "urn:ietf:params:xml:ns:yang:ietf-detnet-topology";
  prefix "detnet-topo";

  import ietf-te-types {
    prefix "te-types";
  }

  import ietf-routing-types {
    prefix "rt-types";
  }

  import ietf-te-topology {
    prefix "tet";
  }

  import ietf-network {
    prefix "nw";
  }

  import ietf-network-topology {
    prefix "nt";
  }

  organization
    "IETF Deterministic Networking(detnet)Working Group";

  contact
   "WG Web:   <http://tools.ietf.org/wg/detnet/>
    WG List:  <mailto:detnet@ietf.org>

    WG Chair: Lou Berger
              <mailto:lberger@labn.net>

    Editor:   Xuesong Geng
              <mailto:gengxuesong@huawei.com>

    Editor:   Mach Chen
              <mailto:mach.chen@huawei.com>

    Eidtor:   Reshad Rahman
              <rrahman@cisco.com>";

  description
    "This YAGN module augments the 'ietf-te-topology'
     module with detnet capability data for detnet
     configuration";

  revision "2018-01-15" {
    description "Initial revision";
    reference "RFC XXXX: YANG Data Model for DetNet Topologies";
    //RFC Ed.: replace XXXX with actual RFC number and remove
    // this note
  }

  grouping detnet-link-info-attributes{
    description
      "DetNet capability attributes in a DetNet topology";
    container detnet-performance-metric-attributes{
      description
        "Link performance information in real time.";
      uses detnet-performance-metric-attributes;
    }
    container detnet-queuing-management-algorithm{
      description
        "Detnet queuing management algorithm used in
         output queue";
      uses detnet-queuing-management-algorithm;
    }
  }

  grouping detnet-performance-metric-attributes{
    description
      "Link performance information in real time.";
    container maximum-detnet-reservable-bandwidth{
      uses te-types:te-bandwidth;
      description
        "This container specifies the maximum bandwidth
         that is reserved for DetNet on this link.";
    }
    container reserved-detnet-bandwidth{
      uses te-types:te-bandwidth;
      description
        "This container specifies the bandwidth that has
         been reserved for DetNet on this link.";
    }
    container available-detnet-bandwidth{
      uses te-types:te-bandwidth;
      description
        "This container specifies the bandwidth that can
         be used for new DetNet flows on this link.";
    }
    leaf minimum-detnet-device-delay{
      type uint32;
      description
        "Minimum delay in the device for DetNet flows";
    }
    leaf maximum-detnet-device-delay{
      type uint32;
      description
        "Maximum delay in the device for DetNet flows";
    }
  }

  grouping detnet-queuing-management-algorithm{
    description
      "Detnet queuing management algorithm used in
       output queue";
    leaf queuing-management-algorithm{
      type enumeration{
        enum credit-based-shaping{
          reference
            "IEEE P802.1 Qav";
        }
        enum time-aware-shaping{
          reference
            "IEEE P802.1 Qbv";
        }
        enum  cyclic-queuing-and-forwarding{
          reference
            "IEEE P802.1 Qch";
        }
        enum  asynchronous-traffic-shaping{
          reference
            "IEEE P802.1 Qcr";
        }
      }
      description
        "Detnet queuing management algorithm type";
    }
  }

  grouping detnet-node-info-attributes{
    description
      "DetNet capability attributes in a DetNet node";
    container detnet-node-type{
      description
        "Three types of DetNet nodes";
      reference
        "draft-ietf-detnet-architecture-03:
         Deterministic Networking Architecture";
      uses detnet-node-type;
    }
    container detnet-resource-reservation-attributes{
      description
        "Attributes about resource reservation for
         DetNet flows";
      uses detnet-resource-reservation-attributes;
    }
    leaf detnet-elimination-capability{
      type boolean;
      description
        "This node is able to do DetNet packet
         elimination";
    }
    leaf detnet-replication-capability{
      type boolean;
      description
        "This node is able to do DetNet packet
         replication";
    }
  }

  grouping detnet-node-type{
    description
      "This grouping defines three types of DetNet nodes";
    reference
      "draft-ietf-detnet-architecture-03:Deterministic
       Networking Architecture";
    leaf detnet-node-type{
      type enumeration{
        enum edge-node{
          description
            "An instance of a DetNet relay node that
             includes either a DetNet service layer proxy
             function for DetNet service protection (e.g.
             the addition or removal of packet sequencing
             information) for one or more end systems, or
             starts or terminate congestion protection at
             the DetNet transport layer,analogous to a
             Label Edge Router (LER).";
        }
        enum relay-node{
          description
            "A DetNet node including a service layer
             function that interconnects different DetNet
             transport layer paths to provide service
             protection.A DetNet relay node can be a bridge,
             a router, a firewall, or any other system that
             participates in the DetNet service layer. It
             typically incorporates DetNet transport layer
             functions as well, in which case it is
             collocated with a transit node.";
        }
        enum  transit-node{
          description
            "A node operating at the DetNet transport layer,
             that utilizes link layer and/or network layer
             switching across multiple links and/or
             sub-networks to provide paths for DetNet
             service layer functions.Optionally provides
             congestion protection over those paths.An MPLS
             LSR is an example of a DetNet transit node.";
        }
      }
      description
      "The type this node belongs to, which also determines
       the role the node can play in DetNet ";
    }
  }

  grouping detnet-resource-reservation-attributes{
    description
      "This grouping describs reservation operation for
       the entire device";
    leaf MaxFanInPorts{
      type uint32;
      description
        "maximum number of fan-in ports in the device";
    }
    leaf MaxPacketSize{
      type uint32;
      description
      "maximum Packet size the device allows";
    }
    leaf MaxDetNetClasses{
      type uint32;
      description
        "maximum number of traffic classes that can be
         reserved for DetNet";
    }
  }

  augment "/nw:networks/nw:network/nw:node" {
    when "../nw:network-types/tet:te-topology"
    {
      description
      "";
    }
    description
      "Advertised DetNet link information attributes.";
    uses detnet-link-info-attributes;
  }

  augment "/nw:networks/nw:network/nt:link" {
    when "../nw:network-types/tet:te-topology"
    {
      description
      "";
    }
    description
      "Advertised DetNet node information attributes.";
    uses detnet-node-info-attributes;
  }
}
