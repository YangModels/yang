module ietf-netconf-notifications-nmda {
  namespace "urn:ietf:params:xml:ns:yang:ietf-netconf-notifications-nmda";
  prefix ncdn;

  import ietf-netconf {
    prefix nc;
  }
  import ietf-datastores {
    prefix ds;
  }
  import ietf-origin {
    prefix or;
  }
  import ietf-netconf-notifications {
    prefix ncn;
  }

  organization
    "IETF NETCONF (Network Configuration Protocol) Working Group";
  contact
    "WG Web:   <http://tools.ietf.org/wg/netconf/>
     WG List:  <mailto:netconf@ietf.org>

     WG Chair: Kent Watsen
               <mailto:kwatsen@juniper.net>

     WG Chair: Mahesh Jethanandani
               <mailto:mjethanandani@gmail.com>

     Editor:   Qin Wu
               <mailto:bill.wu@huawei.com>

     Editor:   Xiaojian Ding
               <mailto:dingxiaojian1@huawei.com>";
  description
    "This module defines a YANG data model for use with the
     NETCONF protocol that allows the NETCONF client to
     receive additional common NETCONF base event notifications
      related to NMDA.

     Copyright (c) 2012 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC xxxx; see
     the RFC itself for full legal notices.";

  revision 2018-02-01 {
    description
      "Initial version.";
    reference "RFC xxx: NETCONF Base Notifications for NMDA";
  }
  identity change-phase {
    description
      "Base identity for change phanse.";
  }

  identity inactive {
    base change-phase;
    description
      "Identity for inactive data.It is referred to as
      configuration that is not currently used.";
  }

  identity in-use {
    base change-phase;
    description
      "Identity for the in use data. It is referred to as
       configuration that is actively used.";
  }

  identity Remnant  {
    base in-use;
    description
      "Identity for the remnant configuration. It indicates that
       both the previous and current configuration coexist.";
  }

  identity miss-resource {
    base in-use;
    description
      "Identity for the missing resource.It indicates that
       Configuration in <intended> can refer to resources that are not
      available or otherwise not physically present and parts of <intended>
      are not applied.";
  }

  identity sys-resource {
    base in-use;
    description
      "Identity for the system congtrolled resource.It indicates that
       a system controlled resource has matching configuration in
      <intended>.";
  }
  notification netconf-data-change {
    description
      "Generated when the NETCONF server detects that the
       <operational> datastore or conventional configuration datastore
       has been changed by a management session.
       The notification summarizes the edits that
       have been detected.

       The server MAY choose to also generate this
       notification while loading a datastore during the
       boot process for the device.";
    uses ncn:changed-by-parms;
    leaf datastore {
      type identityref {
        base ds:datastore;
      }
      default "ds:operational";
      description
        "Indicates which datastore has changed or which datastore is
         target of edit-data operation.";
    }

    list edit {
      description
        "An edit record SHOULD be present for each distinct
         edit operation that the server has detected on
         the target datastore.  This list MAY be omitted
         if the detailed edit operations are not known.
         The server MAY report entries in this list for
         changes not made by a NETCONF session (e.g., CLI).";
      leaf target {
        type instance-identifier;
        description
          "Topmost node associated with the configuration change.
           A server SHOULD set this object to the node within
           the datastore that is being altered.  A server MAY
           set this object to one of the ancestors of the actual
           node that was changed, or omit this object, if the
           exact node is not known.";
      }
      leaf origin {
        type identityref {
          base or:origin;
        }
        description
          "Indicate origin that most accurately reflects the source of the
           configuration that is in use by the system.";
      }
    leaf current-phase {
        type identityref {
          base change-phase;
        }
        description
          "Indicate the current phase of the <operational> datastore or
           conventional configuration datastore change, e.g.,the intended
           datastore is validating, the intended datastore is validated,
           the configuration is applying, the configuration is applied.";
      }
      leaf operation {
        type nc:edit-operation-type;
        description
          "Type of edit operation performed.
           A server MUST set this object to the NETCONF edit
           operation performed on the target datastore.";
      }
    }
  }
}
