module ietf-lmo-usage {
  yang-version 1.1;
  namespace "urn:ietf:params:xml:ns:yang:ietf-lmo-usage";
  prefix lmousage;
  import ietf-yang-types {
    prefix yang;
  }
  import ietf-lmo-assets-inventory {
    prefix lmoasset;
  }
  import ietf-lmo-common {
    prefix lmocom;
  }
  organization
    "IETF OPSA (Operations and Management Area) Working Group";
  contact
    "WG Web:   <https://datatracker.ietf.org/wg/opsawg/>
     WG List:  <mailto:opsawg@ietf.org>
     Editor:  Marisol Palmero
              <mailto:mpalmero@cisco.com>
     Editor:  Josh Suhr
              <mailto:josuhr@cisco.com>
     Editor:  Sudhendu Kumar
              <mailto:skumar23@ncsu.edu>";
  description
    "This YANG module includes the different attributes that define
     description, usage and resource consumption for specific
     features or capabilities of assets.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";
  revision 2021-08-23 {
    description
      "Initial revision for Product Usage Module as part of the
       LMO YANG Model";
    reference
      "RFC XXXX: LMO YANG Model";
  }
  container features {
    config false;
    description
      "Features";
    list feature {
      key "id";
      description
        "Feature List";
      leaf id {
        type string;
        description
          "Identifies feature uniquely across all products of a
          particular vendor: vendor-id/asset-id/id";
      }
      leaf name {
        type string;
        description
          "Friendly name of the feature";
      }
      leaf summary {
        type string;
        description
          "Brief description of the feature";
      }
      leaf category {
        type string;
        description
          "Feature category or tag list (as applicable to the
          product)";
      }
      leaf entitlement {
        type string;
        description
          "Minimum entitlement level, subscription, or license level
           required for the feature";
      }
      leaf first-available-version {
        type string;
        description
          "The first version in which this feature was enabled";
      }
      container backported-versions {
        config false;
        description
          "software patch or update is taken from a recent software
          version and applied to an older version of the same
          software";
        list backported-version {
          config false;
          description
           "Backport releases to older release";
          leaf version {
            type identityref {
              base lmocom:version;
            }
            description
             "version of the backport release";
          }
        }
      }
      leaf scope {
        type identityref {
          base lmocom:feature-scope;
        }
        description
          "Optional tag that could apply to any of the usage
          features, so that if there are multiple dimensions of
          reporting that need to be accommodated (i.e., report
          feature usage by 'site')";
      }
      list config-options {
        key "id";
        description
          "Feature configuration profile - optional, for features
          that require configuration beyond enable/disable";
        leaf id {
          type string;
          description
            "Identify feature configuration option uniquely across
            all products";
        }
        leaf name {
          type string;
          description
            "Friendly name of the feature option";
        }
        leaf summary {
          type string;
          description
            "Brief description of the feature option";
        }
        list characteristic {
          key "id";
          description
            "Characteristics of feature configuration options,
             i.e. value=enabled/disabled";
          leaf id {
            type string;
            description
              "Identifier for feature option configuration
               characteristic";
          }
          leaf name {
            type string;
            description
              "Friendly name for feature option configuration
               characteristic";
          }
          leaf value {
            type string;
            description
              "Configuration characteristic value; describes how this
               feature option characteristic is configured";
          }
        }
      }
      leaf asset {
        type leafref {
          path "/lmoasset:assets/lmoasset:asset/lmoasset:id";
        }
        description
          "Asset to which this feature is attached";
      }
      container subfeatures {
        description
          "Sub-features to the top-level feature";
        list subfeature {
          key "id";
          description
            "Subfeature ID";
          leaf id {
            type leafref {
              path "/features/feature/id";
            }
            description
              "Reference to Feature ID";
          }
        }
      }
    }
  }
  container usages {
    config false;
    description
      "feature usage characteristic";
    list usage {
      key "id";
      description
        "Feature usage profile";
      leaf id {
        type string;
        description
          "Identify feature usage characteristic uniquely across
           all products";
      }
      leaf feature {
          type leafref {
            path "/features/feature/id";
          }
          description
            "usage link to a feature";
    }
    container capture-info {
      config false;
      description
        "Capture information for this data";
      leaf collected-on {
        type yang:date-and-time;
        description
          "Time at which this data was collected";
      }
      leaf collected-from {
        type string;
          description
            "Identifier for original source of this data";
      }
    }
    leaf name {
      type string;
      description
        "Name of feature usage characteristic";
    }
    leaf summary {
      type string;
      description
        "Brief description of feature usage characteristic";
    }
    leaf uri {
      type string;
      description
        "Target URI of feature characteristic, if applicable - e.g.,
         for clickstream or API";
    }
    leaf deployment-mode {
      type identityref {
        base lmocom:deployment-mode;
      }
      description
        "Deployment mode for the feature. When applicable, feature
         might be independent of the deployment mode in the asset;
         e.g., cloud, HA cluster, virtual appliance, etc.";
      }
      leaf scope {
        type identityref {
          base lmocom:feature-scope;
        }
        description
          "Optional tag that could apply to any of the usage
          features, so that if there are multiple dimensions of
          reporting that need to be accommodated, (i.e., report
          feature usage by 'site')";
      }
      leaf activation-status {
        type string;
        description
          "Feature activation status for this instance of the product
           (on/off; active/inactive; enabled/disabled)";
      }
      leaf instances {
        type uint32;
        description
          "Number of instances or end-points using this feature";
      }

      leaf count-type {
        type identityref {
          base lmocom:counter-type;
        }
        description
          "Specify the counter type i.e accumulated-count,
           average-count, last-count, high-water mark count
           (+time stamp), low-water mark count (+time stamp)";
      }
      leaf timestamp {
        type yang:date-and-time;
        description
          "Some counters will benefit from timestamp based on the
          time when the counter has been collected";
      }
      leaf count {
        type uint32;
        units "times";
        description
          "Count of times the feature has been used";
      }
      list frequency {
        key "name";
        description
          "Frequency with which the feature is used";
        leaf name {
          type string {
            length "1..64";
          }
          description
            "reference in case that feature is for different purpose
            of usage";
        }
        leaf type-freq {
          type string;
          description
            "Frequency type, i.e daily, weekly, monthly";
        }
        leaf value {
          type yang:counter64;
          description
            "Value collected for the usage";
        }
      }
      list resource-consumption {
        key "id";
        description
          "Resource consumption profile";
        leaf id {
          type string;
          description
            "Identify resource for consumption measurement";
        }
        leaf name {
          type string;
          description
            "Friendly name of the resource";
        }
        leaf summary {
          type string;
          description
            "Brief description of the resource";
        }
        list characteristic {
          key "id";
          description
            "Characteristic of resource consumption";
          leaf id {
            type string;
            description
              "Identifier for resource consumption characteristic";
          }
          leaf name {
            type string;
            description
              "Friendly name for resource consumption
              characteristic";
          }

          leaf unit {
            type string;
            description
              "unit of measurement for the characteristic";
          }

          // NEED to define identity type for unit: min, hour, sec,
          // days, ...

          leaf value {
            type yang:counter64;
            description
              "Resource consumption characteristic measurement";
          }
          leaf value-max {
            type yang:counter64;
            description
              "Maximum resource consumption characteristic value";
          }
        }
      }
    }
  }
}
