module ietf-bulk-subscription {
  yang-version 1.1;
  namespace "urn:ietf:params:xml:ns:yang:ietf-bulk-subscription";
  prefix bs;

  import ietf-subscribed-notifications {
    prefix sn;
  }
  import ietf-yang-types {
    prefix yang;
  }

  organization
    "IETF NETCONF (Network Configuration) Working Group";
  contact
    "";
  description
    "NETCONF Protocol Data Types and Protocol Operations.

     Copyright (c) 2011 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6241; see
     the RFC itself for full legal notices.";

  revision 2019-09-23 {
    description
      "Initial revision";
       reference "RFC XXXX: Bulk Subscription to YANG Event Notification";
  }
  identity encode-cbor {
    base sn:encoding;
    description
      "Encode data using cbor.";
  }
  identity encode-gpb {
    base sn:encoding;
    description
      "Encode data using gpb.";
  }
  container bundle-groups {
    list bundle-group {
      key "group-id";
      leaf group-id {
        type string;
        description
          "This group ID is used as an index within the bulk subscription module
           , which indicates subscription classification criteria.";
      }
      leaf-list subscription-id {
        type leafref {
         path "/sn:subscriptions/sn:subscription/sn:id";
        }
        description
          "subscription-id";
      }
    leaf-list yang-module {
      type yang:yang-identifier;
      description
        "Name of the YANG module list supported by the publisher.";
    }
      description
        "List for group that classify different subscriptions into groups.";
    }
    leaf compression-algorithm {
      type string;
      description
        "The technology with which an originator compress bytestream
         contents.";
    }
    description
      "Container for subscription group.";
  }
  augment "/sn:subscriptions/sn:subscription" {
      leaf max-bundle-latency {
      type uint32;
      units centiseconds;
      default 400;
      description
      "The maximum latency before a specific YANG Notifications generated
       must egress a publisher.";
     }
    leaf compression-algorithm {
      type string;
      description
        "The technology with which an originator compress bytestream
         contents.";
    }
    description
      "Augment the subscribed-notifications module with transport specific inforamtion.";
  }

  rpc bundle-subscription {
   description
    "Bundle subscription. This paremeter indicates what subscription must be bundled together.";
    input {
     leaf group-id {
      type string;
      description
      "This group ID is used as an index within the bulk subscription module";
      }
    leaf-list subscription-id {
      type uint32;
      description
       "Subscription-id paremeter indicates what subscription must be bundled together.";
      }
   leaf-list mask-subscription-id {
      type uint32;
      description
       "Mask subscription-id paremeter indicates what subscription must
        not be bundled together.";
      }
     leaf max-bundle-latency {
      type uint32;
      units centiseconds;
      default 400;
      description
      "The maximum latency before a specific YANG Notifications generated
       must egress a publisher.";
     }
    leaf compression-algorithm {
      type string;
      description
        "The technology with which an originator compress bytestream
         contents.";
    }
    }
  }
}
