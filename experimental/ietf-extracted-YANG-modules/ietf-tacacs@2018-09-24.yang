module ietf-tacacs {
  namespace "urn:ietf:params:xml:ns:yang:ietf-tacacs";
  prefix tcs;

  import ietf-inet-types {
    prefix inet;
  }
  import ietf-network-instance {
    prefix ni;
  }
  import ietf-system {
    prefix sys;
  }

  organization
    "IETF Opsawg (Operations and Management Area Working Group)";
  contact
    "WG Web:   <http://tools.ietf.org/wg/opsawg/>
     WG List:  <mailto:opsawg@ietf.org>

     Editor:   Guangying Zheng
               <mailto:zhengguangying@huawei.com>";
  description
    "This module provide defines a component that describe the
      configuration of TACACS+ client.";

  revision 2018-09-24 {
    description
      "Initial revision.";
    reference "foo";
  }

  typedef password-extend {
    type string {
      length "1..255";
    }
    description
      "now password extend is like string";
  }

  typedef server-state {
    type enumeration {
      enum up {
        description
          "The server is active.";
      }
      enum down {
        description
          "The server is inactive.";
      }
    }
    description
      "The type of TACACS+ server state";
  }

  typedef server-type {
    type enumeration {
      enum authentication {
        description
          "The server is an authentication server.";
      }
      enum authorization {
        description
          "The server is an authorization server.";
      }
      enum accounting {
        description
          "The server is an accounting server.";
      }
    }
    description
      "The type of TACACS+ server";
  }

  feature tacacs {
    description
      "Indicates that the device can be configured as a
       TACACS+ client.";
  }

  grouping tacacs {
    container tacacs {
      if-feature "tacacs";
      description
        "Container for TACACS+ configurations and operations.";
      leaf enable {
        type boolean;
        default "false";
        description
          "Whether the TACACS+ server is enabled.";
      }
      container tacacs-servers {
        description
          "A set of TACACS+ servers.";
        leaf timeout {
          type uint32 {
            range "1..300";
          }
          default "5";
          description
            "Server response timeout period. The default timeout period
             is 5 seconds.";
        }
        leaf quiet-time {
          type uint32 {
            range "1..255";
          }
          default "5";
          description
            "Time period after which the primary server restores to
             active. The default time period is 5 minutes.";
        }
        leaf shared-key {
          type password-extend;
          description
            "Shared key for a TACACS+ server. Configuring a shared key
             improves the communication security between a router and
             TACACS+ server. By default, no shared key is configured.";
        }
        leaf source-ip {
          type inet:ip-address;
          description
            "Source IP address for a TACACS+ server.";
        }
        list tacacs-server {
          key "name";
          description
            "List for TACACS+ server.  ";
          leaf name {
            type string;
            description
              "Name of TACACS+ server";
          }
          leaf server-ip {
            type inet:ip-address;
            description
              "Server IP address. Must be a valid unicast IP address.";
          }
          leaf server-type {
            type server-type;
            description
              "Server type: authentication/authorization/accounting.";
          }
          leaf network-instance {
            type leafref {
              path "/ni:network-instances/ni:network-instance/ni:name";
            }
            description
              "Configure the vpn-instance name.";
          }
          leaf server-port {
            type uint32 {
              range "1..65535";
            }
            default "49";
            description
              "Server port. Value range: 1-65535. The default port
               number is 49.";
          }
          leaf single-connection {
            type boolean;
            default "false";
            description
              "Whether the single connection mode is enabled for the
               server. By default, the single connection mode is disabled.";
          }
          leaf server-state {
            type server-state;
            config false;
            description
              "Server running status.";
          }
          leaf current-srv {
            type boolean;
            default "false";
            config false;
            description
              "Whether the server is being used.";
          }
          leaf shared-key {
            type password-extend;
            description
              "Shared key for a TACACS+ server. Configuring a shared key
               improves the communication security between a router and
               TACACS+ server. By default, no shared key is configured.";
          }
          leaf authen-srv-connected-num {
            type uint32;
            config false;
            description
              "Number of times that the TACACS+ client successfully
               connected to the authentication server.";
          }
          leaf authen-srv-disconnected-num {
            type uint32;
            config false;
            description
              "Number of times that the TACACS+ client disconnected
               from the authentication server.";
          }
          leaf authen-reqs-num {
            type uint32;
            config false;
            description
              "Number of authentication requests. ";
          }
          leaf authen-rsps-num {
            type uint32;
            config false;
            description
              "Number of authentication responses.";
          }
          leaf authen-errors {
            type uint32;
            config false;
            description
              "Number of authentication errors.";
          }
          leaf author-srv-connected-num {
            type uint32;
            config false;
            description
              "Number of times that the TACACS+ client connected
               to the authorization server.";
          }
          leaf author-srv-disconnected-num {
            type uint32;
            config false;
            description
              "Number of times that the TACACS+ client disconnected
               from the authorization server.";
          }
          leaf author-reqs-num {
            type uint32;
            config false;
            description
              "Number of authorization requests. ";
          }
          leaf author-rsps-num {
            type uint32;
            config false;
            description
              "Number of authorization responses.";
          }
          leaf author-errors {
            type uint32;
            config false;
            description
              "Number of authorization errors.";
          }
          leaf acct-reqs-num {
            type uint32;
            config false;
            description
              "Number of accounting requests. ";
          }
          leaf acct-rsps-num {
            type uint32;
            config false;
            description
              "Number of accounting responses.";
          }
          leaf acct-srv-connected-num {
            type uint32;
            config false;
            description
              "Number of times that the TACACS+ client connected to
               the accounting server.";
          }
          leaf acct-srv-disconnected-num {
            type uint32;
            config false;
            description
              "Number of times that the TACACS+ client disconnected
               from the accounting server.";
          }
          leaf account-rsp-err {
            type uint32;
            config false;
            description
              "Number of abnormal accounting responses received from
               the server.";
          }
        }
      }
    }
    description
      "Grouping for tacacs";
  }

  augment "/sys:system" {
    uses tacacs;
    description
      "Augment the system module";
  }
  rpc rest-all-statistics {
    description
      "Reset All Statistics.";
  }
  rpc reset-authen-statistics {
    description
      "Reset authentication statistics of the TACACS+ server.";
  }
  rpc reset-author-statistics {
    description
      "Reset authorization statistics of the TACACS+ server.";
  }
  rpc reset-account-statistics {
    description
      "Reset accounting statistics of the TACACS+ server.";
  }
  rpc reset-common-statistics {
    description
      "Reset common statistics of the TACACS+ server.";
  }
}
