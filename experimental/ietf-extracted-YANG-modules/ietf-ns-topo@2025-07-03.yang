module ietf-ns-topo {
  yang-version 1.1;
  namespace
    "urn:ietf:params:xml:ns:yang:ietf-ns-topo";
  prefix "ns-topo";

  import ietf-network {
    prefix "nw";
    reference
     "RFC 8345: A YANG Data Model for Network Topologies";
  }
  import ietf-network-topology {
    prefix "nt";
    reference
     "RFC 8345: A YANG Data Model for Network Topologies";
  }

  import ietf-network-slice-service {
    prefix "ietf-nss";
    reference
      "draft-ietf-teas-ietf-network-slice-nbi-yang-25:
       A YANG Data Model for the RFC 9543 Network Slice Service";
  }

  organization
    "IETF TEAS Working Group";
  contact
    "WG Web: <http://tools.ietf.org/wg/teas/>
     WG List: <mailto:teas@ietf.org>

     Editor: Xufeng Liu
             <mailto:xufeng.liu.ietf@gmail.com>

     Editor: Italo Busi
             <mailto:italo.busi@huawei.com>

     Editor: Aihua Guo
             <mailto:aihuaguo.ietf@gmail.com>

     Editor: Sergio Belotti
             <mailto:sergio.belotti@nokia.com>

     Editor: Luis M. Contreras
             <mailto:luismiguel.contrerasmurillo@telefonica.com>";

  description
    "This module defines a base YANG data model for configuring
     customer intent topologies for RFC9543 network slices.

     The model fully conforms to the Network Management Datastore
     Architecture (NMDA).

     Copyright (c) 2023 IETF Trust and the persons
     identified as authors of the code.  All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX; see
     the RFC itself for full legal notices.";

  revision 2025-07-03 {
    description "Initial revision";
    reference
      "RFC XXXX: IETF Network Slice Topology YANG Data Model";
  }

  /*
   * Augmented data nodes
   */
  /* network type augments */
  augment "/nw:networks/nw:network/nw:network-types" {
    description
      "Defines the Network Slice topology type.";
    container network-slice {
      presence "Indicates a Network Slice topology";
      description
        "Its presence identifies the Network Slice type.";
    }
  }

  /* network topology augments */
  augment "/nw:networks/nw:network" {
    when "./nw:network-types/ns-topo:network-slice" {
      description
        "Augmentation parameters apply only for networks
         of type Network Slice topology.";
    }
    description
      "SLO and SLE for topology.";

    uses ietf-nss:service-slo-sle-policy;
  }

  /* network node augments */
  augment "/nw:networks/nw:network/nw:node" {
    when "../nw:network-types/ns-topo:network-slice" {
      description
        "Augmentation parameters apply only for networks
         of type Network Slice topology.";
    }
    description
      "SLO and SLE for nodes.";

    uses ietf-nss:service-slo-sle-policy;
  }

  /* network node's termination point augments */
  augment "/nw:networks/nw:network/nw:node" +
          "/nt:termination-point" {
    when "../../nw:network-types/ns-topo:network-slice" {
      description
        "Augmentation parameters apply only for networks
         of type Network Slice topology.";
    }
    description
      "SLO and SLE for termination points.";

  uses ietf-nss:service-slo-sle-policy;
  }

  /* network link augments */
  augment "/nw:networks/nw:network/nt:link" {
    when "../nw:network-types/ns-topo:network-slice" {
      description
        "Augmentation parameters apply only for networks
         of type Network Slice topology.";
    }
    description
      "SLO and SLE for links.";

    uses ietf-nss:service-slo-sle-policy;
  }
}
