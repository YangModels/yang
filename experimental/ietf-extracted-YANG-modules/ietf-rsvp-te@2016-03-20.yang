module ietf-rsvp-te {

  namespace "urn:ietf:params:xml:ns:yang:ietf-rsvp-te";

  prefix "rsvp-te";

  import ietf-rsvp {
    prefix rsvp;
  }

  import ietf-te {
    prefix ietf-te;
  }

  import ietf-inet-types {
    prefix inet;
  }

  /* Import TE generic types */
  import ietf-te-types {
    prefix ietf-te-types;
  }

  organization
    "IETF TEAS Working Group";

  contact "TBA";

  description
    "This module contains the RSVP YANG generic data model.";

  revision 2016-03-20 {
    description "Latest revision to RSVP-TE generic YANG module";
    reference "RFC3209";
  }

  /**
   * RSVP-TE LSPs groupings.
   */

  grouping lsp-record-route-information_state {
    description "recorded route information grouping";
    container record-route-object {
      description "RSVP recorded route object information";
      list path-record-route-subobjects {
        when "../origin-type != 'ingress'" {
          description "Applicable on non-ingress LSPs only";
        }
        key "subobject-index";
        description "";
        leaf subobject-index {
          type uint32;
          description "RRO subobject index";
        }
        uses ietf-te-types:record-route-subobject;
      }
      list resv-record-route-subobjects {
        when "../origin-type != 'egress'" {
          description "Applicable on non-egress LSPs only";
        }
        key "subobject-index";
        description "";
        leaf subobject-index {
          type uint32;
          description "RRO subobject index";
        }
        uses ietf-te-types:record-route-subobject;
      }
    }
  }

  grouping lsp-explicit-route-information_state {
    description "RSVP-TE LSP explicit-route information";
    container explicit-route-object {
      description "Explicit route object information";
      list incoming-explicit-route-subobjects {
        when "../origin-type != 'ingress'" {
          description "Applicable on non-ingress LSPs only";
        }
        key "subobject-index";
        description "";
        leaf subobject-index {
          type uint32;
          description "ERO subobject index";
        }
        uses ietf-te-types:explicit-route-subobject;
      }
      list outgoing-explicit-route-subobjects {
        when "../origin-type != 'egress'" {
          description "Applicable on non-egress LSPs only";
        }
        key "subobject-index";
        description "";
        leaf subobject-index {
          type uint32;
          description "ERO subobject index";
        }
        uses ietf-te-types:explicit-route-subobject;
      }
    }
  }

  grouping lsp-attributes-flags_config {
    description
      "Configuration parameters relating to RSVP-TE LSP
      attribute flags";
    leaf lsp-rerouting {
      type enumeration {
        enum end-to-end-routing {
          description
            "End-to-end routing desired";
          reference "RFC4920, RFC5420";
        }
        enum boundary-rerouting {
          description
            "Boundary rerouting desired";
          reference "RFC4920, RFC5420";
        }
        enum segment-based-rerouting {
          description
            "Segment-based rerouting desired";
          reference "RFC4920, RFC5420";
        }
      }
      description "LSP rerouting types";
    }
    leaf lsp-integrety-required {
      type empty;
      description "LSP integrity desired";
      reference "RFC4875";
    }
    leaf lsp-contiguous {
      type empty;
      description "Contiguous LSP";
      reference "RFC5151";
    }
    leaf lsp-stitching-desired {
      type empty;
      description "Stitched LSP";
      reference "RFC5150";
    }
    leaf lsp-preplanned {
      type empty;
      description "Preplanned LSP";
      reference "RFC6001";
    }
    leaf lsp-oob-mapping {
      type empty;
      description
        "Mapping is done out-of-band";
      reference "RFC6511";
    }
  }

  grouping lsp-session-attributes-obj-flags_config {
    description
      "Configuration parameters relating to RSVP-TE LSP
      session attribute flags";
    reference
      "RFC4859: Registry for RSVP-TE Session Flags";
    leaf local-recording-desired {
      type empty;
      description "Path recording is desired.";
      reference "RFC3209";
    }
    leaf se-style-desired {
      type empty;
      description "SE Style desired";
      reference "RFC3209";
    }
    leaf path-reevaluation-request {
      type empty;
      description "Path re-evaluation request";
      reference "RFC4736";
    }
    leaf soft-preemption-desired {
      type empty;
      description "Soft-preemption is desired";
      reference "RFC5712";
    }
  }

  grouping lsp-properties_config {
    description
      "Configuration parameters relating to RSVP-TE LSP
      session attribute flags";
    leaf lsp-source {
      type inet:ip-address;
      description
        "LSP source address.";
    }
    leaf lsp-signaled-name {
      type string;
      description
        "Sets the session name to use in the session
        attribute object.";
    }
    leaf lsp-priority-setup {
      type uint8 {
        range "0..7";
      }
      description
        "RSVP session attributes setup priority";
    }
    leaf lsp-priority-hold {
      type uint8 {
        range "0..7";
      }
      description
        "RSVP session attributes hold priority";
    }
    uses lsp-session-attributes-obj-flags_config;
    uses lsp-attributes-flags_config;
  }

  grouping tunnel-properties {
    description
      "Top level grouping for LSP properties.";
    container config {
      description
        "Configuration parameters relating to
        LSP properties";
      uses lsp-properties_config;
    }
    container state {
      config false;
      description
        "State information associated with LSP
        properties";
      uses lsp-properties_config;
    }
  }
  /*** End of RSVP-TE LSP groupings ***/

  /**
   * RSVP-TE generic global properties.
   */

  grouping global-soft-preemption_config {
    description
      "Configuration for global RSVP-TE soft preemption";
    leaf soft-preemption-timeout {
      type uint16 {
        range 0..300;
      }
      default 0;
      description
        "Timeout value for soft preemption to revert
        to hard preemption";
    }
  }

  grouping global-soft-preemption {
    description
      "Top level group for RSVP-TE soft-preemption";
    container global-soft-preemption {
      presence "Enables soft preemption on a node.";
      description
        "Top level container for RSVP-TE soft-preemption";
      container config {
        description
          "Configuration parameters relating to RSVP
          soft preemption support";
        uses global-soft-preemption_config;
      }
      container state {
        description "State parameters relating to RSVP
          soft preemption support";
        uses global-soft-preemption_config;
      }
    }
  }
  /*** End of RSVP-TE generic global properties. ***/

  /**
   * RSVP-TE interface generic groupings.
   */

  grouping rsvp-te-interface-attributes {
    description
      "Top level grouping for RSVP-TE interface properties.";
    container rsvp-te-interface-attributes {
      description
        "Top level container for RSVP-TE interface
        properties";
      container config {
        description
          "Configuration parameters relating to RSVP-TE
          bandwidth";
      }
      container state {
        config false;
        description
          "State information associated with RSVP-TE
          bandwidth";
      }
    }
  }
  /*** End of RSVP-TE generic groupings ***/

  /* RSVP-TE global propeerties */
  augment "/rsvp:rsvp/rsvp:globals" {
    description
      "RSVP-TE augmentation to RSVP globals";
  }

  /* Linkage to the base RSVP all links */
  augment "/rsvp:rsvp/rsvp:interfaces" {
    description
      "RSVP-TE generic data augmentation pertaining to interfaces";
    /* To be added */
  }

  /* Linkage to per RSVP interface */
  augment "/rsvp:rsvp/rsvp:interfaces/rsvp:interface" {
    description
      "RSVP-TE generic data augmentation pertaining to specific
       interface";
    /* To be added */
  }

  /* add augmentation for sessions neighbors */
  augment "/rsvp:rsvp/rsvp:sessions" {
    description
      "RSVP-TE generic data augmentation pertaining to session";
    /* To be added */
  }

  augment "/rsvp:rsvp/rsvp:neighbors" {
    description
      "RSVP-TE generic data augmentation pertaining to neighbors";
    /* To be added */
  }

  /**
   * RSVP-TE generic augmentations of generic TE model.
   */

  augment "/ietf-te:te/ietf-te:tunnels/ietf-te:tunnel" {
    description
      "RSVP-TE generic data augmentation pertaining to TE tunnels";
    uses tunnel-properties;
  }

  augment "/ietf-te:te/ietf-te:interfaces/ietf-te:interface" {
    description
      "RSVP-TE generic data augmentation pertaining to specific TE
       interface";
  }

  augment "/ietf-te:te/ietf-te:lsps-state/ietf-te:lsp" {
    description
      "RSVP-TE generic data augmentation pertaining to specific TE
       LSP";
    uses lsp-properties_config;
    uses lsp-explicit-route-information_state;
    uses lsp-record-route-information_state;
  }
}
