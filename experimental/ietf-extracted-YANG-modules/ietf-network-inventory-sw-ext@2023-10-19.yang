module ietf-network-inventory-sw-ext {
  yang-version 1.1;
  namespace "urn:ietf:params:xml:ns:yang:ietf-network-inventory-sw-ext";
  prefix nis;

  import ietf-network-inventory {
    prefix ni;
    reference
      "RFCxxxx: IETF Network Inventory";
  }

  organization
    "IETF Network Inventory YANG (ivy) Working Group";
  contact
    "WG Web:   <https://datatracker.ietf.org/wg/ivy>
     WG List:  <mailto:inventory-yang@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module defines a model for network inventory software
     extensions.

     Copyright (c) 2023 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2023-10-19 {
    description
      "Initial version";
    reference
      "RFC XXXX: A YANG Data Model for Network Inventory Software
                 Extensions.";
  }

  identity ne-virtual {
    base ni:ne-type;
    description
      "A virtual network element (NE). ";
  }

  identity software-component {
    base ni:non-hardware-component;
    description
      "Base identity for software components in a managed
       device.";
  }

  identity operating-system {
    base software-component;
    description
      "OS software type.";
  }

  identity operating-system-patch {
    base software-component;
    description
      "An operating system update - which should be a subcomponent
       of the `operating-system` running on a component. A patch is
       defined to be a set of software changes that are atomically
       installed (and uninstalled) together. ";
  }
  identity bios {
    base software-component;
    description
      "Legacy BIOS or UEFI firmware interface responsible for
       initializing hardware components and first stage boot
       loader.";
  }

  identity boot-loader {
    base software-component;
    description
      "Software layer responsible for loading and booting the
       device OS or network OS.";
  }

  identity software-module {
    base software-component;
    description
      "A base identity for software modules installed and/or
       running on the device.  Modules include user-space programs
       and kernel modules that provide specific functionality.
       A component with type SOFTWARE_MODULE should also have a
       module type that indicates the specific type of software
       module";
  }

  grouping software-module-specific-info-grouping {
    //To be enriched in the future.
    description
      "Specific attributes applicable to Software Modules only.";
  }

  /* Main blocks */

  augment "/ni:network-elements/ni:network-element" {
    description
      "Augment network element (NE) attributes.";
    container virtual-ne-attributes {
      when "derived-from-or-self(../ni:ne-type,'ne-virtual')";
      description
        "Container for the attributes applicable only to virtual
         Network Elements (NEs).";
      //To be enriched in the future.
    }
  }

  augment "/ni:network-elements/ni:network-element/ni:components/"
        + "ni:component" {
    description
      "Augment component attributes.";
    container software-module-specific-info {
      when "derived-from-or-self(../ni:class,'software-module')";
      description
        "This container contains some attributes belong to
         Software Modules only.";
      uses software-module-specific-info-grouping;
    }
  }
}
