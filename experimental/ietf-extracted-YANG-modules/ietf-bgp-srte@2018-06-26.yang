module ietf-bgp-srte {

  namespace "urn:ietf:params:xml:ns:yang:ietf-bgp-srte";

  prefix "ietf-bgp-srte";

  import ietf-routing-types {
    prefix rt-types;
  }

  import ietf-routing {
    prefix "rt";
  }

  import ietf-inet-types {
    prefix inet;
  }

  import ietf-bgp {
    prefix bgp;
  }

  import ietf-bgp-types {
    prefix bgp-types;
  }

  import ietf-srv6-types {
    prefix srv6-types;
  }

  organization
     "IETF Inter-Domain Routing Working Group";

  contact
     "Inter-Domain working group - idr@ietf.org";

  description
    "This YANG module defines a data model to configure and
     manage segment routing extensions in BGP.

     Terms and Acronyms

     AF : Address Family
     BGP (bgp) : Border Gateway Protocol

     SR : Segment Routing

     SID : Segment Identifier

     SRv6 : Segment Routing with IPv6 Data plane

     VPN : Virtual Private Network

     VRF : Virtual Routing and Forwarding

    ";

  revision 2018-06-26 {
    description
      "Initial revision" ;
    reference "";
  }

  //
  // New identities and typedefs for SR extensions
  //

  // SR Policy SAFI identities
  identity IPV4_SRPOLICY {
    base bgp-types:afi-safi-type;
    description
     "IPv4 SR Policy (AFI,SAFI = 1,73)";
    reference "TBD";
  }

  identity IPV6_SRPOLICY {
    base bgp-types:afi-safi-type;
    description
      "IPv6 SR Policy (AFI,SAFI = 2,73)";
    reference "TBD";
  }

  typedef segment-type {
    type enumeration {
      enum segment-type-1 {
        value 1;
        description "SR-MPLS Label";
      }
      enum segment-type-2 {
        value 2;
        description "SRv6 SID";
      }
      enum segment-type-3 {
        value 3;
        description "IPv4 Prefix with optional SR Algorithm";
      }
      enum segment-type-4 {
        value 4;
        description "IPv6 Global Prefix with optional SR Algorithm for SR-MPLS";
      }
      enum segment-type-5 {
        value 5;
        description "IPv4 Prefix with Local Interface ID";
      }
      enum segment-type-6 {
        value 6;
        description "IPv4 Addresses for link endpoints as Local, Remote pair";
      }
      enum segment-type-7 {
        value 7;
        description "IPv6 Prefix and Interface ID for link endpoints as Local,
           Remote pair for SR-MPLS";
      }
      enum segment-type-8 {
        value 8;
        description "IPv6 Addresses for link endpoints as Local, Remote pair for
           SR-MPLS";
      }
      enum segment-type-9 {
        value 9;
        description "IPv6 Global Prefix with optional SR Algorithm for SRv6";
      }
      enum segment-type-10 {
        value 10;
        description "IPv6 Prefix and Interface ID for link endpoints as Local,
           Remote pair for SRv6";
      }
      enum segment-type-11 {
        value 11;
        description "IPv6 Addresses for link endpoints as Local, Remote pair for
           SRv6";
      }
    }
    description "SR segment type";
  }

  // Sid type union
  typedef sid-type {
    type union {
      type rt-types:mpls-label;
      type srv6-types:srv6-sid;
    }
    description "Type definition for Segment Identifier. This is
                 a union type which can be either a SR MPLS SID in the
                 form of a label,  or a SRv6 SID in the form of
                 an IPv6 address.";
    reference "TBD";
  }

  //
  // SR Policy Related Groupings
  //
  //Color and Endpoint of the SR Policy
  grouping sr-policy-color-endpoint {
    description "Common grouping for SR Policy Color and
                 Endpoint";
    leaf color {
      type uint32;
      description "Color of the policy";
    }

    leaf end-point {
      type inet:ip-address;
      description "Endpoint of the policy";
    }
  }
  // Authorized colors for On Demand SR Policy programming
  grouping sr-odn-auth-colors {
    description
      "Authorized colors for On Demand (dynamic) SR Policies
       towards BGP nexthops";
    container authorized-colors {
      config false;
      description
        "Authorized colors for On Demand (dynamic) SR policies
         towards BGP nexthops";
      list colors {
        key "color";
        description "List of SR Policy Colors";
        leaf color {
          type uint32;
          description "Color value";
        }
      }
    }
  }

  grouping sr-policy-cmn-state {
    description "Common state parameters applicable to
                 SR Policies";
    leaf policy-state {
      type enumeration {
        enum UP {
          description "SR Policy state UP";
        }
        enum DOWN {
          description "SR Policy state DOWN";
        }
      }
      description "SR Policy forwarding state";
    }

    leaf binding-sid {
      type sid-type;
      description "Binding SID of the SR Policy";
    }

    leaf steering-disabled {
      type empty;
      description "This attribute is set if steering
                   is disabled on this SR policy";
    }

    leaf ref-count {
      type uint32;
      description "Count of routes steering over this policy";
    }
  }

  //
  // SR Policy State grouping
  //
  grouping sr-policy-state {
    description "SR Policy State";
    container policy-state {
      config false;
      description "SR Policy State";
      list sr-policy {
        key "color end-point";
        description "List of SR Policies";

        uses sr-policy-color-endpoint;

        // State of the SR Policy in BGP
        uses sr-policy-cmn-state;
      }
    }
  }

  grouping sr-exp-policy-cp-state {
    description "State of BGP signaled SR Policy (explicit)
                 candidate paths";
    container explicit-policies {
      config false;
      description "BGP signaled explicit SR Policies";
      list sr-policy {
        key "distinguisher color end-point";
        description "List of BGP signaled explicit SR Policies";
        leaf distinguisher {
          type uint32;
          description "Distinguisher of the SR Policy
                       candidate path";
        }

        uses sr-policy-color-endpoint;

        leaf preference {
          type uint32;
          description "Preference of the SR Policy candidate path";
        }

        container explicit-binding-sid {
          description "Explicitly supplied Binding SID
                       for this policy";
          leaf binding-sid {
            type sid-type;
            description "Binding SID value";
          }
          leaf strict {
            type boolean;
            description "Boolean indicating that the node
                         must use only the supplied Binding SID
                         for this SR Policy.
                         reference: TBD";
          }
          leaf drop-on-invalid {
            type boolean;
            description "Boolean to indicate drop upon invalid
                         policy, behavior. This overwrites the
                         default behavior of fallback to IGP path
                         , when SR Policy is (or becomes) invalid.
                         reference: TBD";
          }
        }

        leaf usable {
          type boolean;
          description "Boolean to indicate that the SR Policy is
                       usable on this node.
                       reference: TBD";
        }

        leaf registered {
          type boolean;
          description "Boolean to indicate that the SR policy
                       is registered with policy manager to
                       install the corresponding forwarding entry";

        }

        uses segment-lists;
        // TODO: Segment Lists and other parameters from SR Policy model
        //       to be imported here.
      }
    }
  }

  grouping segment-lists {
    description
      "Segment lists grouping";
    container segment-lists {
      description "Segment-lists properties";

      list segment-list {
        key "weight";
        description "Segment-list";
        leaf weight {
          type uint32;
          description "Segment-list weight";
        }
        container segments {
          description
            "Segments for given segment list";

          list segment {
            key "index";
            description "Segment/hop at the index";
            uses segment-properties;
          }
        }
      }
    }
  }

  grouping segment-properties {
    description "Segment properties grouping";
    leaf index {
      type uint32;
      description "Segment index";
    }
    leaf type {
      type segment-type;
      description "Segment type";
    }
    container segment-types {
      description "Types of segments";
      container segment-type-1 {
        description
           "Segment declared by MPLS label";
        leaf sid-value {
           type rt-types:mpls-label;
           description "MPLS label value";
        }
      }
      container segment-type-2 {
        description
           "Segment declared by SRv6 SID value";
        leaf sid-value {
           type srv6-types:srv6-sid;
           description "SRv6 SID value";
        }
      }
      container segment-type-3 {
        description
           "Segment declared by IPv4 Prefix with optional SR Algorithm";
        leaf ipv4-address {
          type inet:ipv4-address;
          description "Segment IPv4 address";
        }
        leaf algorithm {
          type uint8;
          description "Prefix SID algorithm identifier";
        }
      }
      container segment-type-4 {
        description
           "Segment declared by IPv6 Global Prefix with optional
            SR Algorithm for SR-MPLS";
        leaf ipv6-address {
          type inet:ipv6-address;
          description "Segment IPv6 address";
        }
        leaf algorithm {
          type uint8;
          description "Prefix SID algorithm identifier";
        }
      }
      container segment-type-5 {
        description
           "Segment declared by IPv4 Prefix with Local Interface ID";
        leaf ipv4-address {
          type inet:ipv4-address;
          description "Node IPv4 address";
        }
        leaf interface-identifier {
          type uint32;
          description "local interface identifier";
        }
      }
      container segment-type-6 {
        description
           "Segment declared by IPv4 Addresses for link endpoints
            as Local, Remote pair";
        leaf local-ipv4-address {
          type inet:ipv4-address;
          description "Segment local IPv4 adjacency address";
        }
        leaf remote-ipv4-address {
          type inet:ipv4-address;
          description "Segment remote IPv4 adjacency address";
        }
      }
      container segment-type-7 {
        description
           "Segment declared by IPv6 Prefix and Interface ID for
           link endpoints as Local, Remote pair for SR-MPLS";
        leaf local-ipv6-address {
          type inet:ipv6-address;
          description "Local link IPv6 address";
        }
        leaf local-interface-identifier {
          type uint32;
          description "Local interface identifier";
        }
        leaf remote-ipv6-address {
          type inet:ipv6-address;
          description "Remote link IPv6 address";
        }
        leaf remote-interface-identifier {
          type uint32;
          description "Remote interface identifier";
        }
      }
      container segment-type-8 {
        description
           "Segment declared by IPv6 Addresses for link endpoints as
           Local, Remote pair for SR-MPLS";
        leaf local-ipv6-address {
          type inet:ipv6-address;
          description "Segment local IPv6 adjacency address";
        }
        leaf remote-ipv6-address {
          type inet:ipv6-address;
          description "Segment remote IPv6 adjacency address";
        }
      }
      container segment-type-9 {
        description
          "Segment declared by IPv6 Global Prefix with optional
           SR Algorithm for SRv6";
        leaf ipv6-address {
          type inet:ipv6-address;
          description "Segment IPv6 prefix";
        }
        leaf algorithm {
          type uint8;
          description "Prefix SID algorithm identifier";
        }
      }
      container segment-type-10 {
        description
           "Segment declared by IPv6 Prefix and Interface ID for
           link endpoints as Local, Remote pair for SRv6";
        leaf local-ipv6-address {
          type inet:ipv6-address;
          description "Local link IPv6 address";
        }
        leaf local-interface-identifier {
          type uint32;
          description "Local interface identifier";
        }
        leaf remote-ipv6-address {
          type inet:ipv6-address;
          description "Remote link IPv6 address";
        }
        leaf remote-interface-identifier {
          type uint32;
          description "Remote interface identifier";
        }
      }
      container segment-type-11 {
        description
           "Segment declared by IPv6 Addresses for link endpoints as
            Local, Remote pair for SRv6";
          leaf local-ipv6-address {
            type inet:ipv6-address;
            description "Segment local IPv6 adjacency address";
          }
          leaf remote-ipv6-address {
            type inet:ipv6-address;
            description "Segment remote IPv6 adjacency address";
          }
      }
    }
  }
  grouping sr-odn-policies {
    description "SR On Demand (dynamic) SR Policies";
    container installed-policies {
      config false;
      description "BGP triggered On Demand (dynamic) SR Policies
                   corresponding to the BGP nexthops";
      list sr-policy {
        key "color end-point";
        description "SR Policy list";
        uses sr-policy-color-endpoint;
      }
    }
  }

  grouping sr-policy-steering-state {
    description "Per route Automatic Steering parameters";
    container automatic-steering {
      description "Per route Automatic Steering parameters";
      leaf color {
        type leafref {
          path "/rt:routing/rt:control-plane-protocols/rt:control-plane-protocol/" +
               "bgp:bgp/bgp:global/ietf-bgp-srte:segment-routing/" +
               "ietf-bgp-srte:policy-state/ietf-bgp-srte:sr-policy/" +
               "ietf-bgp-srte:color";
        }
        description "Color of the SR Policy being used for
                     Automatic Steering";
      }
      leaf end-point {
        type leafref {
          path "/rt:routing/rt:control-plane-protocols/rt:control-plane-protocol/" +
               "bgp:bgp/bgp:global/ietf-bgp-srte:segment-routing/" +
               "ietf-bgp-srte:policy-state/ietf-bgp-srte:sr-policy/" +
               "ietf-bgp-srte:end-point";
        }
        description "End-point of the SR Policy being used
                     for Automatic Steering";
      }
      leaf co-flag {
        type enumeration {
          enum 00 {
            description "Color-Only flag 00";
          }
          enum 01 {
            description "Color-Only flag 01";
          }
          enum 10 {
            description "Color-Only flag 10";
          }
        }
        default "00";
        description "Color-Only (CO) flags applicable for
                     Automatic Steering of this route";
      }
      leaf binding-sid {
        type leafref {
          path "/rt:routing/rt:control-plane-protocols/rt:control-plane-protocol/" +
               "bgp:bgp/bgp:global/ietf-bgp-srte:segment-routing/" +
               "ietf-bgp-srte:policy-state/ietf-bgp-srte:sr-policy/" +
               "ietf-bgp-srte:binding-sid";
        }
        description "Binding SID of the SR Policy";
      }
    }
  }

  grouping route-key-leafs {
    description "Grouping for key leafs identifying a route";
    leaf prefix {
      type union {
         type inet:ip-prefix;
         type string;
      }
      description "BGP Prefix. This is a temp definition to
                  cover ip-prefix and other NLRI formats.
                  Import the type once defined in base
                  BGP RIB model";
    }
    leaf neighbor {
      type inet:ip-address;
      description "BGP Neighbor";
    }
    leaf add-path-id {
      type uint32;
      description "Add-path ID";
    }
  }

  grouping common-bgp-route-grouping {
    description "BGP route list" ;
    container routes {
      config false;
      description "BGP Route in local RIB";
      list route {
        key "prefix neighbor add-path-id";
        description "BGP route list";
        uses route-key-leafs;
      }
    }
  }

  grouping common-bgp-vpn-route-grouping {
    description "BGP route list" ;
    container routes {
      config false;
      description "BGP VPN Route in local RIB";
      list route {
        key "rd prefix neighbor add-path-id";
        description "Route List";

        leaf rd {
          type rt-types:route-distinguisher;
          description "Route Distinguisher";
        }
        uses route-key-leafs;
      }
    }
  }

  //
  // BGP Specific Paramters
  //
  // Augment AF with route list
  augment "/rt:routing/rt:control-plane-protocols/rt:control-plane-protocol/" +
          "bgp:bgp/bgp:global/bgp:afi-safis/bgp:afi-safi/bgp:ipv4-unicast" {
    description
      "Augment BGP SAFI route";
    uses common-bgp-route-grouping;
  }
  augment "/rt:routing/rt:control-plane-protocols/rt:control-plane-protocol/" +
          "bgp:bgp/bgp:global/bgp:afi-safis/bgp:afi-safi/bgp:ipv6-unicast" {
    description
      "Augment BGP SAFI route";
    uses common-bgp-route-grouping;
  }
  augment "/rt:routing/rt:control-plane-protocols/rt:control-plane-protocol/" +
          "bgp:bgp/bgp:global/bgp:afi-safis/bgp:afi-safi/bgp:ipv4-labeled-unicast" {
    description
      "Augment BGP SAFI route";
    uses common-bgp-route-grouping;

  }
  augment "/rt:routing/rt:control-plane-protocols/rt:control-plane-protocol/" +
          "bgp:bgp/bgp:global/bgp:afi-safis/bgp:afi-safi/bgp:ipv6-labeled-unicast" {
    description
      "Augment BGP SAFI route";
    uses common-bgp-route-grouping;
  }
  augment "/rt:routing/rt:control-plane-protocols/rt:control-plane-protocol/" +
          "bgp:bgp/bgp:global/bgp:afi-safis/bgp:afi-safi/bgp:l3vpn-ipv4-unicast" {
    description
      "Augment BGP SAFI route";
    uses common-bgp-vpn-route-grouping;
  }
  augment "/rt:routing/rt:control-plane-protocols/rt:control-plane-protocol/" +
          "bgp:bgp/bgp:global/bgp:afi-safis/bgp:afi-safi/bgp:l3vpn-ipv6-unicast" {
    description
      "Augment BGP SAFI route";
    uses common-bgp-vpn-route-grouping;
  }

  // SR Policy Related
  // On Demand authorized colors table
  // SR Policy state data
  augment "/rt:routing/rt:control-plane-protocols/rt:control-plane-protocol/" +
          "bgp:bgp/bgp:global" {
    description
      "Segment Routing parameters in BGP global model";
    container segment-routing {
      description "Segment Routing parameters";
      container on-demand-policies {
        description
          "Segment Routing On Demand Nexthop
           (ODN) SR Policies";
        uses sr-odn-auth-colors;
        uses sr-odn-policies;
      }
      uses sr-policy-state;
    }
  }

  // Steering state in overlay BGP routes
  augment "/rt:routing/rt:control-plane-protocols/rt:control-plane-protocol/" +
          "bgp:bgp/bgp:global/bgp:afi-safis/" +
          "bgp:afi-safi/bgp:ipv4-unicast/ietf-bgp-srte:routes/ietf-bgp-srte:route" {
    description
      "Augment BGP SAFI route with steering info";
    uses sr-policy-steering-state;
  }
  augment "/rt:routing/rt:control-plane-protocols/rt:control-plane-protocol/" +
          "bgp:bgp/bgp:global/bgp:afi-safis/" +
          "bgp:afi-safi/bgp:ipv6-unicast/ietf-bgp-srte:routes/ietf-bgp-srte:route" {
    description
      "Augment BGP SAFI route with steering info";
    uses sr-policy-steering-state;
  }
  augment "/rt:routing/rt:control-plane-protocols/rt:control-plane-protocol/" +
          "bgp:bgp/bgp:global/bgp:afi-safis/" +
          "bgp:afi-safi/bgp:ipv4-labeled-unicast/ietf-bgp-srte:routes/ietf-bgp-srte:route" {
    description
      "Augment BGP SAFI route with steering info";
    uses sr-policy-steering-state;
  }
  augment "/rt:routing/rt:control-plane-protocols/rt:control-plane-protocol/" +
          "bgp:bgp/bgp:global/bgp:afi-safis/" +
          "bgp:afi-safi/bgp:ipv6-labeled-unicast/ietf-bgp-srte:routes/ietf-bgp-srte:route" {
    description
      "Augment BGP SAFI route with steering info";
    uses sr-policy-steering-state;
  }
  augment "/rt:routing/rt:control-plane-protocols/rt:control-plane-protocol/" +
          "bgp:bgp/bgp:global/bgp:afi-safis/" +
          "bgp:afi-safi/bgp:l3vpn-ipv4-unicast/ietf-bgp-srte:routes/ietf-bgp-srte:route" {
    description
      "Augment BGP SAFI route with steering info";
    uses sr-policy-steering-state;
  }
  augment "/rt:routing/rt:control-plane-protocols/rt:control-plane-protocol/" +
          "bgp:bgp/bgp:global/bgp:afi-safis/" +
          "bgp:afi-safi/bgp:l3vpn-ipv6-unicast/ietf-bgp-srte:routes/ietf-bgp-srte:route" {
    description
      "Augment BGP SAFI route with steering info";
    uses sr-policy-steering-state;
  }

  // BGP Signaled SR Policy explicit candidate paths state
  augment "/rt:routing/rt:control-plane-protocols/rt:control-plane-protocol/" +
          "bgp:bgp/bgp:global/bgp:afi-safis/bgp:afi-safi" {
    description "Augment IPv4 SR Policy SAFI list entry";
    container ipv4-srpolicy {
      when "/rt:routing/rt:control-plane-protocols/rt:control-plane-protocol/" +
          "bgp:bgp/bgp:global/bgp:afi-safis/bgp:afi-safi/" +
          "bgp:afi-safi-name  = 'bgp-types:IPV4_SRPOLICY'" {
       description
         "Include this container for IPv4 SR Policy specific
          configuration";
      }
      description "IPv4 SR Policy specific parameters";
      uses sr-exp-policy-cp-state;
    }
  }

  augment "/rt:routing/rt:control-plane-protocols/rt:control-plane-protocol/" +
          "bgp:bgp/bgp:global/bgp:afi-safis/bgp:afi-safi" {
    description "Augment IPv6 SR Policy SAFI list entry";
    container ipv6-srpolicy {
      when "/rt:routing/rt:control-plane-protocols/rt:control-plane-protocol/" +
          "bgp:bgp/bgp:global/bgp:afi-safis/bgp:afi-safi/" +
          "bgp:afi-safi-name  = 'bgp-types:IPV6_SRPOLICY'" {
        description
          "Include this container for IPv6 SR Policy specific
           configuration";
      }
      description "IPv6 SR Policy specific parameters";
      uses sr-exp-policy-cp-state;
    }
  }
}
