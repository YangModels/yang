module ietf-otn-tunnel {
    yang-version 1.1;

    namespace "urn:ietf:params:xml:ns:yang:ietf-otn-tunnel";
    prefix "otn-tunnel";

    import ietf-te { prefix "te"; }
    import ietf-transport-types { prefix "tran-types"; }
    //import yang-ext { prefix ext; revision-date 2013-07-09; }
    organization
        "IETF CCAMP Working Group";

    contact
        "WG Web: <http://tools.ietf.org/wg/ccamp/>
        WG List: <mailto:ccamp@ietf.org>

        Editor: Haomian Zheng
                <mailto:zhenghaomian@huawei.com>

        Editor: Zheyu Fan
                <mailto:fanzheyu2@huawei.com>

        Editor: Anurag Sharma
                <mailto:ansha@google.com>

        Editor: Rajan Rao
                <mailto:rrao@infinera.com>

        Editor: Sergio Belotti
                <mailto:sergio.belotti@nokia.com>

        Editor: Victor Lopez
                <mailto:victor.lopezalvarez@telefonica.com>

        Editor: Yunbo Li
                <mailto:liyunbo@chinamobile.com>";

    description
        "This module defines a model for OTN Tunnel Services.";

    revision "2017-05-25" {
        description
            "Revision 0.3";
        reference
            "draft-sharma-ccamp-otn-tunnel-model-02.txt";
    }

    grouping otn-tunnel-endpoint {
        description "Parameters for OTN tunnel.";

        leaf payload-treatment {
            type enumeration {
                enum switching;
                enum transport;
            }
            default switching;
            description
                "Treatment of the incoming payload. Payload can
                either be switched, or transported as is.";
        }

        leaf src-client-signal {
                type identityref {
                        base tran-types:client-signal;
                }
                description
                        "Client signal at the source endpoint of
                        the tunnel.";
        }

        leaf src-tpn {
            type uint16 {
                range "0..4095";
            }
            description
                "Tributary Port Number. Applicable in case of mux
                 services.";
            reference
                "RFC7139: GMPLS Signaling Extensions for Control of
                 Evolving G.709 Optical Transport Networks.";
        }

        leaf src-tsg {
            type identityref {
                base tran-types:tributary-slot-granularity;
            }
            description
                "Tributary slot granularity. Applicable in case of
                 mux services.";
            reference
                "G.709/Y.1331, February 2016: Interfaces for the
                Optical Transport Network (OTN)";
        }

        leaf src-tributary-slot-count {
                type uint16;
                description
                    "Number of tributary slots used at the source.";
        }

        container src-tributary-slots {
            description
                "A list of tributary slots used by the client
                service. Applicable in case of mux services.";
            leaf-list values {
                type uint8;
                description
                        "Tributary tributary slot value.";
                reference
                    "G.709/Y.1331, February 2016: Interfaces for the
                        Optical Transport Network (OTN)";
            }
        }

        leaf dst-client-signal {
            type identityref {
                base tran-types:client-signal;
            }
            description
                "Client signal at the destination endpoint of
                 the tunnel.";
        }

        leaf dst-tpn {
            type uint16 {
                range "0..4095";
            }
            description
                "Tributary Port Number. Applicable in case of mux
                services.";
            reference
                "RFC7139: GMPLS Signaling Extensions for Control of
                Evolving G.709 Optical Transport Networks.";
        }

        leaf dst-tsg {
            type identityref {
                base tran-types:tributary-slot-granularity;
            }
            description
                "Tributary slot granularity. Applicable in case of
                 mux services.";
            reference
                "G.709/Y.1331, February 2016: Interfaces for the
                 Optical Transport Network (OTN)";
        }

        leaf dst-tributary-slot-count {
            type uint16;
            description
                "Number of tributary slots used at the destination.";
        }

        container dst-tributary-slots {
            description
                "A list of tributary slots used by the client
                service. Applicable in case of mux services.";
            leaf-list values {
                type uint8;
                description
                        "Tributary slot value.";
                reference
                    "G.709/Y.1331, February 2016: Interfaces for the
                        Optical Transport Network (OTN)";
            }
        }
    }

    /*
    Note: Comment has been given to authors of TE Tunnel model to add
    tunnel-types to the model in order to identify the technology
    type of the service.

    grouping otn-service-type {
        description
          "Identifies the OTN Service type.";
        container otn-service {
          presence "Indicates OTN Service.";
          description
            "Its presence identifies the OTN Service type.";
        }
      } // otn-service-type

    augment "/te:te/te:tunnels/te:tunnel/te:tunnel-types" {
        description
                "Introduce OTN service type for tunnel.";
        ext:augment-identifier otn-service-type-augment;
        uses otn-service-type;
    }
    */

    /*
    Note: Comment has been given to authors of TE Tunnel model to add
    list of endpoints under config to support P2MP tunnel.
    */
    augment "/te:te/te:tunnels/te:tunnel/te:config" {
        description
                "Augment with additional parameters required for OTN
                service.";
        //ext:augment-identifier otn-tunnel-endpoint-config-augment;
        uses otn-tunnel-endpoint;
    }

    augment "/te:te/te:tunnels/te:tunnel/te:state" {
        description
                "Augment with additional parameters required for OTN
                service.";
        //ext:augment-identifier otn-tunnel-endpoint-state-augment;
        uses otn-tunnel-endpoint;
    }

    /*
    Note: Comment has been given to authors of TE Tunnel model to
    add tunnel-lifecycle-event to the model. This notification is
    reported for all lifecycle changes (create, delete, and update)
    to the tunnel or lsp.
    augment "/te:tunnel-lifecycle-event" {
        description
          "OTN service event";
        uses otn-service-type;
        uses otn-tunnel-params;

        list endpoint {
          key
            "endpoint-address tp-id";
          description
            "List of Tunnel Endpoints.";
          uses te:tunnel-endpoint;
          uses otn-tunnel-params;
        }
      }
    */
}
