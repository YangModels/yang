module ietf-system-dns-resolver {
  yang-version "1";

  namespace "urn:ietf:params:xml:ns:yang:ietf-system:dns-resolver";
  prefix "dnsres";

  import ietf-inet-types {
    prefix inet;
  }

  import ietf-system {
    prefix sys;
  }

  organization
    "IETF NETMOD (NETCONF Data Modeling Language) Working Group";

  contact
    "Qifeng Zhang
     Ericsson (China) Communication Co.,Ltd
     ET2, No.5 Lize East street, Chaoyang District
     100102
     China
     Phone: +86 13911502387
     EMail: qifeng.zhang@ericsson.com";

  description
    "This YANG module defines a data model for the configuration of
     DNS Resolver defined in RFC1035";
  revision 2016-09-23 {
    description
      "Initial revision.";
    reference
      "RFC 1035: DOMAIN NAMES - IMPLEMENTATION AND SPECIFICATION";
  }

  /* Configuration data */

  augment "/sys:system/sys:dns-resolver" {
    description
      "Augment dns-resolver to include resource record.";

    list resource-record {
      key "name";
      description
        "List of Resource Record entry.";

      leaf name {
        type string;
        description
          "An arbitrary name for the host.";
      }

      leaf address {
        type inet:ip-address;
        mandatory true;
        description
           "The address of the host.";
      }
    }
  }
}
