module ietf-nrp-policy {
  yang-version 1.1;
  namespace "urn:ietf:params:xml:ns:yang:ietf-nrp-policy";
  prefix nrp-pol;

  import ietf-inet-types {
    prefix inet;
    reference
      "RFC 6991: Common YANG Data Types";
  }
  import ietf-routing-types {
    prefix rt-types;
    reference
      "RFC 8294: Common YANG Data Types for the Routing Area";
  }
  import ietf-network {
    prefix nw;
    reference
      "RFC 8345: A YANG Data Model for Network Topologies";
  }
  import ietf-network-topology {
    prefix nt;
    reference
      "RFC 8345: A YANG Data Model for Network Topologies";
  }
  import ietf-access-control-list {
    prefix acl;
    reference
      "RFC 8519: YANG Data Model for Network Access Control Lists
       (ACLs)";
  }
  import ietf-topology-filter {
    prefix topo-filt;
    reference
      "draft-bestbar-teas-yang-topology-filter: YANG Data Model
       for Topology Filter";
  }

  organization
    "IETF Traffic Engineering Architecture and Signaling (TEAS)
     Working Group.";
  contact
    "WG Web:   <http://tools.ietf.org/wg/teas/>
     WG List:  <mailto:teas@ietf.org>

     Editor:   Vishnu Pavan Beeram
               <mailto:vbeeram@juniper.net>

     Editor:   Tarek Saad
               <mailto:tsaad@juniper.net>

     Editor:   Bin Wen
               <mailto:Bin_Wen@cable.comcast.com>

     Editor:   Daniele Ceccarelli
               <mailto:daniele.ceccarelli@ericsson.com>

     Editor:   Shaofu Peng
               <mailto:peng.shaofu@zte.com.cn>
     Editor:   Ran Chen
               <mailto:chen.ran@zte.com.cn>

     Editor:   Luis M. Contreras
               <mailto:luismiguel.contrerasmurillo@telefonica.com>

     Editor:   Xufeng Liu
               <mailto:xufeng.liu.ietf@gmail.com>";
  description
    "This YANG module defines a data model for managing Network
     Resource Partition Policies on Network Resource Partition
     capable nodes and controllers.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2022-07-25 {
    description
      "Initial revision.";
    reference
      "RFC XXXX: YANG Data Model for Network Resource Partition
       Policies.";
  }

  /*
   * I D E N T I T I E S
   */
  /*
   * Identity:
   * MPLS Flow Aggregate Selector (FAS) Label Position Type.
   */

  identity fas-mpls-label-position-type {
    description
      "Base identity for the position of the MPLS FAS label.";
  }

  identity fas-mpls-label-position-top {
    base fas-mpls-label-position-type;
    description
      "MPLS FAS label is at the top of the label stack.";
  }

  identity fas-mpls-label-position-bottom {
    base fas-mpls-label-position-type;
    description
      "MPLS FAS label is either at the bottom or at a specific
       offset from the bottom of the label stack.";
  }

  identity fas-mpls-label-position-indicator {
    base fas-mpls-label-position-type;
    description
      "MPLS FAS is preceded by a special purpose
       indicator label in the label stack.";
  }

  /*
   * T Y P E D E F S
   */

  typedef nrp-policy-acl-ref {
    type leafref {
      path "/acl:acls/acl:acl/acl:name";
    }
    description
      "This type is used to reference an ACL.";
  }

  typedef nrp-policy-topo-filter-ref {
    type leafref {
      path "/nw:networks/topo-filt:topology-filters/"
         + "topo-filt:topology-filter/topo-filt:name";
    }
    description
      "This type is used to reference a Topology Filter.";
  }

  typedef nrp-policy-topo-network-ref {
    type leafref {
      path "/nw:networks/nw:network/nw:network-id";
    }
    description
      "This type is used to reference a network.";
  }
  typedef nrp-policy-topo-node-ref {
    type leafref {
      path "/nw:networks/nw:network/nw:node/"
         + "nw:node-id";
    }
    description
      "This type is used to reference a node.";
  }

  typedef nrp-policy-topo-link-ref {
    type leafref {
      path "/nw:networks/nw:network/nt:link/"
         + "nt:link-id";
    }
    description
      "This type is used to reference a link.";
  }

  /*
   * G R O U P I N G S
   */
  /*
   * Grouping - MPLS FAS label location specific fields
   */

  grouping nrp-pol-fas-mpls-label-location {
    description
      "Grouping for MPLS FAS label location specific fields.";
    leaf label-position {
      type identityref {
        base fas-mpls-label-position-type;
      }
      description
        "MPLS FAS label position.";
    }
    leaf label-position-offset {
      when "derived-from-or-self(../label-position,"
         + "'nrp-pol:fas-mpls-label-position-bottom')" {
        description
          "MPLS label position offset is relevant only when the
           label-position is set to 'bottom'.";
      }
      type uint8;
      description
        "MPLS label position offset.";
    }
  }

  /*
   * Grouping - Flow-Aggregate Selector (FAS)
   */

  grouping nrp-pol-flow-agg-selector {
    description
      "Grouping for Flow-Aggregate Selector (FAS).";
    container flow-agg-selector {
      description
        "Container for FAS.";
      container mpls {
        description
          "Container for MPLS FAS.";
        choice fas-type {
          description
            "Choices for MPLS FAS.";
          case label {
            choice specification-type {
              description
                "Choices for MPLS label specification.";
              case derived {
                leaf forwarding-label {
                  type empty;
                  description
                    "MPLS FAS Label is derived from
                     forwarding label.";
                }
              }
              case explicit {
                leaf label {
                  type rt-types:mpls-label;
                  description
                    "MPLS FAS Label is explicitly
                     specified.";
                }
                uses nrp-pol-fas-mpls-label-location;
              }
            }
          }
          case label-ranges {
            list label-range {
              key "index";
              unique "start-label end-label";
              description
                "Any label from the specified set of MPLS label
                 ranges can be used as the FAS.";
              leaf index {
                type string;
                description
                  "A string that uniquely identifies a label
                   range.";
              }
              leaf start-label {
                type rt-types:mpls-label;
                must '. <= ../end-label' {
                  error-message
                    "The start-label must be less than or equal "
                  + "to end-label";
                }
                description
                  "Label-range start.";
              }
              leaf end-label {
                type rt-types:mpls-label;
                must '. >= ../start-label' {
                  error-message
                    "The end-label must be greater than or equal "
                  + "to start-label";
                }
                description
                  "Label-range end.";
              }
              uses nrp-pol-fas-mpls-label-location;
            }
          }
        }
      }
      container ipv4 {
        description
          "Container for IPv4 FAS.";
        leaf-list destination-prefix {
          type inet:ipv4-prefix;
          description
            "Any prefix from the specified set of IPv4
             destination prefixes can be the FAS.";
        }
      }
      container ipv6 {
        description
          "Container for IPv6 FAS.";
        choice fas-type {
          description
            "Choices for IPv6 FAS.";
          case ipv6-destination {
            leaf-list destination-prefix {
              type inet:ipv6-prefix;
              description
                "Any prefix from the specified set of IPv6
                 destination prefixes can be the FAS.";
            }
          }
          case ipv6-hbh-eh {
            leaf-list fas-hbh-eh {
              type uint32;
              description
                "Set of FAS values carried in Hop-by-Hop
                 Option of IPv6 extension header.";
            }
          }
        }
      }
      leaf-list acl-ref {
        type nrp-policy-acl-ref;
        description
          "Flow Aggregate selection is done based on the
           specified list of ACLs.";
      }
    }
  }

  /*
   * Grouping - NRP Policy Resource Reservation
   */

  grouping nrp-pol-resource-reservation {
    description
      "Grouping for NRP policy resource reservation.";
    container resource-reservation {
      description
        "Container for NRP policy resource reservation.";
      leaf preference {
        type uint16;
        description
          "Control plane preference for the corresponding
           Network Resource Partition (NRP). A higher
           preference indicates a more favorable resource
           reservation than a lower preference.";
      }
      choice max-bw-type {
        description
          "Choice of maximum bandwidth specification.";
        case bw-value {
          leaf maximum-bandwidth {
            type uint64;
            description
              "The maximum bandwidth allocated to an NRP
               - specified as absolute value.";
          }
        }
        case bw-percentage {
          leaf maximum-bandwidth-percent {
            type rt-types:percentage;
            description
              "The maximum bandwidth allocated to an NRP
               - specified as percentage of link
               capacity.";
          }
        }
      }
      leaf-list shared-resource-groups {
        type uint32;
        description
          "List of shared resource groups that an NRP
           shares its allocated resources with.";
      }
      container protection {
        description
          "Container for NRP protection reservation.";
        leaf backup-nrp-id {
          type uint32;
          description
            "The ID that identifies the NRP used for
             backup paths that protect primary paths
             setup over a specific NRP.";
        }
        choice backup-bw-type {
          description
            "Choice of backup bandwidth specification.";
          case backup-bw-value {
            leaf backup-bandwidth {
              type uint64;
              description
                "The maximum bandwidth on a network resource that
                 is allocated for backup traffic - specified as
                 absolute value.";
            }
          }
          case backup-bw-percentage {
            leaf backup-bandwidth-percent {
              type rt-types:percentage;
              description
                "The maximum bandwidth on a network resource that
                 is allocated for backup traffic - specified as
                 percentage of the link capacity.";
            }
          }
        }
      }
    }
  }

  /*
   * Grouping - NRP policy - PHB (NRP-PHB)
   */

  grouping nrp-pol-phb {
    description
      "Grouping for NRP-PHB.";
    leaf phb {
      type string;
      description
        "PHB profile identifier.";
    }
  }

  /*
   * Grouping - NRP Policy - Topology
   */

  grouping nrp-pol-topology {
    description
      "Grouping for NRP topology.";
    container topology {
      description
        "Container for NRP topology.";
      container filters {
        description
          "Container for filters.";
        list filter {
          key "filter-ref";
          description
            "List of filters.";
          leaf filter-ref {
            type nrp-policy-topo-filter-ref;
            description
              "Reference to a specific topology filter from the
               list of global topology filters.";
          }
          uses nrp-pol-resource-reservation;
          uses nrp-pol-flow-agg-selector;
          uses nrp-pol-phb;
        }
      }
      container filtered-topology {
        config false;
        description
          "Container for filtered topology.";
        choice filtered-topo-type {
          description
            "Choices for filtered topology.";
          case network {
            list network {
              key "network-ref";
              description
                "List of networks.";
              leaf network-ref {
                type nrp-policy-topo-network-ref;
                description
                  "Reference to a specific network.";
              }
            }
          }
          case network-elements {
            list node {
              key "network-ref node-ref";
              description
                "List of nodes.";
              leaf network-ref {
                type nrp-policy-topo-network-ref;
                description
                  "Reference to the network that
                   the node belongs to.";
              }
              leaf node-ref {
                type nrp-policy-topo-node-ref;
                description
                  "Reference to a specific node.";
              }
            }
            list link {
              key "network-ref link-ref";
              description
                "List of links.";
              leaf network-ref {
                type nrp-policy-topo-network-ref;
                description
                  "Reference to the network that
                   the link belongs to.";
              }
              leaf link-ref {
                type nrp-policy-topo-link-ref;
                description
                  "Reference to a specific link.";
              }
            }
          }
        }
      }
    }
  }

  /*
   * Grouping - Network Resource Partition Policies
   */

  grouping nrp-pol {
    description
      "Grouping for NRP policies.";
    container nrp-policies {
      description
        "Container for nrp policies.";
      list nrp-policy {
        key "name";
        unique "nrp-id";
        description
          "List of NRP policies.";
        leaf name {
          type string;
          description
            "A string that uniquely identifies the NRP policy.";
        }
        leaf nrp-id {
          type uint32;
          description
            "A 32-bit ID that uniquely identifies the NRP
             created by the enforcement of this NRP policy.";
        }
        uses nrp-pol-resource-reservation;
        uses nrp-pol-flow-agg-selector;
        uses nrp-pol-phb;
        uses nrp-pol-topology;
      }
    }
  }

  /*
   * Augment - Network Resource Partition Policies.
   */

  augment "/nw:networks" {
    description
      "Augment networks with network resource partition
       policies.";
    uses nrp-pol;
  }
}
