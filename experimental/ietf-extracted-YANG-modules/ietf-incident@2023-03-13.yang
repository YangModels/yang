module ietf-incident {
  yang-version 1.1;
  namespace "urn:ietf:params:xml:ns:yang:ietf-incident";
  prefix inc;
  import ietf-yang-types {
    prefix yang;
    reference
      "RFC 6991: Common YANG Data Types";
  }
  import ietf-network {
    prefix nw;
    reference
      "RFC 8345: A YANG Data Model for Network Topologies";
  }
  import ietf-network-inventory {
    prefix nw-inv;
    reference
      "draft-wzwb-opsawg-network-inventory-management-01:
      An Inventory Management Model for Enterprise Networks";
  }
  import ietf-alarms {
    prefix al;
    reference
      "RFC 8632: A YANG Data Model for Alarm Management";
  }
  organization
    "IETF OPSAWG Working Group";
  contact
    "WG Web:   &lt;https://datatracker.ietf.org/wg/opsawg/&gt;
     WG List:  &lt;mailto:opsawg@ietf.org&gt;
     Author:   Chong Feng  &lt;mailto:frank.fengchong@huawei.com&gt;
     Author:   Tong Hu  &lt;mailto:hutong@cmhi.chinamobile.com&gt;
     Author:   Luis Miguel Contreras Murillo &lt;mailto:
               luismiguel.contrerasmurillo@telefonica.com&gt;;
     Author :   Qin Wu   &lt;mailto:bill.wu@huawei.com&gt;
     Author:   ChaoDe Yu   &lt;mailto:yuchaode@huawei.com&gt;";

 description
    "This module defines the interfaces for incident management
     lifecycle.

     This module is intended for the following use cases:
     * incident lifecycle management:
       - incident report: report incident instance to client
                          when an incident instance is detected.
       - incident acknowledge: acknowledge an incident instance.
       - incident diagnose: diagnose an incident instance.
       - incident resolve: resolve an incident instance.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";
  revision 2023-03-13 {
    description "initial version";
    reference "RFC XXX: Yang module for incident management.";
  }
  //identities
  identity incident-domain {
    description "The abstract identity to indicate the domain of
                 an incident.";
  }
  identity single-domain {
    base incident-domain;
    description "single domain.";
  }
  identity access {
    base single-domain;
    description "access domain.";
  }
  identity ran {
    base access;
    description "radio access network domain.";
  }
  identity transport {
    base single-domain;
    description "transport domain.";
  }
  identity otn {
    base transport;
    description "optical transport network domain.";
  }
  identity ip {
    base single-domain;
    description "ip domain.";
  }
  identity ptn {
    base ip;
    description "packet transport network domain.";
  }

  identity cross-domain {
    base incident-domain;
    description "cross domain.";
  }
  identity incident-category {
    description "The abstract identity for incident category.";
  }
  identity device {
    base incident-category;
    description "device category.";
  }
  identity power-enviorment {
    base device;
    description "power system category.";
  }
  identity device-hardware {
    base device;
    description "hardware of device category.";
  }
  identity device-software {
    base device;
    description "software of device category";
  }
  identity line {
    base device-hardware;
    description "line card category.";
  }
  identity maintenance {
    base incident-category;
    description "maintenance category.";
  }
  identity network {
    base incident-category;
    description "network category.";
  }
  identity protocol {
    base incident-category;
    description "protocol category.";
  }
  identity overlay {
    base incident-category;
    description "overlay category";
  }
  identity vm {
    base incident-category;
    description "vm category.";
  }

  //typedefs
  typedef incident-priority {
    type enumeration {
      enum critical {
        description "the incident MUST be handled immediately.";
      }
      enum high {
        description "the incident should be handled as soon as
                     possible.";
      }
      enum medium {
        description "network services are not affected, or the
                     services are slightly affected,but corrective
                     measures need to be taken.";
      }
      enum low {
        description "potential or imminent service-affecting
                     incidents are detected,but services are
                     not affected currently.";
      }
    }
    description "define the priority of incident.";
  }
  typedef node-ref {
    type leafref {
      path "/nw:networks/nw:network/nw:node/nw-inv:name";
    }
    description "reference a network node.";
  }
  //groupings
  grouping resources-info {
    description "the grouping which defines the network
                 resources of a node.";
    leaf node {
      type node-ref;
      description "reference to a network node.";
    }
    list resource {
      key name;
      description "the resources of a network node.";
      leaf name {
         type al:resource;
         description "network resource name.";
      }
    }
  }

  grouping incident-time-info {
    description "the grouping defines incident time information.";
    leaf raise-time {
      type yang:date-and-time;
      description "the time when an incident instance is raised.";
    }
    leaf occur-time {
      type yang:date-and-time;
      description "the time when an incident instance is occured.
                   It's the occur time of the first event during
                   incident detection.";
    }
    leaf clear-time {
      type yang:date-and-time;
      description "the time when an incident instance is
                   resolved.";
    }
    leaf ack-time {
      type yang:date-and-time;
      description "the time when an incident instance is
                   acknowledged.";
    }
    leaf last-updated {
      type yang:date-and-time;
      description "the latest time when an incident instance is
                   updated";
    }
  }

  grouping incident-info {
    description "the grouping defines the information of an
                 incident.";
    leaf csn {
      type uint64;
      mandatory true;
      description "The sequence number of the incident instance.";
    }
    leaf-list service-instance {
      type string;
      description "the related network service instances of
                   the incident instance.";
    }
    leaf name {
      type string;
      mandatory true;
      description "the name of an incident.";
    }
    leaf type {
      type enumeration {
        enum fault {
          description "It indicates the type of the incident
                       is a fault, for example an interface
                       fails to work.";
        }
        enum potential-risk {
          description "It indicates the type of the incident
                       is a potential risk, for example high
                       CPU rate may cause a fault in the
                       future.";
        }
      }
      mandatory true;
      description "The type of an incident.";
    }
    leaf domain {
      type identityref {
        base incident-domain;
      }
      mandatory true;
      description "the domain of an incident.";
    }
    leaf priority {
      type incident-priority;
      mandatory true;
      description "the priority of an incident instance.";
    }

    leaf status {
      type enumeration {
        enum raised {
          description "an incident instance is raised.";
        }
        enum updated {
          description "the information of an incident instance
                       is updated.";
        }
        enum cleared {
          description "an incident is cleared.";
        }
      }
      default raised;
      description "The status of an incident instance.";
    }
    leaf ack-status {
      type enumeration {
        enum acknowledged;
        enum unacknowledged;
      }
      default unacknowledged;
      description "the acknowledge status of an incident.";
    }
    leaf category {
      type identityref {
        base incident-category;
      }
      mandatory true;
      description "The category of an incident.";
    }

    leaf tenant {
      type string;
      description "the identifier of related tenant.";
    }
    leaf detail {
      type string;
      description "detail information of this incident.";
    }
    leaf resolve-suggestion {
      type string;
      description "The suggestion to resolve this incident.";
    }
    container sources {
      description "The source components.";
      list source {
        key node;
        uses resources-info;
        min-elements 1;
        description "The source components of incident.";
      }
    }

    container root-causes{
      description "The root cause objects.";
      list root-cause {
        key node;
        description "the root causes of incident.";
        grouping root-cause-info {
          description "The information of root cause.";
          leaf cause-name {
            type string;
            description "the name of cause";
          }
          leaf detail {
            type string;
            description "the detail information of the cause.";
          }
        }
        uses resources-info {
          augment resource {
            description "augment root cause information.";
            //if root cause object is a resource of a node
            uses root-cause-info;
          }
        }
        //if root cause object is a node
        uses root-cause-info;
      }
    }
    container events {
      description "related event.";
      list event {
        key "type original-node";
        description "related event.";
        leaf type {
          type enumeration {
            enum alarm {
              description "alarm type";
            }
            enum notification {
              description "notification type";
            }
            enum log {
              description "log type";
            }
            enum KPI {
              description "KPI type";
            }
            enum unknown {
              description "unknown type";
            }
          }
          description "event type.";
        }
        leaf original-node {
          type union {
            type node-ref;
            type empty;//self
          }
          description "the original node where the event occurs.";
        }
        leaf is-root {
          type boolean;
          default false;
          description "whether this event is the cause of
                        incident.";
        }
        choice event-type-info {
          description "event type information.";
          case alarm {
            when "type = 'alarm'";
            container alarm {
              description "alarm type event.";
              leaf resource {
                type leafref {
                  path "/al:alarms/al:alarm-list/al:alarm"
                      +"/al:resource";
                }
                description "network resource.";
                reference "RFC 8632: A YANG Data Model for Alarm
                           Management";
              }
              leaf alarm-type-id {
                type leafref {
                  path "/al:alarms/al:alarm-list/al:alarm"
                      +"[al:resource = current()/../resource]"
                      +"/al:alarm-type-id";
                }
                description "alarm type id";
                reference "RFC 8632: A YANG Data Model for Alarm
                            Management";
              }
              leaf alarm-type-qualifier {
                type leafref {
                  path "/al:alarms/al:alarm-list/al:alarm"
                      +"[al:resource = current()/../resource]"
                      +"[al:alarm-type-id = current()/.."
                      +"/alarm-type-id]/al:alarm-type-qualifier";
                }
                description "alarm type qualitifier";
                reference "RFC 8632: A YANG Data Model for Alarm
                           Management";
              }
            }
          }
          case notification {
            //TODO
          }
          case log {
          //TODO
          }
          case KPI {
          //TODO
          }
          case unknown {
          //TODO
          }
        }
      }

    }

  }

  //data definitions
  container incidents {
    config false;
    description "the information of incidents.";
    list incident {
      key incident-id;
      description "the information of incident.";
      leaf incident-id {
        type string;
        description "the identifier of an incident instance.";
      }
      uses incident-info;
      uses incident-time-info;
    }
  }

  // notifications
  notification incident-notification {
    description "incident notification. It will be triggered when
                 the incident is raised, updated or cleared.";
    leaf incident-id {
      type string;
      description "the identifier of an incident instance.";
    }
    uses incident-info;
    leaf time {
      type yang:date-and-time;
      description "occur time of an incident instance.";
    }
  }
  // rpcs
  rpc incident-acknowledge {
    description "This rpc can be used to acknowledge the specified
                 incidents.";
    input {
      leaf-list incident-id {
        type string;
        description "the identifier of an incident instance.";
      }
    }
  }
  rpc incident-diagnose {
    description "This rpc can be used to diagnose the specified
                 incidents.";
    input {
      leaf-list incident-id {
        type string;
        description
          "the identifier of an incident instance.";
      }
    }
    output {
      list incident {
        key incident-id;
        description "The entry of returned incidents.";
        leaf incident-id {
          type string;
          description
            "the identifier of an incident instance.";
        }
        choice result {
          description "result information.";
          case success {
            uses incident-info;
            leaf time {
              type yang:date-and-time;
              description
                "The update time of an incident.";
            }
          }
          case failure {
            leaf error-code {
              type string;
              description "error code";
            }
            leaf error-message {
              type string;
              description "error message";
            }
          }
        }
      }
    }
  }

  rpc incident-resolve {
    description "This rpc can be used to resolve the specified
                 incidents. It also can be used to set the
                 incident instances are resolved if these incident
                 instances are resolved by external system.";
    input {
      list incident {
        key incident-id;
        min-elements 1;
        description "incident instances.";
        leaf incident-id {
          type leafref {
            path "/inc:incidents/inc:incident/inc:incident-id";
          }
          description
            "the identifier of an incident instance.";
        }
        leaf resolved {
          type empty;
          description "indicate the incident instance has
                       been resolved.";
        }

      }
    }
    output {
      list incident {
        key incident-id;
        description "incident instances";
        leaf incident-id {
          type string;
          description "the identifier of incident instance";
        }
        choice result {
          description "result information";
          case success {
            leaf success {
              type empty;
              description "reslove incident instance
                           successfully";
            }
            leaf time {
              type yang:date-and-time;
              description "The resolved time of an incident.";
            }
          }
          case failure {
            leaf error-code {
              type string;
              description "error code";
            }
            leaf error-message {
              type string;
              description "error message.";
            }
          }
        }
      }
    }
  }
}
