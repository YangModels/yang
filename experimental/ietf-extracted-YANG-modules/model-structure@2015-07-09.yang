module model-structure {

  yang-version "1";

  // namespace
  namespace "urn:ietf:params:xml:ns:yang:model-structure";

  prefix "struct";

  // import some basic types

  // meta
  organization "OpenConfig working group/IETF RTG YANG Design Team";

  contact
    "OpenConfig working group netopenconfig@googlegroups.com
     Routing Area YANG Architecture DT rtg-dt-yang-arch@ietf.org";

  description "This module describes a model structure for YANG
    configuration and operational state data models. Its intent is
    to describe how individual device protocol and feature models
    fit together and interact.";

  revision "2015-07-09" {
    description
      "First Pass of IETF Routing YANG Design Team";
    reference "draft-rtgyangdt-rtgwg-device-model-00.txt";
  }

  // extension statements

  // feature statements

  // identity statements

  // typedef statements

  // grouping statements

  grouping info {
    description
      "Base system information";

    container info {
      description
        "This container is for base system information, including
        device type (e.g., physical or virtual), model, serial no.,
        location, etc.";

      leaf device-type {
        //TODO: consider changing to an identity if finer grained
        // device type classification is envisioned
        type enumeration {
          enum PHYSICAL {
            description "physical or hardware device";
          }
          enum VIRTUAL {
            description "virtual or software device";
          }
        }
        description
          "Type of the device, e.g., physical or virtual.  This node
          may be used to activate other containers in the model";
      }

    }
  }

  grouping hardware {
    description
      "hardware / vendor -specific data relevant to the platform";
    container hardware {
      description
        "This container is an anchor point for platform-specific
        configuration and operational state data.  It may be further
        organized into chassis, line cards, ports, etc.  It is
        expected that vendor or platform-specific augmentations
        would be used to populate this part of the device model";
    }
  }

  grouping interface-ip-common {
    description
      "interface-specific configuration for IP interfaces, IPv4 and
      IPv6";

  }

  grouping interfaces {
    description "interface-related models";
    container interfaces {
      description "Various interface models";
      reference "RFC 7223 - A Yang Model for Interface Management";
      list interface {
        key "name";
        description "List of interfaces keyed by name";
        leaf name {
            type string;
            description "Interface name";
        }
        leaf bind-network-element-id {
          type uint8;
          description "Logical network element ID to which
                       interface is bound";
        }
        container ethernet {
          description "Ethernet interface config, e.g., 10, 40,
                       100GB Ethernet";
          leaf bind-networking-instance-name {
              type string;
              description "Networking Instance to which
                           the Ethernet instance is bound";
          }
          container aggregates {
              description
                  "LAGs, LACP, etc. for Ethernet interfaces";
              reference "IEEE 802.1ad, 802.1AX";
          }
          container rstp {
              description "Rapid Spanning Tree Protocol";
              reference "IEEE 802.1D-2004";
          }
          container lldp {
              description "link layer discovery protocol";
              reference "IEEE 802.1AB";
          }
          container ptp {
              description
                  "Precision Time Protocol (PTP) for time
                   synchronization services. PTP typically requires
                   per-interface configuration";
              reference "IEEE 1588-2008";
          }
        }
        container vlans {
            description "VLANs, 802.1q, q-in-q, etc.";
            reference "IEEE 802.1Q";
        }
        container tunnels {
            description
                "Logical tunnel interfaces incl. GRE, VxLAN,
                  L2TP etc.";
        }

        container ipv4 {
          description "IPv4 interface";
          reference "RFC 7277 - A Yang Model for IP Management";
          leaf bind-networking-instance-name {
              type string;
              description "Networking Instance to which
                           IPv4 interface is bound";
          }
          container arp {
            description "Address resolution protocol";
            reference "STD 37 - An Ethernet Address Resolution
                       Protocol";
          }
         container icmp {
           description "Internet Control Message Protocol";
           reference "RFC 792 - Internet Control Message Protocol";
         }
         container vrrp {
           description "virtual router redundancy protocol";
           reference
             "RFC 5798 - Virtual Router Redundancy Protocol
              (VRRP) Version 3 for IPv4 and IPv6";
          }
         container dhcp-client {
           description "Dynamic Host Configuration Protocol";
            reference
              "RFC 2131 - Dynamic Host Configuration Protocol";
         }
        }
        container ipv6 {
          description "IPv6 interface";
            reference "RFC 7277 - A Yang Model for IP Management";
            leaf bind-networking-instance-name {
                type string;
                description "Networking Instance to which
                             IPv4 interface is bound";
            }
          container vrrp {
              description "virtual router redundancy protocol";
              reference
                  "RFC 5798 - Virtual Router Redundancy Protocol
                   (VRRP) Version 3 for IPv4 and IPv6";
          }
          container icmpv6 {
            description "Internet Control Message Protocol";
            reference
              "RFC 2463 - Internet Control Message Protocol
               (ICMPv6) for Internet Protocol Version 6 (IPv6)";
          }
          container nd {
            description "IPv6 Neighbor Discovery";
              reference "RFC 4861 - Neighbor Discovery for IP
                         version 6 (IPv6)";
          }
         container dhcpv6-client {
           description
               "Dynamic Host Configuration Protocol Version 6";
            reference
                "RFC 3315 - Dynamic Host Configuration Protocol
                 for IPv6 (DHCPv6)";
         }
        }
      }
    }
  }

  identity networking-instance {
      description
         "Base identity from which identities describing
          networking instance types are derived.";
  }

  grouping router-id {
      description
          "This grouping provides router ID.";
      leaf router-id {
          type uint32;  // yang:dotted-quad
          description
            "A 32-bit number in the form of a dotted quad that is
             used by some routing protocols identifying a router.";
          reference
              "RFC 2328: OSPF Version 2.";
      }
  }

  grouping oam-protocols {
   description
      "Definitions for OAM protocols within a networking-instance";
   container oam-protocols {
       description
           "OAM protocols";
     container bfd {
         description "Bi-directional Forwarding Detection (BFD)
                   configuration";

     }
     container cfm {
         description
            "Ethernet connectivity fault management.  Also includes
             options that are associated with specific interfaces,
             such as maintenance endpoint domains.";
        reference "IEEE 802.1ag";
     }
     container twamp {
         description
             "Two-way active measurement protocol for measuring
             round-trip IP layer performance.";
         reference "RFC 5357 A Two-Way Active Measurement Protocol
                   (TWAMP)";
     }
   }
  }

  grouping mpls {
    description "MPLS and TE configuration";
    container mpls {
      description "MPLS and TE configuration";
      container global {
          description "global MPLS configuration";
      }
     container label-switched-paths {
       description "Models for different types of LSPs";
     }
     container constrained-path {
       description "traffic-engineered or constrained path LSPs";
     }
     container igp-congruent {
       description "LSPs that follow the IGP-computed path";
     }
     container static {
        description "Statically configured LSPs";
     }
    }
  }

  grouping networking-instance-policy {
    description
        "Networking instance policies such as route
         distinguisher, route targets, VPLS ID and neighbor,
         Ethernet ID, etc. ";
    reference
        "RFC 4364 - BGP/MPLS Virtual Private Networks (VPNs)
         RFC 6074 - Provisioning, Auto-Discovery, and Signaling
              in Layer 2 Virtual Private Networks (L2VPNs)
         RFC 7432 - BGP MPLS-Based Ethernet VPN";
    container networking-instance-policy {
        description "Networking Instance Policy -- details TBD";
    }
  }

  grouping control-plane-protocols {
    description "control protocol models";

    container control-plane-protocols {
      description "Control plane protocols and features";

      container bgp {
          description "BGP-4 protocol configuration";
          reference "RFC 4271 - Border Gateway Protocol 4 (BGP-4)";
          container policy {
              description "Policy specific to BGP";
          }
      }
      container is-is {
          description "ISO IS-IS protocol configuration";
          reference "RFC 1195 - Use of OSI IS-IS for Routing in
                     TCP/IP and Dual Environments";
          container policy {
              description "Policy specific to IS-IS";
          }
      }
      container ospf {
          description "Open Shortest Path First (OSPF) protocol
                       configuration";
          reference "RFC 2328 - OSPFv2 Protocol
                     RFC 5340 - OSPF for IPv6";
          container policy {
              description "Policy specific to OSPF";
          }
      }
      container rsvp {
          description "Resource Reservation Protocol (RSVP)
                       protocol configuration";
          reference "RFC 2205 - Resource ReSerVation Protocol (RSVP)
                     RFC 3209 - RSVP-TE: Extensions to RSVP for LSP
                     Tunnels";
      }
      container segment-routing {
          description "Segment Routing configuration for networking
                       instance";
          reference "draft-likowski-spring-sr-yang";
      }
      container ldp {
          description "Label Distribution Protocol (LDP)
                       configuration";
          reference "RFC 5036 - LDP Specification";
      }
      container pim {
          description "Protocol Independent Multicast (PIM)
                       configuration";
          reference "RFC 4601 - Protocol Independent Multicast -
                     Sparse Mode (PIM-SM) Protocol Specification";
      }
      container igmp {
          description "Internet Group Management Protocol
                       configuration";
          reference "RFC 3376 - Internet Group Management Protocol,
                     Version 3";
      }
      container mld {
          description "Multicast Listener Discovery Protocol
                       configuration";
          reference "RFC 3810 - Multicast Listener Discovery
                     Version 2 (MLDv2 for IPv6)";
      }
      container static-routes {
          description "Static route configuration";
          reference "draft-ietf-netmod-routing-cfg";
      }
    }
  }

  grouping ribs {
    description
      "Routing Information Bases (RIBs) supported by a
       networking-instance";
    container ribs {
        description
            "RIBs supported by a networking-instance";
        list rib {
            key "name";
            min-elements "1";
            description
                "Each entry represents a RIB identified by the
               'name' key. All routes in a RIB must belong to the
                same address family.

                For each routing instance, an implementation should
                provide one system-controlled default RIB for each
                supported address family.";
            leaf name {
                type string;
                description
                    "The name of the RIB.";
            }
            reference "draft-ietf-netmod-routing-cfg";
            leaf description {
                type string;
                description
                    "Description of the RIB";
            }
            // Note that there is no list of interfaces within
            container policy {
                description "Policy specific to RIB";
            }
        }
    }
  }

  grouping networking-services {
    description
      "Networking services provided by the device in the scope of
       the networking-instance";
     container networking-services {
       description "Networking services";
       container ntp-server {
         description "Network Time Protocol (NTP) Server";
         reference "RFC 5905 - Network Time Protocol Version 4:
                    Protocol and Algorithms Specification";
       }
       container dns-server {
         description "Domain Name System (DNS) Server";
         reference "RFC 1035 - DOMAIN NAMES - IMPLEMENTATION
                   AND SPECIFICATION";
       }
       container dhcp-server {
         description "Dynamic Host Configuration Protocol (DHCP)
                      Server";
         reference "RFC 2131 - Dynamic Host Configuration Protocol";
       }
     }
  }

  grouping system-management {
      description "System management for device or logical network
                   element";
      container system-management {
          description "System management - logical device
                       management with reuse of RFC 7317";
          leaf device-view {
              type boolean;
              default "true";
              description "Flag indicating whether or not the
                           logical network element is able to view
                           and manage the entire device";
          }
          container syslog {
              description "Syslog configuration";
          }
          container dns {
              description "Domain Name Service (DNS) and resolver
                           configuration";
          }
          container ntp {
              description "network time protocol configuration";
          }
          container statistics-collection {
              description
                  "Mechanisms for data collection from devices,
                   including packet and flow-level sampling";
          }
          container ssh {
              description "SSH server configuration";
          }
          container tacacs {
              description "TACACS+ configuration";
          }
          container snmp {
              description "System Network Management Protocol
                           (SNMP) configuration";
          }
          container netconf {
              description "Network Configuration Protocol(NETCONF)";
              reference "RFC 6020 - YANG - A Data Modeling Language
                         for the Network Configuration Protocol
                         (NETCONF)";
          }
      }
  }

  grouping ietf-acl {
      description "Packet Access Control Lists (ACLs) as specified
                   in draft-ietf-netmod-acl-model";
      container ietf-acl {
          description "ACLs and packet forwarding rules";
      }
  }

  grouping ietf-key-chain {
      description "Key chains as specified in
                   draft-acee-rtgwg-yang-key-chain;";
      container ietf-key-chain {
          description "Key chains";
      }
  }

  grouping qos {
    description "QoS features";

    container qos {
      description "QoS, including policing, shaping, etc.";
    }
  }

  // data definition statements

  container device {
    description "Top-level anchor point for models. Device is a
                 generic L2/L3 network element";
    uses info;
    uses hardware;
    uses interfaces;
    uses qos;
    container logical-network-elements {
      description "Network devices may support multiple logical
      network instances";
      list logical-network-element {
        key network-element-id;
        description "List of logical network elements";
        leaf network-element-id {
          type uint8; // expect a small number of logical routers
          description "Device-wide unique identifier for the
                       logical network element";
        }
        leaf network-element-name {
          type string;
          description "Descriptive name for the logical network
                       element";
        }
        leaf default-networking-instance-name {
          type string;
          description "Specification of the networking instance to
                       use for management connectivity";
        }
        uses system-management;
        uses ietf-acl;
        uses ietf-key-chain;
        container networking-instances {
            description "Networking instances each of which have
                         an independent IP/IPv6 addressing space
                         and protocol instantiations. For layer 3,
                         this consistent with the routing-instance
                         definition in ietf-routing";
            reference "draft-ietf-netmod-routing-cfg";
            list networking-instance {
                key networking-instance-name;
                description "List of networking-instances";
                leaf networking-instance-name {
                    type string;
                    description "logical network element scoped
                                 identifier for the networking
                                 instance";
                }
                leaf type {
                    type identityref {
                        base networking-instance;
                    }
                    description
                        "The networking instance type -- details TBD
                         Likely types include core, L3-VRF, VPLS,
                         L2-cross-connect, L2-VSI, etc.";
                }
                leaf enabled {
                    type boolean;
                    default "true";
                    description
                      "Flag indicating whether or not the networking
                       instance is enabled.";
                }
                uses router-id {
                    description
                        "Router ID for networking instances";
                }
                leaf description {
                    type string;
                    description
                      "Description of the networking instance
                      and its intended purpose";
                }
                // Note that there is no list of interfaces within
                // the networking-instance
                uses oam-protocols;
                uses networking-instance-policy;
                uses control-plane-protocols;
                uses ribs;
                uses mpls;
                uses networking-services;
            }
        }
      }
    }

  }

  // augment statements

  // rpc statements

  // notification statements

}
