submodule ietf-bgp-rib-shared-attributes {
  yang-version "1.1";
  belongs-to ietf-bgp {
    prefix "br";
  }

  // import some basic types
  include ietf-bgp-rib-attributes;

  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "This submodule contains structural data definitions for
     attribute sets shared across routes.";

  revision "2019-03-21" {
    description
      "Initial version";
    reference
      "RFC XXXX: BGP YANG Model for Service Provider Network.";
  }
  grouping attribute-sets {
    description
      "Top level grouping for list of common attribute sets";

    container attr-sets {
      description
        "Enclosing container for the list of path attribute sets";

      list attr-set {
        key "index";

        description
          "List of path attributes that may be in use by multiple
          routes in the table";

        leaf index {
          type uint64;
          description
            "System generated index for each attribute set.  The
              index is used to reference an attribute set from a
              specific path.  Multiple paths may reference the same
              attribute set.";
        }

        uses bgp-shared-common-attr-state;
        uses bgp-aggregator-attr-top;
        uses bgp-as-path-attr-top;
        uses bgp-as4-path-attr-top;
        uses bgp-tunnel-encapsulation-attr-top;
      }
    }
  }

  grouping community-sets {
    description
      "Top level grouping for list of shared community attribute
      sets";

    container communities {
      description
        "Enclosing container for the list of community attribute
        sets";

      list community {
        key "index";

        config false;
        description
          "List of path attributes that may be in use by multiple
          routes in the table";

        leaf index {
          type uint64;
          description
            "System generated index for each attribute set.  The
              index is used to reference an attribute set from a
              specific path.  Multiple paths may reference the same
              attribute set.";
        }

        uses bgp-community-attr-state;
      }
    }
  }

  grouping ext-community-sets {
    description
      "Top level grouping for list of extended community attribute
      sets";

    container ext-communities {
      description
        "Enclosing container for the list of extended community
        attribute sets";

      list ext-community {
        key "index";

        config false;
        description
          "List of path attributes that may be in use by multiple
          routes in the table";

        leaf index {
          type uint64;
          description
            "System generated index for each attribute set.  The
              index is used to reference an attribute set from a
              specific path.  Multiple paths may reference the same
              attribute set.";
        }

        uses bgp-extended-community-attr-state;
      }
    }
  }
}
