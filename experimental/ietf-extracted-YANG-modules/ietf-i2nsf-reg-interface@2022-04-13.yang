module ietf-i2nsf-reg-interface {
  yang-version 1.1;

  namespace "urn:ietf:params:xml:ns:yang:ietf-i2nsf-reg-interface";

  prefix nsfreg;

  //RFC Ed.: replace occurences of XXXX with actual RFC number and
  //remove this note

  import ietf-inet-types {
    prefix inet;
    reference "RFC 6991";
  }
  import ietf-i2nsf-capability {
    prefix nsfcap;
  // RFC Ed.: replace YYYY with actual RFC number of
  // draft-ietf-i2nsf-capability-data-model and remove this note.
    reference "RFC YYYY: I2NSF Capability YANG Data Model";
  }

  organization
   "IETF I2NSF (Interface to Network Security Functions)
    Working Group";

  contact
    "WG Web: <https://datatracker.ietf.org/wg/i2nsf>
     WG List: <mailto:i2nsf@ietf.org>

     Editor: Sangwon Hyun
     <mailto:shyun@mju.ac.kr>

     Editor: Jaehoon Paul Jeong
     <mailto:pauljeong@skku.edu>";

  description
    "This module defines a YANG data model for I2NSF
     Registration Interface.

     The key words 'MUST', 'MUST NOT', 'REQUIRED', 'SHALL',
     'SHALL NOT', 'SHOULD', 'SHOULD NOT', 'RECOMMENDED',
     'NOT RECOMMENDED', 'MAY', and 'OPTIONAL' in this
     document are to be interpreted as described in BCP 14
     (RFC 2119) (RFC 8174) when, and only when, they appear
     in all capitals, as shown here.

     Copyright (c) 2022 IETF Trust and the persons
     identified as authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision "2022-04-13" {
    description "Initial revision";
    reference
      "RFC XXXX: I2NSF Registration Interface YANG Data Model";
    // RFC Ed.: replace XXXX with actual RFC number and remove
    // this note
  }

  grouping nsf-performance-capability {
    description
      "Description of the performance capabilities of an NSF";

    container processing {
      description
        "Processing power of an NSF in the unit of GHz (gigahertz)";

      leaf processing-average {
        type uint16;
        units "GHz";
        description
          "Average processing power";
      }
      leaf processing-peak {
        type uint16;
        units "GHz";
        description
          "Peak processing power";
      }
    }

    container bandwidth {
      description
        "Network bandwidth available on an NSF
         in the unit of Mbps (megabits per second)";

      container outbound {
        description
          "Outbound network bandwidth";
        leaf outbound-average {
          type uint32;
          units "Mbps";
          description
            "Average outbound bandwidth";
        }
        leaf outbound-peak {
          type uint32;
          units "Mbps";
          description
            "Peak outbound bandwidth";
        }
      }

      container inbound {
        description
          "Inbound network bandwidth";
        leaf inbound-average {
          type uint32;
          units "Mbps";
          description
            "Average inbound bandwidth";
        }
        leaf inbound-peak {
          type uint32;
          units "Mbps";
          description
            "Peak inbound bandwidth";
        }
      }
    }
  }

  grouping nsf-capability-info {
    description
      "Capability description of an NSF";
    container security-capability {
      description
        "Description of the security capabilities of an NSF";
      uses nsfcap:nsf-capabilities;
      reference "RFC YYYY: I2NSF Capability YANG Data Model";
      // RFC Ed.: replace YYYY with actual RFC number of
      // draft-ietf-i2nsf-capability-data-model and remove this note.
    }
    container performance-capability {
      description
        "Description of the performance capabilities of an NSF";
      uses nsf-performance-capability;
    }
  }

  grouping nsf-access-info {
    description
      "Information required to access an NSF";
    leaf ip {
      type inet:ip-address-no-zone;
      description
        "Either an IPv4 address or an IPv6 address of this NSF";
    }
    leaf port {
      type inet:port-number;
      description
        "Port available on this NSF";
    }
  }

  container nsf-registrations {
    description
      "Information of an NSF that DMS registers
       to Security Controller";
    list nsf-information {
      key "nsf-name";
      description
        "Required information for registration";
      leaf nsf-name {
        type string;
        description
        "The name of this registered NSF. The NSF name MUST be unique
         to identify the NSF with the capability. The name can be an
         arbitrary string including FQDN (Fully Qualified Domain
         Name).";
      }
      container nsf-capability-info {
        description
          "Capability description of this NSF";
        uses nsf-capability-info;
      }
      container nsf-access-info {
        description
          "Network access information of this NSF";
        uses nsf-access-info;
      }
    }
  }

  rpc nsf-capability-query {
    description
      "Description of the capabilities that the
       Security Controller requests to the DMS";
    input {
      container query-nsf-capability {
        description
          "Description of the capabilities to request";
        uses nsfcap:nsf-capabilities;
        reference "RFC YYYY: I2NSF Capability YANG Data Model";
      //RFC Ed.: replace YYYY with actual RFC number of
      //draft-ietf-i2nsf-capability-data-model and remove this note.
      }
    }
    output {
      container nsf-access-info {
        description
          "Network access information of an NSF
           with the requested capabilities";
        leaf nsf-name {
          type string;
          description
          "The name of this registered NSF. The NSF name MUST be
           unique to identify the NSF with the capability. The name
           can be an arbitrary string including FQDN (Fully Qualified
           Domain Name).";
        }
        uses nsf-access-info;
      }
    }
  }
}
