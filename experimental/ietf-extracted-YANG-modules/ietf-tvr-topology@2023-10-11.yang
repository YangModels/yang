module ietf-tvr-topology {
  yang-version 1.1;
  namespace "urn:ietf:params:xml:ns:yang:ietf-tvr-topology";
  prefix tvr-topo;

  import ietf-inet-types {
    prefix inet;
    reference
      "RFC 6991: Common YANG Data Types";
  }

  import ietf-te-types {
    prefix te-types;
  }

  import ietf-tvr-schedule {
    prefix "tvr-schd";
  }

  organization
    "IETF Time-Variant Routing Working Group";

  contact
    "WG Web:   <https://datatracker.ietf.org/wg/tvr/>
     WG List:  <mailto:tvr@ietf.org>

     Author:   Eric Kinzie
               <mailto:ekinzie@labn.net>
     Author:   Don Fedyk
               <mailto:dfedyk@labn.net>
     Author:   Yingzhen Qu
               <mailto:yingzhen.ietf@gmail.com>
     Author:   Acee Lindem
               <mailto:acee.ietf@gmail.com>
     Author:   Marc Blanchet
               <mailto:marc.blanchet@viagenie.ca>";

  description
    "This YANG module contains YANG definitions for describing
    network topology with an time-variant availability schedule.

    Copyright (c) 2023 IETF Trust and the persons identified as
    authors of the code.  All rights reserved.

    Redistribution and use in source and binary forms, with or
    without modification, is permitted pursuant to, and subject to
    the license terms contained in, the Revised BSD License set forth
    in Section 4.c of the IETF Trust's Legal Provisions Relating
    to IETF Documents (https://trustee.ietf.org/license-info).

    This version of this YANG module is part of RFC XXXX
    (https://www.rfc-editor.org/info/rfcXXXX); see the RFC itself
    for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2023-10-11 {
    description
      "Initial revision";
    reference
      "RFC XXXX: YANG Data Model for Scheduled Attributes";
  }

  container topology-schedule {
    description
      "Network topology schedules.";
    list nodes {
      key "node-id";
      description
        "List of nodes with schedules.";
      leaf node-id {
        type inet:uri;
        description
          "Identifier for a node, uniquely identifies a node. This
           may be the same as the node-id defined in the ietf-network
           module defined in RFC 8345.";
      }
      list available {
        key "start-date-time";
        description
          "The time at which this node becomes available.";
        uses tvr-schd:schedule {
          augment value-default {
            description
              "Augment default node availability.";
            leaf default-node-available {
              type boolean;
              default false;
              description
                "By default, the node is powered off.";
            }
          }
          augment base-schedule/intervals/value {
            description
              "Augment scheduled node availability.";
            leaf node-available {
              type boolean;
              description
                "Node availability.";
            }
          }
        }
      }
    }

    list links {
      key "source-node source-link-id";
      description
        "List of links.";
      leaf source-node {
        type inet:uri;
        description
          "A name refers to the source node of the link.";
      }
      leaf destination-node {
        type inet:uri;
        description
          "A name refers to the destination node of the link.";
      }
      leaf source-link-id {
        type string;
        description
          "A name refers to the link of the source node.";
      }
      list available {
        key "start-date-time";
        description
          "The time at which this link becomes available.";
        uses tvr-schd:schedule;

        container bandwidth {
          description
            "Scheduled link bandwidth.
             If the value measured by the system is less than this
             value, the system value is used.  If the value measured
             by the system is greater than this value the predicted
             value SHOULD be used.";
          uses tvr-schd:base-schedule {
            augment value-default {
              description
                "Augment default interface bandwidth.";
              leaf default-bandwidth {
                type te-types:te-bandwidth;
                default "0";
                description
                  "The default link capacity specified in a
                   generic format.";
              }
            }
            augment base-schedule/intervals/value {
              description
                "Augment scheduled interface bandwidth.";
              leaf bandwidth {
                type te-types:te-bandwidth;
                description
                  "The predicted link capacity specified in a
                   generic format.";
              }
            }
          }
        }
        container delay {
          description
            "The one-way delay or latency in microseconds. If the
             value measured by the system is less than this value
             the predicted value SHOULD be used.";
          uses tvr-schd:base-schedule {
            augment value-default {
              description
                "Augment default delay.";
              leaf default-delay {
                type uint32 {
                  range "0..16777215";
                }
                description
                  "The default link capacity specified in a
                   generic format.";
              }
            }
            augment base-schedule/intervals/value {
              description
                "Augment scheduled delay.";
              leaf delay {
                type uint32 {
                  range "0..16777215";
                }
                description
                  "The predicted link delay specified in a
                   generic format.";
              }
            }
          }
        }
      }
    }
  }
}
