module ietf-netconf-proxy {

  namespace "urn:ietf:params:xml:ns:yang:ietf-netconf-proxy";

  prefix np;

  organization
    "IETF NETCONF (Network Configuration) Working Group";

  contact
    "WG Web:   http://tools.ietf.org/wg/netconf
     WG List:  netconf@ietf.org

     WG Chair: Mehmet Ersue
               mehmet.ersue@nsn.com

     Editor:   zitao wang
                   wangzitao@huawei.com";

  description
    "NETCONF Protocol Data Types and Protocol Operations.

     Copyright (c) 2011 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This YANG module describe how to define a netconf proxy";

  revision 2017-03-09 {
    description
      "Initial revision";
    reference
      "draft-wang-netconf-proxy";
  }

  feature proxy {
    description
      "Netconf proxy";
  }

  container proxy {
   if-feature proxy;
   leaf proxy-name{
    type string;
    description
        "Proxy name";
   }
   list target-list {
    key "target-id";
        leaf target-id{
         type string;
         description
         "Target ID";
        }
        leaf protocol {
         type string;
         description
         "Support protocols";
        }
        leaf authentication {
         type string;
         description
         "Authentication";
        }
        description
        "List for target information";
   }
   description
   "Container for NETCONF Proxy";
  }

}
