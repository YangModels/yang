submodule ietf-snmp-ssh {

  belongs-to ietf-snmp {
    prefix snmp;
  }

  import ietf-inet-types {
    prefix inet;
  }

  include ietf-snmp-common;
  include ietf-snmp-engine;
  include ietf-snmp-target;

  organization
    "IETF NETMOD (NETCONF Data Modeling Language) Working Group";

  contact
    "WG Web:   <http://tools.ietf.org/wg/netmod/>
     WG List:  <mailto:netmod@ietf.org>

     WG Chair: David Kessens
               <mailto:david.kessens@nsn.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";

  description
    "This submodule contains a collection of YANG definitions for
     configuring the Secure Shell Transport Model (SSHTM)
     of SNMP.
     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  reference
    "RFC5592: Secure Shell Transport Model for the
              Simple Network Management Protocol (SNMP)";

  // RFC Ed.: update the date below with the date of RFC publication
  // and remove this note.

  revision 2013-11-05 {
    description
      "Initial revision.";
    reference
      "RFC XXXX: A YANG Data Model for SNMP Configuration";
  }

  feature sshtm {
    description
      "A server implements this feature if it supports the
      Secure Shell Transport Model for SNMP.";
    reference
      "RFC5592: Secure Shell Transport Model for the
                Simple Network Management Protocol (SNMP)";
  }

  augment /snmp:snmp/snmp:engine/snmp:listen {
    if-feature sshtm;
    list ssh {
      key "ip port";
      description
        "A list of IPv4 and IPv6 addresses and ports to which the
         engine listens for SNMP messages over SSH.";

      leaf ip {
        type inet:ip-address;
        description
          "The IPv4 or IPv6 address on which the engine listens
           for SNMP messages over SSH.";
      }
      leaf port {
        type inet:port-number;
        description
          "The TCP port on which the engine listens for SNMP
           messages over SSH.";
      }
    }
  }

  augment /snmp:snmp/snmp:target/snmp:transport {
    if-feature sshtm;
    case ssh {
      reference "SNMP-SSH-TM-MIB.snmpSSHDomain";
      container ssh {
        leaf ip {
          type inet:host;
          mandatory true;
          reference "SNMP-TARGET-MIB.snmpTargetAddrTAddress
                     SNMP-SSH-TM-MIB.SnmpSSHAddress";
        }
        leaf port {
          type inet:port-number;
          default 5161;
          reference "SNMP-TARGET-MIB.snmpTargetAddrTAddress
                     SNMP-SSH-TM-MIB.SnmpSSHAddress";
        }
        leaf username {
          type string;
          reference "SNMP-TARGET-MIB.snmpTargetAddrTAddress
                     SNMP-SSH-TM-MIB.SnmpSSHAddress";
        }
      }
    }
  }
}
