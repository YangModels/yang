module ietf-bfd-ip-sh-ext {
  yang-version 1.1;
  namespace "urn:ietf:params:xml:ns:yang:ietf-bfd-ip-sh-ext";

  prefix "bfd-ip-sh-ext";

  import ietf-bfd {
    prefix "bfd";
    reference
      "RFC 9314: A YANG Data Model for Bidirectional Forwarding
       Detection (BFD)";
  }

  import ietf-routing {
    prefix "rt";
    reference
      "RFC 8349: A YANG Data Model for Routing Management
       (NMDA version)";
  }

  import ietf-bfd-ip-sh {
    prefix "bfd-ip-sh";
    reference
      "RFC 9314: A YANG Data Model for Bidirectional Forwarding
       Detection (BFD)";
  }

  organization "IETF BFD Working Group";
  contact
    "WG Web:   <http://tools.ietf.org/wg/bfd>
     WG List:  <rtg-bfd@ietf.org>

     Editors:  Rajaguru Veluchamy (rvelucha@cisco.com)";

  description
    "This module contains the YANG definition for BFD IP single-hop
     as per RFC 5881 with some extended info.

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  reference
     "RFC 5881: Bidirectional Forwarding Detection (BFD)
      for IPv4 and IPv6 (Single Hop)
      RFC 9314: YANG Data Model for Bidirectional Forwarding
      Detection (BFD)";

  revision 2022-02-18 {
    description "Initial revision.";
    reference
       "RFC XXXX: A YANG data model for BFD IP single-hop extension";
  }

  /*
   * Augments
   */
  augment "/rt:routing/rt:control-plane-protocols/"
        + "rt:control-plane-protocol/bfd:bfd/bfd-ip-sh:ip-sh/"
        + "bfd-ip-sh:sessions/bfd-ip-sh:session" {
    description "BFD augmentation for IP single-hop-ext";
    leaf session-offloaded {
        type boolean;
        description
           "Indicates whether BFD session is running in hardware";
    }
  }
}
