module ietf-network-slice-service {
  yang-version 1.1;
  namespace
    "urn:ietf:params:xml:ns:yang:ietf-network-slice-service";
  prefix ietf-nss;

  import ietf-inet-types {
    prefix inet;
    reference
      "RFC 6991: Common YANG Types";
  }
  import ietf-yang-types {
    prefix yang;
    reference
      "RFC 6991: Common YANG Data Types";
  }
  import ietf-geo-location {
    prefix geo;
    reference
      "RFC 9179: A YANG Grouping for Geographic Locations";
  }
  import ietf-vpn-common {
    prefix vpn-common;
    reference
      "RFC 9181: A Common YANG Data Model for Layer 2 and Layer 3
                 VPNs";
  }
  import ietf-network {
    prefix nw;
    reference
      "RFC 8345: A YANG Data Model for Network Topologies";
  }
  import ietf-network-topology {
    prefix nt;
    reference
      "RFC 8345: A YANG Data Model for Network
                 Topologies, Section 6.2";
  }
  import ietf-ac-common {
    prefix ac-common;
    reference
      "RFC BBBB: A Common YANG Data Model for Attachment Circuits";
  }
  import ietf-ac-svc {
    prefix ac-svc;
    reference
      "RFC CCCC: YANG Data Models for Bearers and 'Attachment
                 Circuits'-as-a-Service (ACaaS)";
  }
  import ietf-te-types {
    prefix te-types;
    reference
      "RFC DDDD: Common YANG Types for Traffic Engineering";
  }
  import ietf-te-packet-types {
    prefix te-packet-types;
    reference
      "RFC DDDD: Common YANG Data Types for Traffic Engineering";
  }

  organization
    "IETF Traffic Engineering Architecture and Signaling (TEAS)
     Working Group";
  contact
    "WG Web:  <https://datatracker.ietf.org/wg/teas/>
     WG List:  <mailto:teas@ietf.org>

     Editor: Bo Wu
             <lana.wubo@huawei.com>
     Editor: Dhruv Dhody
             <dhruv.ietf@gmail.com>
     Editor: Reza Rokui
             <rrokui@ciena.com>
     Editor: Tarek Saad
             <tsaad@cisco.com>
     Editor: John Mullooly
             <jmullool@cisco.com>";
  description
    "This YANG module defines a service model for the RFC 9543
     Network Slice Service.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC AAAA; see the
     RFC itself for full legal notices.";

  revision 2024-08-28 {
    description
      "Initial revision.";
    reference
      "RFC AAAA: A YANG Data Model for the RFC 9543 Network Slice
       Service";
  }

  /* Identities */

  identity service-tag-type {
    description
      "Base identity of Network Slice Service tag type, which is
       used for management purposes, such as classification
       (e.g., customer names) and policy constraints
       (e.g., Layer 2 or Layer 3 technology realization).";
  }

  identity customer {
    base service-tag-type;
    description
      "The Network Slice Service customer name tag type,
       e.g., adding tags with 'customer name' when multiple actual
       customers use the same Network Slice Service.";
  }

  identity service {
    base service-tag-type;
    description
      "The Network Slice Service tag type, which can indicate the
       technical constraints used during service realization,
       for example, Layer 2 or Layer 3 technologies.";
  }

  identity opaque {
    base service-tag-type;
    description
      "An opaque type, which can be used for future use,
       such as filtering of services.";
  }

  identity attachment-circuit-tag-type {
    description
      "Base identity for the attachment circuit tag type.";
  }

  identity vlan-id {
    base attachment-circuit-tag-type;
    description
      "Identity for VLAN ID tag type, 802.1Q dot1Q.";
    reference
      "IEEE Std 802.1Q: IEEE Standard for Local and Metropolitan
                        Area Networks--Bridges and Bridged
                        Networks";
  }

  identity cvlan-id {
    base attachment-circuit-tag-type;
    description
      "Identity for C-VLAN ID tag type, 802.1ad QinQ VLAN IDs.";
    reference
      "IEEE Std 802.1ad: IEEE Standard for Local and Metropolitan
                         Area Networks---Virtual Bridged Local
                         Area Networks---Amendment 4: Provider
                         Bridges";
  }

  identity svlan-id {
    base attachment-circuit-tag-type;
    description
      "Identity for S-VLAN ID tag type, 802.1ad QinQ VLAN IDs.";
    reference
      "IEEE Std 802.1ad: IEEE Standard for Local and Metropolitan
                         Area Networks---Virtual Bridged Local
                         Area Networks---Amendment 4: Provider
                         Bridges";
  }

  identity ip-address-mask {
    base attachment-circuit-tag-type;
    description
      "Identity for IP address mask tag type.";
  }

  identity service-isolation-type {
    description
      "Base identity for Network Slice Service isolation type.";
  }

  identity traffic-isolation {
    base service-isolation-type;
    description
      "Specify the requirement for separating the traffic of the
       customer's Network Slice Service from other services,
       which may be provided by the service provider using VPN
       technologies, such as L3VPN, L2VPN, EVPN, etc.";
  }

  identity service-security-type {
    description
      "Base identity for Network Slice Service security type.";
  }

  identity authentication {
    base service-security-type;
    description
      "Indicates that the Slice Service requires authentication.";
  }

  identity integrity {
    base service-security-type;
    description
      "Indicates that the Slice Service requires data integrity.";
  }

  identity encryption {
    base service-security-type;
    description
      "Indicates that the Slice Service requires data encryption.";
  }

  identity point-to-point {
    base vpn-common:vpn-topology;
    description
      "Identity for point-to-point Network Slice
       Service connectivity.";
  }

  identity point-to-multipoint {
    base vpn-common:vpn-topology;
    description
      "Identity for point-to-multipoint Network Slice
       Service connectivity.";
  }

  identity multipoint-to-multipoint {
    base vpn-common:vpn-topology;
    description
      "Identity for multipoint-to-multipoint Network Slice
       Service connectivity.";
  }

  identity multipoint-to-point {
    base vpn-common:vpn-topology;
    description
      "Identity for multipoint-to-point Network Slice
       Service connectivity.";
  }

  identity sender-role {
    base vpn-common:role;
    description
      "Indicates that an SDP is acting as a sender.";
  }

  identity receiver-role {
    base vpn-common:role;
    description
      "Indicates that an SDP is acting as a receiver.";
  }

  identity service-slo-metric-type {
    description
      "Base identity for Network Slice Service SLO metric type.";
  }

  identity one-way-bandwidth {
    base service-slo-metric-type;
    description
      "SLO bandwidth metric. Minimum guaranteed bandwidth between
       two SDPs at any time and is measured unidirectionally.";
  }

  identity two-way-bandwidth {
    base service-slo-metric-type;
    description
      "SLO bandwidth metric. Minimum guaranteed bandwidth between
       two SDPs at any time.";
  }

  identity shared-bandwidth {
    base service-slo-metric-type;
    description
      "The shared SLO bandwidth bound. It is the limit on the
       bandwidth that can be shared amongst a group of
       connectivity constructs of a Slice Service.";
  }

  identity one-way-delay-maximum {
    base service-slo-metric-type;
    description
      "The SLO objective of this metric is the upper bound of network
       delay when transmitting between two SDPs.";
    reference
      "RFC 7679: A One-Way Delay Metric for IP Performance
                 Metrics (IPPM)";
  }

  identity one-way-delay-percentile {
    base service-slo-metric-type;
    description
      "The SLO objective of this metric is percentile objective of
       network delay when transmitting between two SDPs.
       The metric is defined in RFC7679.";
    reference
      "RFC 7679: A One-Way Delay Metric for IP Performance
                 Metrics (IPPM)";
  }

  identity two-way-delay-maximum {
    base service-slo-metric-type;
    description
      "SLO two-way delay is the upper bound of network delay when
       transmitting between two SDPs";
    reference
      "RFC 2681: A Round-trip Delay Metric for IPPM";
  }

  identity two-way-delay-percentile {
    base service-slo-metric-type;
    description
      "The SLO objective of this metric is the percentile
       objective of network delay when the traffic transmitting
       between two SDPs.";
    reference
      "RFC 2681: A Round-trip Delay Metric for IPPM";
  }

  identity one-way-delay-variation-maximum {
    base service-slo-metric-type;
    description
      "The SLO objective of this metric is maximum bound of the
       difference in the one-way delay between sequential packets
       between two SDPs.";
    reference
      "RFC 3393: IP Packet Delay Variation Metric for IP Performance
                 Metrics (IPPM)";
  }

  identity one-way-delay-variation-percentile {
    base service-slo-metric-type;
    description
      "The SLO objective of this metric is the percentile objective
       in the one-way delay between sequential packets between two
       SDPs.";
    reference
      "RFC 3393: IP Packet Delay Variation Metric for IP Performance
                 Metrics (IPPM)";
  }

  identity two-way-delay-variation-maximum {
    base service-slo-metric-type;
    description
      "SLO two-way delay variation is the difference in the
       round-trip delay between sequential packets between two
       SDPs.";
    reference
      "RFC 5481: Packet Delay Variation Applicability Statement";
  }

  identity two-way-delay-variation-percentile {
    base service-slo-metric-type;
    description
      "The SLO objective of this metric is the percentile objective
       in the round-trip delay between sequential packets between
       two SDPs.";
    reference
      "RFC 5481: Packet Delay Variation Applicability Statement";
  }

  identity one-way-packet-loss {
    base service-slo-metric-type;
    description
      "This metric type refers to the ratio of packets dropped
       to packets transmitted between two SDPs in one-way.";
    reference
      "RFC 7680: A One-Way Loss Metric for IP Performance
                 Metrics (IPPM)";
  }

  identity two-way-packet-loss {
    base service-slo-metric-type;
    description
      "This metric type refers to the ratio of packets dropped
       to packets transmitted between two SDPs in two-way.";
    reference
      "RFC 7680: A One-Way Loss Metric for IP Performance
                 Metrics (IPPM)";
  }

  identity availability-type {
    description
      "Base identity for availability.";
  }

  identity six-nines {
    base availability-type;
    description
      "Specifies the availability level: 99.9999%";
  }

  identity five-nines {
    base availability-type;
    description
      "Specifies the availability level: 99.999%";
  }

  identity four-nines {
    base availability-type;
    description
      "Specifies the availability level: 99.99%";
  }

  identity three-nines {
    base availability-type;
    description
      "Specifies the availability level: 99.9%";
  }

  identity two-nines {
    base availability-type;
    description
      "Specifies the availability level: 99%";
  }

  identity service-match-type {
    description
      "Base identity for Network Slice Service traffic
       match type.";
  }
  identity phy-interface {
    base service-match-type;
    description
      "Uses the physical interface as match criteria for
       Slice Service traffic.";
  }

  identity vlan {
    base service-match-type;
    description
      "Uses the VLAN ID as match criteria for the Slice Service
       traffic.";
  }

  identity label {
    base service-match-type;
    description
      "Uses the MPLS label as match criteria for the Slice Service
       traffic.";
  }

  identity source-ip-prefix {
    base service-match-type;
    description
      "Uses source IP prefix as match criteria for the Slice Service
       traffic. Examples of 'value' of this match type are
       '192.0.2.0/24' and '2001:db8::1/64'.";
  }

  identity destination-ip-prefix {
    base service-match-type;
    description
      "Uses destination IP prefix as match criteria for the Slice
       Service traffic. Examples of 'value' of this match type are
       '203.0.113.1/32' and '2001:db8::2/128'.";
  }

  identity dscp {
    base service-match-type;
    description
      "Uses DSCP field in the IP packet header as match criteria
       for the Slice Service traffic.";
  }

  identity acl {
    base service-match-type;
    description
      "Uses Access Control List (ACL) as match criteria
       for the Slice Service traffic.";
    reference
      "RFC 8519: YANG Data Model for Network Access Control
                 Lists (ACLs)";
  }

  identity any {
    base service-match-type;
    description
      "Matches any Slice Service traffic.";
  }

  identity slo-sle-policy-override {
    description
      "Base identity for SLO/SLE policy override options.";
  }

  identity full-override {
    base slo-sle-policy-override;
    description
      "The SLO/SLE policy defined at the child level overrides a
       parent SLO/SLE policy, which means that no SLO/SLEs are
       inherited from parent if a child SLO/SLE policy exists.";
  }

  identity partial-override {
    base slo-sle-policy-override;
    description
      "The SLO/SLE policy defined at the child level updates the
       parent SLO/SLE policy. For example, if a specific SLO is
       defined at the child level, that specific SLO overrides
       the one inherited from a parent SLO/SLE policy, while all
       other SLOs in the parent SLO-SLE policy still apply.";
  }

  /* Typedef */

  typedef percentage {
    type decimal64 {
      fraction-digits 5;
      range "0..100";
    }
    description
      "Percentage to 5 decimal places.";
  }

  typedef percentile {
    type decimal64 {
      fraction-digits 3;
      range "0..100";
    }
    description
      "The percentile is a value between 0 and 100
       to 3 decimal places, e.g., 10.000, 99.900,99.990, etc.
       For example, for a given one-way delay measurement,
       if the percentile is set to 95.000 and the 95th percentile
       one-way delay is 2 milliseconds, then the 95 percent of
       the sample value is less than or equal to 2 milliseconds.";
  }

  typedef slice-template-ref {
    type leafref {
      path "/ietf-nss:network-slice-services"
         + "/ietf-nss:slo-sle-templates"
         + "/ietf-nss:slo-sle-template"
         + "/ietf-nss:id";
    }
    description
      "This type is used by data models that need to reference
       Network Slice templates.";
  }

  typedef slice-service-ref {
    type leafref {
      path
        "/ietf-nss:network-slice-services/ietf-nss:slice-service"
      + "/ietf-nss:id";
    }
    description
      "Defines a reference to a slice service that can be used
       by other modules.";
  }

  /* Groupings */

  grouping service-slos {
    description
      "A reusable grouping for directly measurable objectives of
       a Slice Service.";
    container slo-policy {
      description
        "Contains the SLO policy.";
      list metric-bound {
        key "metric-type";
        description
          "List of Slice Service metric bounds.";
        leaf metric-type {
          type identityref {
            base service-slo-metric-type;
          }
          description
            "Identifies SLO metric type of the Slice Service.";
        }
        leaf metric-unit {
          type string;
          mandatory true;
          description
            "The metric unit of the parameter. For example,
             for time units, where the options are hours, minutes,
             seconds, milliseconds, microseconds, and nanoseconds;
             for bandwidth units, where the options are bps, Kbps,
             Mbps, Gbps; for the packet loss rate unit,
             the options can be a percentage.";
        }
        leaf value-description {
          type string;
          description
            "The description of the provided value.";
        }
        leaf percentile-value {
          type percentile;
          description
            "The percentile value of the metric type.";
        }
        leaf bound {
          type uint64;
          description
            "The bound on the Slice Service connection metric.
             When set to zero, this indicates an unbounded
             upper limit for the specific metric-type.";
        }
      }
      leaf availability {
        type identityref {
          base availability-type;
        }
        description
          "Service availability level";
      }
      leaf mtu {
        type uint32;
        units "bytes";
        description
          "Specifies the maximum length of Layer 2 data
           packets of the Slice Service.
           If the customer sends packets that are longer than the
           requested service MTU, the network may discard them
           (or for IPv4, fragment them).
           This service MTU takes precedence over the MTUs of
           all attachment circuits (ACs). The value needs to be
           less than or equal to the minimum MTU value of
           all ACs in the SDPs.";
      }
    }
  }

  grouping service-sles {
    description
      "A reusable grouping for indirectly measurable objectives of
       a Slice Service.";
    container sle-policy {
      description
        "Contains the SLE policy.";
      leaf-list security {
        type identityref {
          base service-security-type;
        }
        description
          "The security functions that the customer requests
           the operator to apply to traffic between the two SDPs.";
      }
      leaf-list isolation {
        type identityref {
          base service-isolation-type;
        }
        description
          "The Slice Service isolation requirement.";
      }
      leaf max-occupancy-level {
        type uint8 {
          range "1..100";
        }
        description
          "The maximal occupancy level specifies the number of flows
           to be admitted and optionally a maximum number of
           countable resource units (e.g., IP or MAC addresses)
           a Network Slice Service can consume.";
      }
      container path-constraints {
        description
          "Container for the policy of path constraints
           applicable to the Slice Service.";
        container service-functions {
          description
            "Container for the policy of service function
             applicable to the Slice Service.";
        }
        container diversity {
          description
            "Container for the policy of disjointness
             applicable to the Slice Service.";
          leaf diversity-type {
            type te-types:te-path-disjointness;
            description
              "The type of disjointness on Slice Service, i.e.,
               across all connectivity constructs.";
          }
        }
      }
    }
  }

  grouping slice-service-template {
    description
      "A reusable grouping for Slice Service templates.";
    container slo-sle-templates {
      description
        "Contains a set of Slice Service templates.";
      list slo-sle-template {
        key "id";
        description
          "List for SLO and SLE template identifiers.";
        leaf id {
          type string;
          description
            "Identification of the Service Level Objective (SLO)
             and Service Level Expectation (SLE) template to be used.
             Local administration meaning.";
        }
        leaf description {
          type string;
          description
            "Describes the SLO and SLE policy template.";
        }
        leaf template-ref {
          type slice-template-ref;
          description
            "The reference to a standard template. When set it
              indicates the base template over which further
              SLO/SLE policy changes are made.";
        }
        uses service-slos;
        uses service-sles;
      }
    }
  }

  grouping service-slo-sle-policy {
    description
      "Slice service policy grouping.";
    choice slo-sle-policy {
      description
        "Choice for SLO and SLE policy template.
         Can be standard template or customized template.";
      case standard {
        description
          "Standard SLO template.";
        leaf slo-sle-template {
          type slice-template-ref;
          description
            "Standard SLO and SLE template to be used.";
        }
      }
      case custom {
        description
          "Customized SLO and SLE template.";
        container service-slo-sle-policy {
          description
            "Contains the SLO and SLE policy.";
          leaf description {
            type string;
            description
              "Describes the SLO and SLE policy.";
          }
          uses service-slos;
          uses service-sles;
        }
      }
    }
  }

  grouping service-qos {
    description
      "Grouping for the Slice Service QoS policy.";
    container incoming-qos-policy {
      description
        "The QoS policy imposed on ingress direction of the traffic,
         from the customer network or from another provider's
         network.";
      leaf qos-policy-name {
        type string;
        description
          "The name of the QoS policy that is applied to the
           attachment circuit. The name can reference a QoS
           profile that is pre-provisioned on the device.";
      }
      container rate-limits {
        description
          "Container for the asymmetric traffic control.";
        uses ac-common:bandwidth-parameters;
        container classes {
          description
            "Container for service class bandwidth control.";
          list cos {
            key "cos-id";
            description
              "List of Class of Services.";
            leaf cos-id {
              type uint8;
              description
                "Identifier of the CoS, indicated by
                 a Differentiated Services Code Point
                 (DSCP) or a CE-CLAN CoS (802.1p)
                 value in the service frame.";
              reference
                "IEEE Std 802.1Q: Bridges and Bridged
                                  Networks";
            }
            uses ac-common:bandwidth-parameters;
          }
        }
      }
    }
    container outgoing-qos-policy {
      description
        "The QoS policy imposed on egress direction of the traffic,
         towards the customer network or towards another
         provider's network.";
      leaf qos-policy-name {
        type string;
        description
          "The name of the QoS policy that is applied to the
           attachment circuit. The name can reference a QoS
           profile that is pre-provisioned on the device.";
      }
      container rate-limits {
        description
          "The rate-limit imposed on outgoing traffic.";
        uses ac-common:bandwidth-parameters;
        container classes {
          description
            "Container for classes.";
          list cos {
            key "cos-id";
            description
              "List of Class of Services.";
            leaf cos-id {
              type uint8;
              description
                "Identifier of the CoS, indicated by
                 a Differentiated Services Code Point
                 (DSCP) or a CE-CLAN CoS (802.1p)
                 value in the service frame.";
              reference
                "IEEE Std 802.1Q: Bridges and Bridged
                                  Networks";
            }
            uses ac-common:bandwidth-parameters;
          }
        }
      }
    }
  }

  grouping service-slo-sle-policy-override {
    description
      "Slice Service policy override grouping.";
    leaf service-slo-sle-policy-override {
      type identityref {
        base slo-sle-policy-override;
      }
      description
        "SLO/SLE policy override option.";
    }
  }

  grouping connectivity-construct-monitoring-metrics {
    description
      "Grouping for connectivity construct monitoring metrics.";
    uses
      te-packet-types:one-way-performance-metrics-gauge-packet;
    uses
      te-packet-types:two-way-performance-metrics-gauge-packet;
  }
  /* Main Network Slice Services Container */

  container network-slice-services {
    description
      "Contains a list of Network Slice Services";
    uses slice-service-template;
    list slice-service {
      key "id";
      description
        "A Slice Service is identified by a service id.";
      leaf id {
        type string;
        description
          "A unique Slice Service identifier within an NSC.";
      }
      leaf description {
        type string;
        description
          "Textual description of the Slice Service.";
      }
      container service-tags {
        description
          "Container for a list of service tags for management
           purposes, such as policy constraints
           (e.g., Layer 2 or Layer 3 technology realization),
           classification (e.g., customer names, opaque values).";
        list tag-type {
          key "tag-type";
          description
            "The service tag list.";
          leaf tag-type {
            type identityref {
              base service-tag-type;
            }
            description
              "Slice Service tag type, e.g., realization technology
               constraints, customer name, or other customer-defined
               opaque types.";
          }
          leaf-list value {
            type string;
            description
              "The tag values, e.g., 5G customer names when multiple
               customers share the same Slice Service in 5G scenario,
               or Slice realization technology (such as Layer 2 or
               Layer 3).";
          }
        }
      }
      uses service-slo-sle-policy;
      leaf compute-only {
        type empty;
        description
          "When present, this is a feasibility check. That is, no
           resources are reserved in the network.";
      }
      uses ac-common:service-status;
      container sdps {
        description
          "Slice Service SDPs.";
        list sdp {
          key "id";
          min-elements 2;
          description
            "List of SDPs in this Slice Service.";
          leaf id {
            type string;
            description
              "The unique identifier of the SDP within the scope of
               an NSC.";
          }
          leaf description {
            type string;
            description
              "Provides a description of the SDP.";
          }
          uses geo:geo-location;
          leaf node-id {
            type string;
            description
              "A unique identifier of an edge node of the SDP
               within the scope of the NSC.";
          }
          leaf-list sdp-ip-address {
            type inet:ip-address;
            description
              "IPv4 or IPv6 address of the SDP.";
          }
          leaf tp-ref {
            type leafref {
              path
                "/nw:networks/nw:network[nw:network-id="
              + "current()/../../../custom-topology/network-ref]/"
              + "nw:node/nt:termination-point/nt:tp-id";
            }
            description
              "A reference to Termination Point (TP) in the custom
               topology";
            reference
              "RFC 8345: A YANG Data Model for Network Topologies";
          }
          container service-match-criteria {
            description
              "Describes the Slice Service match criteria.";
            list match-criterion {
              key "index";
              description
                "List of the Slice Service traffic match criteria.";
              leaf index {
                type uint32;
                description
                  "The identifier of a match criteria.";
              }
              list match-type {
                key "type";
                description
                  "List of the Slice Service traffic match types.";
                leaf type {
                  type identityref {
                    base service-match-type;
                  }
                  mandatory true;
                  description
                    "Indicates the match type of the entry in the
                     list of the Slice Service match criteria.";
                }
                leaf-list value {
                  type string;
                  description
                    "Provides a value for the Slice Service match
                     criteria, e.g., IP prefix, VLAN ID, or
                     ACL name.";
                }
              }
              leaf target-connection-group-id {
                type leafref {
                  path
                    "../../../../../ietf-nss:connection-groups"
                  + "/ietf-nss:connection-group"
                  + "/ietf-nss:id";
                }
                mandatory true;
                description
                  "Reference to the Slice Service connection group.";
              }
              leaf connection-group-sdp-role {
                type identityref {
                  base vpn-common:role;
                }
                default "vpn-common:any-to-any-role";
                description
                  "Specifies the role of SDP in the connection group
                   When the service connection type is MP2MP,
                   such as hub and spoke service connection type.
                   In addition, this helps to create connectivity
                   construct automatically, rather than explicitly
                   specifying each one.";
              }
              leaf target-connectivity-construct-id {
                type leafref {
                  path
                    "../../../../../ietf-nss:connection-groups"
                  + "/ietf-nss:connection-group[ietf-nss:id="
                  + "current()/../target-connection-group-id]"
                  + "/ietf-nss:connectivity-construct/ietf-nss:id";
                }
                description
                  "Reference to a Network Slice connection
                   construct.";
              }
            }
          }
          uses service-qos;
          container sdp-peering {
            description
              "Describes SDP peering attributes.";
            leaf-list peer-sap-id {
              type string;
              description
                "Indicates the reference to the remote endpoints of
                 the attachment circuits. This information can be
                 used for correlation purposes, such as identifying
                 SAPs of provider equipments when requesting
                 a service with CE based SDP attributes.";
              reference
                "RFC 9408: A YANG Network Data Model for Service
                 Attachment Points (SAPs)";
            }
            container protocols {
              description
                "Serves as an augmentation target.
                 Protocols can be augmented into this container,
                 e.g., BGP, static routing.";
            }
          }
          leaf-list ac-svc-ref {
            type ac-svc:attachment-circuit-reference;
            description
              "A reference to the ACs that have been created before
               the slice creation.";
            reference
              "RFC CCCC: YANG Data Models for Bearers and
                'Attachment Circuits'-as-a-Service (ACaaS)";
          }
          leaf ce-mode {
            type boolean;
            description
              "Indicates that SDP is on the CE.";
          }
          container attachment-circuits {
            description
              "List of attachment circuits.";
            list attachment-circuit {
              key "id";
              description
                "The Network Slice Service SDP attachment circuit
                 related parameters.";
              leaf id {
                type string;
                description
                  "The identifier of attachment circuit.";
              }
              leaf description {
                type string;
                description
                  "The attachment circuit's description.";
              }
              leaf ac-svc-ref {
                type ac-svc:attachment-circuit-reference;
                description
                  "A reference to the AC service that has been
                   created before the slice creation.";
                reference
                  "RFC CCCC: YANG Data Models for Bearers and
                    'Attachment Circuits'-as-a-Service (ACaaS)";
              }
              leaf ac-node-id {
                type string;
                description
                  "The attachment circuit node ID in the case of
                   multi-homing.";
              }
              leaf ac-tp-id {
                type string;
                description
                  "The termination port ID of the
                   attachment circuit.";
              }
              leaf ac-ipv4-address {
                type inet:ipv4-address;
                description
                  "The IPv4 address of the AC.";
              }
              leaf ac-ipv4-prefix-length {
                type uint8;
                description
                  "The IPv4 subnet prefix length expressed in bits.";
              }
              leaf ac-ipv6-address {
                type inet:ipv6-address;
                description
                  "The IPv6 address of the AC.";
              }
              leaf ac-ipv6-prefix-length {
                type uint8;
                description
                  "The IPv6 subnet prefix length expressed in bits.";
              }
              leaf mtu {
                type uint32;
                units "bytes";
                description
                  "Maximum size of the Slice Service Layer 2 data
                   packet that can traverse an SDP.";
              }
              container ac-tags {
                description
                  "Container for the attachment circuit tags.";
                list ac-tag {
                  key "tag-type";
                  description
                    "The attachment circuit tag list.";
                  leaf tag-type {
                    type identityref {
                      base attachment-circuit-tag-type;
                    }
                    description
                      "The attachment circuit tag type.";
                  }
                  leaf-list value {
                    type string;
                    description
                      "The attachment circuit tag values.
                       For example, the tag may indicate
                       multiple VLAN identifiers.";
                  }
                }
              }
              uses service-qos;
              container sdp-peering {
                description
                  "Describes SDP peering attributes.";
                leaf peer-sap-id {
                  type string;
                  description
                    "Indicates a reference to the remote endpoints
                     of an attachment circuit. This information can
                     be used for correlation purposes, such as
                     identifying a service attachment point (SAP)
                     of a provider equipment when requesting a
                     service with CE based SDP attributes.";
                  reference
                    "RFC 9408: A YANG Network Data Model for
                               Service Attachment Points (SAPs)";
                }
                container protocols {
                  description
                    "Serves as an augmentation target.
                     Protocols can be augmented into this container,
                     e.g., BGP or static routing.";
                }
              }
              uses ac-common:service-status;
            }
          }
          uses ac-common:service-status;
          container sdp-monitoring {
            config false;
            description
              "Container for SDP monitoring metrics.";
            leaf incoming-bw-value {
              type yang:gauge64;
              units "bps";
              description
                "Indicates the absolute value of the incoming
                 bandwidth at an SDP from the customer network or
                 from another provider's network.";
            }
            leaf incoming-bw-percent {
              type percentage;
              units "percent";
              description
                "Indicates a percentage of the incoming bandwidth
                 at an SDP from the customer network or
                 from another provider's network.";
            }
            leaf outgoing-bw-value {
              type yang:gauge64;
              units "bps";
              description
                "Indicates the absolute value of the outgoing
                 bandwidth at an SDP towards the customer network or
                 towards another provider's network.";
            }
            leaf outgoing-bw-percent {
              type percentage;
              units "percent";
              description
                "Indicates a percentage of the outgoing bandwidth
                 at an SDP towards the customer network or towards
                 another provider's network.";
            }
          }
        }
      }
      container connection-groups {
        description
          "Contains connection groups.";
        list connection-group {
          key "id";
          description
            "List of connection groups.";
          leaf id {
            type string;
            description
              "The connection group identifier.";
          }
          leaf connectivity-type {
            type identityref {
              base vpn-common:vpn-topology;
            }
            default "vpn-common:any-to-any";
            description
              "Connection group connectivity type.";
          }
          uses service-slo-sle-policy;
          /* Per connection group SLO/SLE policy
           * overrides the per Slice SLO/SLE policy.
           */
          uses service-slo-sle-policy-override;
          list connectivity-construct {
            key "id";
            description
              "List of connectivity constructs.";
            leaf id {
              type string;
              description
                "The connectivity construct identifier.";
            }
            choice type {
              default "p2p";
              description
                "Choice for connectivity construct type.";
              case p2p {
                description
                  "P2P connectivity construct.";
                leaf p2p-sender-sdp {
                  type leafref {
                    path "../../../../sdps/sdp/id";
                  }
                  description
                    "Reference to a sender SDP.";
                }
                leaf p2p-receiver-sdp {
                  type leafref {
                    path "../../../../sdps/sdp/id";
                  }
                  description
                    "Reference to a receiver SDP.";
                }
              }
              case p2mp {
                description
                  "P2MP connectivity construct.";
                leaf p2mp-sender-sdp {
                  type leafref {
                    path "../../../../sdps/sdp/id";
                  }
                  description
                    "Reference to a sender SDP.";
                }
                leaf-list p2mp-receiver-sdp {
                  type leafref {
                    path "../../../../sdps/sdp/id";
                  }
                  description
                    "Reference to a receiver SDP.";
                }
              }
              case a2a {
                description
                  "A2A connectivity construct.";
                list a2a-sdp {
                  key "sdp-id";
                  description
                    "List of included A2A SDPs.";
                  leaf sdp-id {
                    type leafref {
                      path "../../../../../sdps/sdp/id";
                    }
                    description
                      "Reference to an SDP.";
                  }
                  uses service-slo-sle-policy;
                }
              }
            }
            uses service-slo-sle-policy;
            /* Per connectivity construct SLO/SLE policy
             * overrides the per slice SLO/SLE policy.
             */
            uses service-slo-sle-policy-override;
            uses ac-common:service-status;
            container connectivity-construct-monitoring {
              config false;
              description
                "SLO status per connectivity construct.";
              uses connectivity-construct-monitoring-metrics;
            }
          }
          container connection-group-monitoring {
            config false;
            description
              "SLO status per connection group.";
            uses connectivity-construct-monitoring-metrics;
          }
        }
      }
      container custom-topology {
        description
          "Serves as an augmentation target.
           Container for custom topology, which is indicated by the
           referenced topology predefined, e.g., an abstract RFC8345
           topology.";
        uses nw:network-ref;
      }
    }
  }
}
