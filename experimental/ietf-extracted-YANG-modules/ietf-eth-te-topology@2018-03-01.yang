module ietf-eth-te-topology {

        namespace "urn:ietf:params:xml:ns:yang:ietf-eth-te-topology";

        prefix "ethtetopo";

        import ietf-network {
                prefix "nd";
        }

        import ietf-network-topology {
                prefix "lnk";
        }

        import ietf-te-topology {
                prefix "tet";
        }

        import ietf-yang-types {
                prefix "yang";
        }

        import ietf-eth-tran-types {
                prefix "etht-types";
        }
        organization
                "Internet Engineering Task Force (IETF) CCAMP WG";
  contact
    "
      WG List: <mailto:ccamp@ietf.org>

      ID-draft editor:
        Haomian Zheng (zhenghaomian@huawei.com);
        Italo Busi (italo.busi@huawei.com);
        Aihua Guo (aihuaguo@huawei.com);
        Yunbin Xu (xuyunbin@ritt.cn);
        Yang Zhao (zhaoyangyjy@chinamobile.com);
        Xufeng Liu (Xufeng_Liu@jabil.com);
        Giuseppe Fioccola (giuseppe.fioccola@telecomitalia.it);
    ";

        description
                "This module defines a YANG data model for describing
                layer-2 Ethernet transport topologies.";

        revision 2018-03-01 {
                description
                        "Initial revision";
                reference
                        "draft-zheng-ccamp-client-topo-yang";
        }

        /*
        Groupings
        */

        grouping eth-tran-topology-type {
                description
                        "Identifies the Ethernet Transport topology type";

                container eth-tran-topology {
                        presence "indicates a topology type of Ethernet
                                                                Transport Network.";
                        description "Eth transport topology type";
                }
        }

        grouping eth-link-te-attributes {
                description "Ethernet TE link attributes";

                leaf max-bandwidth {
                        type uint64{
                                range "0..10000000000";
                        }
                        units "Kbps";
                        description
                                "Maximum bandwith value expressed in kilobits per second";
                }

                leaf available-bandwidth {
                        type uint64{
                                range "0..10000000000";
                        }
                        units "Kbps";
                        description
                                "Available bandwith value expressed in kilobits per second";
                }

                leaf available-vlan-range {
                        type etht-types:vid-range-type;
                        description
                                "The range of the VLAN values that are available.";
                }
        }

        grouping ltp-bandwidth-profiles {
                description
                        "A grouping which represents the bandwidt profile(s) for the ETH LTP.";

                choice direction {
                        description
                                "Whether the bandwidth profiles are symmetrical or
                                 asymmetrical";
                        case symmetrical {
                                description
                                        "The same bandwidth profile is used to describe the ingress
                                        and the egress bandwidth profile.";

                                container ingress-egress-bandwidth-profile {
                                        description
                                                "The bandwith profile used in the ingress and egress direction.";
                                        uses etht-types:etht-bandwidth-profiles;
                                }
                        }
                        case asymmetrical {
                                description
                                        "Different ingress and egress bandwidth profiles
                                        can be specified.";
                                container ingress-bandwidth-profile {
                                        description
                                                "The bandwidth profile used in the ingress direction.";
                                        uses etht-types:etht-bandwidth-profiles;
                                }
                                container egress-bandwidth-profile {
                                        description
                                                "The bandwidth profile used in the egress direction.";
                                        uses etht-types:etht-bandwidth-profiles;
                                }
                        }
                }
        }

        grouping eth-ltp-attributes {
                description
                        "Ethernet transport link termination point attributes";

                /*
                        Open Issue: should we remove this attribute (duplicates with I2RS L2 attributes)?
                */
                leaf ltp-mac-address {
                        type yang:mac-address;
                        description "the MAC address of the LTP.";
                }
                /*
                        Open Issue: should we remove this attribute (duplicates with I2RS L2 attributes)?
                */
                leaf port-vlan-id {
                        type etht-types:vlanid;
                        description "the port VLAN ID of the LTP.";
                }
                /*
                        Open Issue: should we remove this attribute (duplicates with I2RS L2 attributes)?
                */
                leaf maximum-frame-size {
                        type uint16 {
                                range "64 .. 65535";
                        }
                        description
                                "Maximum frame size";
                }
                uses ltp-bandwidth-profiles;
        }

        grouping svc-vlan-classification {
                description
                        "Grouping defining the capabilities for VLAN classification.";

                leaf-list supported-tag-types {
                        type etht-types:eth-tag-classify;
                        description
                                "List of VLAN tag types that can be used for the VLAN classification.
                                In case VLAN classification is not supported, the list is empty.";
                }
                leaf vlan-bundling {
                        type boolean;
                        description
                                "In case VLAN classification is supported, indicates whether VLAN bundling classification is also supported.";
                }
                leaf vlan-range {
                        type etht-types:vid-range-type;
                        description
                                "In case VLAN classification is supported, indicates the of available VLAN ID values.";
                }
        }

        grouping svc-vlan-push {
                description
                        "Grouping defining the capabilities for VLAN push or swap operations.";

                leaf-list supported-tag-types {
                        type etht-types:eth-tag-type;
                        description
                                "List of VLAN tag types that can be used to push or swap a VLAN tag.
                                In case VLAN push/swap is not supported, the list is empty.";
                }
                leaf vlan-range {
                        type etht-types:vid-range-type;
                        description
                                "In case VLAN push/swap operation is supported, the range of available VLAN ID values.";
                }
        }

        grouping eth-ltp-svc-attributes {
                description
                        "Ethernet link termination point (LTP) service attributes.";

                leaf client-facing {
                        type boolean;
                        description
                                "indicates whether this LTP is a client-facing ltp.";
                }

                container supported-classification {
                        description
                                "Service classification capabilities supported by the ETH LTP.";

                        leaf port-classification {
                                type boolean;
                                description
                                        "Indicates that the ETH LTP support port-based service classification.";
                        }
                        container vlan-classification {
                                description
                                        "Service classification capabilities based on the VLAN tag(s)
                                        supported by the ETH LTP.";

                                leaf vlan-tag-classification {
                                        type boolean;
                                        description
                                                "Indicates that the ETH LTP supports VLAN service classification.";
                                }
                                container outer-tag {
                                        description
                                                "Service classification capabilities based on the outer VLAN tag,
                                                supported by the ETH LTP.";
                                        uses svc-vlan-classification;
                                }
                                container second-tag {
                                        description
                                                "Service classification capabilities based on the second VLAN tag,
                                                supported by the ETH LTP.";
                                        /*
                                                Open issue: indicates that second-tag-classification can be True only if
                                                outer-tag-classification is also True.
                                        */
                                        leaf second-tag-classification {
                                                type boolean;
                                                description
                                                        "Indicates that the ETH LTP support  VLAN service classification
                                                        based on the second VLAN tag.";
                                        }
                                        uses svc-vlan-classification;
                                }
                        }
                }

                container supported-vlan-operations {
                description
                                        "Description.";
                        leaf asymmetrical-operations {
                                type boolean;
                                description
                                        "Indicates whether the ETH LTP supports also asymmetrical VLAN operations.
                                        It is assumed that symmetrical VLAN operations are alwyas supported.";
                        }
                        leaf transparent-vlan-operations {
                                type boolean;
                                description
                                        "Indicates that the ETH LTP supports transparent operations.";
                        }
                        container vlan-pop {
                                description
                                        "Indicates VLAN pop or swap operations capabilities.";

                                leaf vlan-pop-operations {
                                        type boolean;
                                        description
                                                "Indicates that the ETH LTP supports VLAN pop or swap operations.";
                                }
                                leaf max-pop-tags {
                                        type uint8 {
                                                range "1..2";
                                        }
                                        description
                                                "Indicates the maximum number of tags that can be popped/swapped.";
                                }
                        }
                        container vlan-push {
                                description
                                        "Indicates VLAN push or swap operations capabilities.";

                                leaf vlan-push-operation {
                                        type boolean;
                                        description
                                                "Indicates that the ETH LTP supports VLAN push or swap operations.";
                                }
                                container outer-tag {
                                        description
                                                "Indicates the supported VLAN operation capabilities on the outer VLAN tag.";
                                        uses svc-vlan-push;
                                }
                                container second-tag {
                                        description
                                                "Indicates the supported VLAN operation capabilities on the second VLAN tag.";

                                        leaf push-second-tag {
                                                type boolean;
                                                description
                                                        "Indicates that the ETH LTP supports VLAN push or swap operations
                                                        for the second VLAN tag.";
                                        }
                                        uses svc-vlan-push;
                                }
                        }
                }
        }

        /*
        Data nodes
        */

        augment "/nd:networks/nd:network/nd:network-types/tet:te-topology" {
                description
                        "Augment network types to include ETH transport newtork";

                uses eth-tran-topology-type;
        }

        augment "/nd:networks/nd:network/lnk:link/tet:te/tet:te-link-attributes" {
                when "../../../nd:network-types/tet:te-topology/eth-tran-topology" {
                        description
                                "Augment only for ETH transport network.";
                }
                description
                        "Augment ETH transport link config attributes";

                uses eth-link-te-attributes;
        }

        augment "/nd:networks/nd:network/nd:node/lnk:termination-point" {
                when "../../nd:network-types/tet:te-topology/eth-tran-topology" {
                        description
                                "Augment only for ETH transport network";
                }
                description
                        "Augment ETH LTP attributes";

                uses eth-ltp-attributes;
                container svc {
                        presence "client-facing LTP.";

                        description
                                "ETH LTP Service attributes.";
                        uses eth-ltp-svc-attributes;
                }
        }
}
