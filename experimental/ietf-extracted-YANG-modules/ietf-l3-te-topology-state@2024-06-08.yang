module ietf-l3-te-topology-state {
  yang-version 1.1;
  namespace "urn:ietf:params:xml:ns:yang:ietf-l3-te-topology-state";
  prefix "l3tet-s";

  import ietf-l3-te-topology {
    prefix "l3tet";
    reference
      "RFC XXXX: YANG Data Models for Layer 3 and Packet TE Topologies";
  }
  import ietf-network-state {
    prefix "nw-s";
    reference "RFC 8345: A YANG Data Model for Network Topologies";
  }
  import ietf-network-topology-state {
    prefix "nt-s";
    reference "RFC 8345: A YANG Data Model for Network Topologies";
  }
  import ietf-l3-unicast-topology-state {
    prefix "l3t-s";

    reference "RFC 8346: A YANG Data Model for Layer 3 Topologies";
  }

  organization
    "IETF Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Igor Bryskin
               <mailto:Igor.Bryskin@huawei.com>

     Editor:   Vishnu Pavan Beeram
               <mailto:vbeeram@juniper.net>

     Editor:   Tarek Saad
               <mailto:tsaad@cisco.com>

     Editor:   Himanshu Shah
               <mailto:hshah@ciena.com>

     Editor:   Oscar Gonzalez De Dios
               <mailto:oscar.gonzalezdedios@telefonica.com>";

  description
    "YANG data model for representing operational state information
     of Layer 3 TE Topologies, when NMDA is not supported.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2024-06-08 {

    description
      "Initial revision";
    reference "RFC XXXX: YANG Data Models for Layer 3 and Packet TE Topologies";
  }

  augment "/nw-s:networks/nw-s:network/nw-s:network-types/"
        + "l3t-s:l3-unicast-topology" {
    description
      "Defines the L3 TE topology type.";
    uses l3tet:l3-te-topology-type;
  }

  augment "/nw-s:networks/nw-s:network/"
        + "l3t-s:l3-topology-attributes" {
    when "../nw-s:network-types/l3t-s:l3-unicast-topology/"
       + "l3tet-s:l3-te" {
      description
        "Augment only for L3 TE topology";
    }
    description
      "Augment topology configuration";
    uses l3tet:l3-te-topology-attributes;
  }

  augment "/nw-s:networks/nw-s:network/nw-s:node/"
        + "l3t-s:l3-node-attributes" {
    when "../../nw-s:network-types/l3t-s:l3-unicast-topology/"
       + "l3tet-s:l3-te" {
      description
        "Augment only for L3 TE topology";
    }
    description
      "Augment node configuration";
    uses l3tet:l3-te-node-attributes;
  }

  augment "/nw-s:networks/nw-s:network/nw-s:node/"
        + "nt-s:termination-point/"
        + "l3t-s:l3-termination-point-attributes" {
    when "../../../nw-s:network-types/l3t-s:l3-unicast-topology/"
       + "l3tet-s:l3-te" {
      description
        "Augment only for L3 TE topology";
    }
    description
      "Augment termination point configuration";
    uses l3tet:l3-te-tp-attributes;
  }

  augment "/nw-s:networks/nw-s:network/nt-s:link/"
        + "l3t-s:l3-link-attributes" {
    when "../../nw-s:network-types/l3t-s:l3-unicast-topology/"
       + "l3tet-s:l3-te" {
      description
        "Augment only for L3 TE topology";
    }
    description
      "Augment link configuration";
    uses l3tet:l3-te-link-attributes;
  }
}
