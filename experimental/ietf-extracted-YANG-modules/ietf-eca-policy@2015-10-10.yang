module ietf-eca-policy { 
  namespace "urn:ietf:params:xml:ns:yang:ietf-eca-policy"; 
  // replace with IANA namespace when assigned 
  prefix policy; 

  import ietf-yang-types { 
    prefix yang; 
  } 

  organization "IETF"; 
  contact 
    "Editor: Maoke Chen"; 

  description 
    "This YANG module defines a component that describing 
      the generic ECA policy data model refining from SGPIM and 
      EPRIM. 

     Terms and Acronyms 
     "; 

  revision 2015-08-25 { 
    reference ""; 
  } 

  container supa-policy{ 
    description 
      "This defines a Generic ECA policy data model "; 
    leaf supa-policy-name { 
      type string; 
      description  
        "The name of the policy";  
    } 
    leaf supa-policy-priority { 
      type uint8; 
      description 
        "The priority of the defined policy"; 
    } 
    container supa-policy-validity-period { 
      description 
            "The valid time of the policy. E.g., the policy will 
            be valid 9am-9am daily"; 
      leaf start { 
        type yang:date-and-time; 
        description "date and time to start the policy"; 
      }  
      leaf end { 
        type yang:date-and-time; 
        description "date and time to end the policy"; 
      } 
      leaf duration { 
        type uint32; 
        description "duration of the policy"; 
      } 
      leaf periodicity { 
        type enumeration { 
          enum daily {  
            value 0; 
            description "The policy is repeated daily"; 
          } 
          enum monthly {   
            value 1; 
            description "The policy is repeated monthly"; 
          } 
        } 
        description "How the policy is repeated"; 
      } 
    } 
    container supa-policy-target { 
      description  
            "SUPAPolicyTarget is an abstract class that defines a 
            set of managed objects that may be affected by the 
            actions of a SUPAPolicyStatement."; 
      leaf profileType { 
        type string; 
        description 
          "Which profile the policy will be worked on"; 
      } 
      leaf asDomainName { 
        type string; 
        description 
          "Which domain the policy will be worked on"; 
      } 
      leaf adminSubnetwork { 
        type string; 
        description 
          "Which subnet the policy will be worked on"; 
      } 
      leaf businessTypeName { 
        type string; 
        description 
          "Which business the policy will be worked on"; 
      }  
      container instance  { 
        description 
          "Which instance the policy will be worked on? E.g.,  
          a VPN, a flow or a link"; 

      }  
    } 
    container supa-policy-atomic { 
      description 
        "Define a atomic ECA policy rule"; 
      container supa-ECA-policy-rule { 
        description  
          "SUPA policy atomic defines a standalone policy 
          rule."; 
        leaf policy-rule-deploy-status { 
          type enumeration { 
            enum 0{ 
              description "undefined";        
            } 
            enum 1{ 
              description "deployed and enabled";        
            } 
            enum 2{ 
              description "deployed and in test";        
            } 
            enum 3{ 
              description "deployed but not enabled";        
            } 
            enum 4{ 
              description "ready to be deployed";        
            } 
            enum 5{ 
              description "not deployed";        
            } 
          } 
          description 
          "The deploy status of the policy."; 
        } 
        leaf policy-rule-exec-status { 
          type enumeration { 
            enum 0{ 
              description "undefined";        
            } 
            enum 1{ 
              description  
                "executed and SUCEEDED (operational mode)";        
            } 
            enum 2{ 
              description  
                "executed and FAILED (operational mode)";        
            } 
            enum 3{ 
              description  
                "currently executing (operational mode)";        
            } 
            enum 4{ 
              description  
                "executed and SUCEEDED (test mode)";        
            } 
            enum 5{ 
              description  
                "executed and FAILED (test mode)";        
            } 
            enum 6{ 
              description  
                "currently executing (test mode)";        
            } 
          } 
          description 
            "The executing status of the policy."; 
        } 
        container supa-ECA-component{ 
          description 
             "The component defines how the event, condition 
             and action clauses are constructed into policy"; 
          container supa-policy-events { 
            description 
              "An event or a set of events that trigger the 
              evaluation of policy: This is the trigger for 
              the service management application to 
              evaluate if a policy needs to be applied. For 
              example a user action to provision a new VPN 
              service can be an event."; 
            leaf has-policy-events { 
              type boolean; 
              description 
                "Whether the policy has an event?"; 
            } 
          } 
          container supa-policy-conditions { 
            description 
              "A set of conditions that need to be 
              satisfied for the policy to be applicable: 
              This enables service management to select the 
              right policy by validating the conditions 
              against the current network state."; 
            leaf has-policy-conditions { 
              type boolean;  
              description 
                "Whether the policy has an condition?"; 
            } 
            leaf conjunctive-type { 
              type enumeration { 
                enum 0 { 
                  description "AND: all the conditions 
                    must be matched"; 
                } 
                enum 1 { 
                  description "OR: one or more of the 
                    conditions are matched"; 
                } 
              } 
              description  
                "Define how the condition clauses will be 
                conjuncted, AND or OR"; 
            }  
          } 
          container supa-policy-actions { 
            description 
              "A set of actions that should be triggered as 
              part of the policy execution: This enables 
              the service management to provision the 
              service.";  
            leaf action-execution { 
              type enumeration{ 
                enum 0 { 
                  description "Single: execute one action"; 
                } 
                enum 1 { 
                  description "Sequenced: execute actions 
                          one by one  
                  in sequence"; 
                } 
              } 
              description 
              "How the actions will be executed";  
            } 
          } 
        } 
      } 
    } 
    container supa-policy-statement { 
      description 
        "The individual policy statement clauses.";  
      /*typedef scriptTemplate { 
        type string; 
        description 
          "The script defined in the YANG model can be sent 
          to the policy engine to execute. Here is the 
          content of the script template"; 
      }*/ 
      typedef scriptType { 
        type enumeration{ 
          enum 0{ 
            description 
              "Python"; 
          } 
          enum 1{ 
            description 
              "Perl"; 
          } 
          enum 2{ 
            description 
              "Javascript"; 
          } 
        } 
        description 
          "Here is the type of the script to be executed. 
          E.g., Python, Perl"; 
      } 
      grouping supa-entity{ 
        leaf entity{ 
          type empty; 
          description 
            "The path of the reference node needs to be 
            specified when using this type to define event 
            or condition"; 
        } 
        description 
          "Use predefined object to specify the event and 
          condition"; 
      } 
      grouping supa-script{ 
        description  
          "The script can be used to specify the event and 
          condition clauses. The script can be executed in 
          the policy engine."; 
        leaf supa-script-type  { 
          type scriptType; 
          description  
            "Use which type of script, such as Python, Perl 
            and so on."; 
        } 
        anyxml supa-script-content { 
          description  
            "The script template that will be sent to the 
            policy engine to specify the event or condition 
            clause"; 
        } 
      } 

      container event-list{ 
        description 
          "The event clauses. Each one can be a predefined 
          network entity, a script or boolean clause,"; 
        container event-name { 
          description  
            "The event clause of the policy."; 
          choice eventType{ 
            description  
            "User define to use which type event."; 
            case entity{ 
              uses supa-entity; 
            } 
            case script { 
              uses supa-script; 
            } 
          } 
        } 
      } 
      container condition-list{ 
        description 
          "The condition clauses. Each one can be a 
          predefined network entity, a script or boolean 
          clause, and conjuncted by AND or OR"; 
      } 
      container action-list{ 
        description 

          "Defines actions clause here. Each action has 
          unique attributes so a choice statement here to 
          allow self-defined action without changing.";   

      } 
    } 
  } 
}
