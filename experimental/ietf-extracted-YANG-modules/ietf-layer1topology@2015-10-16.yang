module ietf-layer1topology { 
  yang-version 1; 

  namespace "urn:ietf:params:xml:ns:yang:ietf-layer1topology"; 
  prefix "l1topo"; 

  import ietf-inet-types {  
    prefix "inet";  
  } 
  import ietf-network { 
    prefix "nt"; 
  } 

  import ietf-network-topology { 
    prefix "nttopo"; 
  } 

  import ietf-te-types { 
    prefix "ietf-te-types"; 
  } 

  organization  
    "Internet Engineering Task Force (IETF) CCAMP WG"; 
  contact 
    "ID-draft editor: zhang.xian@huawei.com"; 
  description 
    "This module defines a protocol independent Layer One/OTN  
    topology data model."; 

  revision 2015-10-16 { 
    description 
      "Initial version."; 
    reference 
      "draft-zhang-ccamp-l1-topo-yang-00.txt"; 
  } 

  /* 
  Groupings 
  */ 

  grouping srlg-attributes {  
    description  
      "Shared Risk Link Group Attributes";  
    reference  
      "RFC 4203: OSPF Extensions in Support of Generalized  
      Multi-Protocol Label Switching (GMPLS)";  
    leaf-list srlg-values {  
      type uint32;  
      description "SRLG value list"; 
    } 
  } 

  grouping l1-network-type { 
    container l1-network { 
      presence "indicates a L1 network, i.e., Optical  
      Transport Network (OTN)."; 
      description "l1 network type"; 
    } 
    description "l1-network-type"; 
  } 

  grouping l1-network-attributes { 
    container l1-network-attributes { 
      leaf name { 
        type string; 
        description "the network name"; 
      } 
      description "name attribute for l1 network";  
    } 
    description "l1-network-attributes";       
  } 
  grouping l1-node-attributes { 
    description "l1-node-attributes"; 
    container l1-node-attributes { 
      description "l1-node-attributes"; 
      leaf name { 
        type string; 
        description "a name for this node."; 
      } 

      list connectivity-matrix { 
        key "id"; 

        description 
          "This describes the connectivity constraints within  
          a node in the network. It can be one matrix or a set 
          of matrixes. Further details, read the reference 
          provided below."; 
        reference 
          "https://tools.ietf.org/html/draft-ietf-ccamp-general 
          -constraint-encode-16 Section 2.1"; 

        leaf id { 
          type uint32; 
          description "matrix id"; 
        } 
        leaf type { 
          type enumeration { 
            enum fixed { 
              value 0; 
              description "Fixed"; 
            } 
            enum dynamic { 
              value 1; 
              description "Dynamic/changeable"; 
            } 
          } 
          description 
            "This field describes the attribute of a  
            connectivity matrix, i.e., whether it is  
            fixed or switched."; 
        } 
        list in-tp { 
          key "tp-ref"; 

          description  
            "This list describes a (sub)-set of ingoing 
            interfaces within a node that may have  
            connectivity constraints. 
            Note: directionality may not be relevant 
             and it is decided by the dir parameter."; 

          leaf tp-ref { 
            type leafref { 
              path "../../../../nttopo:termination-point/"+ 
              "nttopo:tp-id"; 
            } 
            description "reference to an incoming interface, 
            must be within the same node"; 
          } 
        } 
        list out-tp { 
          key "tp-ref"; 

          description 
            "This list describes a (sub)-set of outgoing 
            interfaces within a node that may have  
            connectivity constraints. 
            Note: directionality may not be relevant and 
            it is decided by the dir parameter."; 

          leaf tp-ref { 
            type leafref { 
              path "../../../../nttopo:termination-point"+ 
              "/nttopo:tp-id"; 
            } 
            description "reference to an outgoing interface, 
            must be within the same node"; 
          } 
        } 
        leaf dir{ 
          type enumeration{ 
            enum "uni-dir"{ 
              description 
              "the matrix is unidirectional."; 
            } 
            enum "bi-dir"{ 
              description 
              "this matrix is bidirectional."; 
            } 
          } 
          mandatory true; 
          description 
            "the directionality attribute of a connc. matrix."; 
        } 
      } 

      leaf oper-status { 
        type enumeration { 
          enum "unknown" { 
            description "unknown - lost connect with control 
                 plane."; 
          } 
          enum "up" { 
            description "normal"; 
          } 
          enum "down" { 
            description "not available"; 
          } 
        } 

        config false; 
        description "operational status of a node"; 
      } 
    } 
  } 

  grouping l1-link-attributes { 
    description "l1-link-attributes"; 
    container l1-link-attributes { 
      presence "L1 link attributes"; 
      description "l1 link attributes"; 
      leaf source-tp-type { 
        type enumeration { 
          enum "client-side" { 
            description "client side"; 
          } 
          enum "line-side" { 
            description "line side"; 
          } 
        } 
        mandatory true; 
        description  
        "the type of a port:0-client side; 1 - line side"; 
      } 

      leaf admin-status { 
        type enumeration { 
          enum "up" { 
            description "up"; 
          } 
          enum "down" { 
            description "normal"; 
          } 
       } 
       description "administrative status of a link"; 
      } 

      leaf link-protection-type { 
        type enumeration {  
          enum "extra-traffic" {  
            description "Extra traffic";  
          }  
          enum "unprotected" {  
            description "unprotected";  
          }  
          enum "shared" {  
            description "Shared";  
          }  
          enum "1-for-1" {  
            description "Dedicated one for one protection";  
          }  
          enum "1-plus-1" {  
            description "Dedicated one plus one protection";  
          }  
          enum "enhanced" {  
            description "a protection type that is more reliable 
            than Dedicated 1+1, e.g.,4 fiber BLSR/MS-SPRING.";  
          }  
        }  
        description  
          "Link Protection Type configured for this link"; 
        reference 
          "RFC3471: Generalized Multi-Protocol Label Switching  
          (GMPLS) Signaling Functional Description.";  
      } 

      leaf switching-capability { 
        type identityref{ 
          base ietf-te-types:switching-capabilities; 
        } 
        description  
          "the switching capability supported by the link"; 
      } 

      leaf encoding { 
        type identityref{ 
          base ietf-te-types:lsp-encoding-types; 
        } 
        description 
          "the encoding type supported by this link."; 
      } 

      container srlg { 
        uses srlg-attributes; 
        description " the SRLG values of a link"; 
      } 

      choice link-attributes { 
        case ODU { 
          leaf ODU-type { 
            type uint32; 
            description "link capacity, subject to change 
            to the type of enumeration"; 
          } 

          container availabe-resources { 
            leaf granularity { 
              type enumeration { 
                enum "1.25G" { 
                  description "1.25G"; 
                } 
                enum "2.5G" { 
                  description "2.5G"; 
                } 
              } 
              mandatory true; 
              description "the base unit for unreserved-bandwidth 
                     description"; 
            } 
            leaf num { 
              type uint32; 
             description "number * granularity = max-bandwidth"; 
            } 
            leaf-list availability-bitmap { 
              type boolean; 
              description "0-avaialble, 1- unavaialbe"; 
            }            
            description "describe what is available in the unit 
                  of granularity"; 
          } 
          container mapping-info { 
            leaf-list mapping-list { 
              type string; 
                                             description "it can be one or multiple mapping 
                     route"; 
            } 
            description "mapping supported by this link; subject 
            to further change"; 
          } 
        } 
        case client { 
          leaf max-bandwidth { 
            type uint32; 
            description "max bandwidth supported by this client 
            facing link"; 
          } 
          leaf unreserved-bandwidth { 
            type uint32; 
            description "available bandwidth on this link"; 
          } 
          leaf local-ip { 
            type inet:ip-address; 
            description "the local-end ip address of a link"; 
          } 
          leaf remote-ip { 
            type inet:ip-address; 
            description "the remote-end ip address of a link"; 
          } 
        } 
        description "attributes for a client interface"; 
      } 

      leaf oper-status { 
        type enumeration { 
          enum "unknown" { 
                        description "unknown-lost connection with control 
                 plane"; 
          } 
          enum "normal" { 
            description "normal"; 
          } 
          enum "down" { 
            description "down"; 
          } 
          enum "degraded" { 
            description "degraded, temporarily unusable"; 
          } 
        } 

        config false; 
        description "status of a link"; 
      } 
    } 
  } 

  grouping l1-tp-attributes { 
    description "l1-tp-attributes"; 
    container physical-info { 
      description "physical info of an termination point/port"; 
      leaf shelf-id { 
        type uint32; 
        description "shelf-id of which this tp belongs to"; 
      } 
      leaf board-id { 
        type uint32; 
        description "board-id of which this tp belongs to"; 
      } 
      leaf subcard-id { 
        type uint32; 
        description "subcard id information, if no such info.,"+ 
        "fill in 0xff."; 
      } 
      leaf port-id { 
        type uint32; 
        description "port-id of which this tp belongs to"; 
      } 
    } 
  } 

   /* 
    * Data nodes 
    */ 

  augment "/nt:network/nt:network-types" { 
    uses l1-network-type; 
    description "augment network types to include L1 newtork"; 
  } 

  augment "/nt:network" { 
    when "nt:network-types/l1-network" { 
      description "Augment only for L1 network"; 
    } 
    uses l1-network-attributes;     
    description "Augment network configuration";    
  } 

  augment "/nt:network/nt:node" { 
    when "nt:network-types/l1-network" { 
      description "Augment only for L1 network"; 
    } 
    description "Augment node configuration"; 

    uses l1-node-attributes; 
  } 

  augment "/nt:network/nt:node/nttopo:termination-point" { 
    when "nt:network-types/l1-network" { 
      description "Augment only for L1 network"; 
    } 
    description "Augment tp configuration"; 

    uses l1-tp-attributes; 
  } 

  augment "/nt:network/nttopo:link" { 
    when "nt:network-types/l1-network" { 
      description "Augment only for L1 network."; 
    } 
    description "Augment link configuration"; 

    uses l1-link-attributes; 
  } 

  notification link-failure { 
    leaf topology-ref { 
      type leafref { 
        path "/nt:network/nt:network-id"; 
      } 
      mandatory true; 
      description "the topology reference of which"  
      +"this link belongs to"; 
    } 
    leaf link-ref { 
      type leafref { 
        path "/nt:network[nt:network-id= current ()"+ 
        "/../topology-ref]/nttopo:link/nttopo:link-id"; 
      } 
      mandatory true; 
      description ""; 
    } 
    leaf admin_status { 
      type leafref { 
        path 
          "/nt:network/nttopo:link[nttopo:link-id ="+ 
          "current()/../link-ref]/l1-link-attributes/admin-status"; 
      } 
      description "admin status of the reported link"; 
    } 
    leaf oper-status { 
      type leafref { 
        path 
          "/nt:network/nttopo:link[nttopo:link-id = current()" 
          +"/../link-ref]/l1-link-attributes/oper-status"; 
      } 
      description ""; 
    } 
    description 
     "link failure information"; 
  } //notification-link failure 

  notification node-failure { 
    leaf topology-ref { 
      type leafref { 
        path "/nt:network/nt:network-id"; 
      } 
      mandatory true; 
      description "";  
    } 
    leaf node-ref { 
      type leafref { 
        path "/nt:network[nt:network-id= current ()"+ 
        "/../topology-ref]/nt:node/nt:node-id"; 
      } 
      mandatory true; 
      description ""; 
    } 
    leaf oper-status { 
      type leafref { 
        path 
          "/nt:network/nt:node[nt:node-id = current()" 
          +"/../node-ref]/l1-node-attributes/oper-status"; 
      } 
      description ""; 
    } 
    description 
     "node failure information"; 
  } 
}
