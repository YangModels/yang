module ietf-detnet-static {
  namespace "urn:ietf:params:xml:ns:yang:ietf-detnet-static";
  prefix "detnet-static";

  import ietf-routing {
    prefix "rt";
  }

  import ietf-yang-types{
    prefix "yang";
  }

  import ietf-inet-types{
    prefix "inet";
  }

  import ietf-routing-types {
    prefix "rt-types";
  }

  organization
    "IETF Deterministic Networking(detnet)Working Group";

  contact
   "WG Web:   <http://tools.ietf.org/wg/detnet/>
    WG List:  <mailto: detnet@ietf.org>

    WG Chair: Lou Berger
              <mailto:lberger@labn.net>

    Editor:   Xuesong Geng
              <mailto:gengxuesong@huawei.com>

    Editor:   Mach Chen
              <mailto:mach.chen@huawei.com>";

    description
      "This YAGN module augments the 'ietf-routing'module
       with detnet flow configuration attribute";
    revision "2018-01-15" {
      description "Initial revision";
      reference "RFC XXXX: YANG Data Model for DetNet Topologies";
      //RFC Ed.: replace XXXX with actual RFC number and remove
      // this note
    }

    grouping flow-identfication {
      description
        "DetNet flow identification";
      reference
        "draft-farkas-detnet-flow-information-model";
      leaf source-ip-address {
        type inet:ip-address;
        description
          "Source IP address";
      }
      leaf destination-ip-address {
        type inet:ip-address;
        description
          "Destination IP address";
      }
      leaf source-mac-address {
        type yang:mac-address;
        description
          "Source MAC address";
      }
      leaf destination-mac-address {
        type yang:mac-address;
        description
          "Destination MAC address";
      }
      leaf ipv6-flow-label {
        type uint32;
        description
          "ipv6 flow label";
      }
      leaf mpls-label {
        type rt-types:mpls-label;
        description
          "MPLS Label";
      }
    }

    grouping traffic-specification{
      description
        "traffic-specification specifies how the Source
         transmits packets for the flow.  This is the
         promise/request of the Source to the network.
         The network uses this traffic specification
         to allocate resources and adjust queue
         parameters in network nodes.";
      reference
        "draft-farkas-detnet-flow-information-model";
      leaf max-packets-per-interval{
        type uint16;
        description
          "max-packets-per-interval specifies the maximum
           number of packets that the application shall
           transmit in one Interval.";
      }
      leaf max-packet-size{
        type uint16;
        description
          "max-packet-size specifies maximum packet size
           that the Source will transmit";
      }
      leaf queuing-algorithm-selection{
        type uint8;
        description
        "";
      }
    }

    grouping routing-configuration{
      description
        "configuration parameters direct data plane
         operations";
      container flow-identification{
        description
          "flow identification";
        uses flow-identfication;
      }
      leaf operation{
        type enumeration{
          enum transmission{
            description
              "Operation: transmit ";
          }
          enum replication{
            description
              "Operation: packet replication";
          }
          enum elimination{
            description
              "Operation: packet elimination";
          }
          enum elimination-and-replication{
            description
              "Operation: packet elimination and
               replication";
          }
        }
        description
          "The operation will be done to the
           packet";
      }
    }

    grouping queuing-parameters{
      description
        "The paramters used to configure
         queuing managment algorithm";
    }

    grouping replication-function{
      description
        "The paramters used to configure
         packet replication";
    }

    grouping elimination-function{
      description
        "The paramters used to configure
         packet elimination";
    }

    augment "/rt:routing"{
      description
        "DetNet node static configuration
         attributes.";
      uses flow-identfication;
      uses traffic-specification;
      uses routing-configuration;
      uses queuing-parameters;
      uses replication-function;
      uses elimination-function;
    }
  }
