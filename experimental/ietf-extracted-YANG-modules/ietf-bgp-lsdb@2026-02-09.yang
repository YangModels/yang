module ietf-bgp-lsdb {
  yang-version 1.1;
  namespace "urn:ietf:params:xml:ns:yang:ietf-bgp-lsdb";
  prefix bgp-lsdb;

  import ietf-inet-types {
    prefix inet;
    reference
      "RFC 9911: Common YANG Data Types.";
  }

  import ietf-yang-types {
    prefix yang;
    reference
      "RFC 9911: Common YANG Data Types.";
  }

  import ietf-bgp-ls-topo-types {
    prefix bgp-ls-topo-t;
    reference
      "RFC XXXX: BGP Model for Link State Distribution.";
  }

  import ietf-routing-types {
    prefix ietf-rt-t;
    reference
      "RFC 8294: Common YANG Data Types for the Routing Area.";
  }

  import ietf-isis {
    prefix ietf-isis-t;
    reference
      "RFC 9130: YANG Data Model for IS-IS Protocol.";
  }

  import ietf-ospf {
    prefix ietf-ospf-t;
    reference
      "RFC 9129: YANG Data Model for the OSPF Protocol.";
  }

  include ietf-bgp-ls-topo-attr;

  organization
    "IETF LSVR Working Group";
  contact
    "WG Web:   <https://datatracker.ietf.org/wg/lsvr>
     WG List:  <lsvr@ietf.org>

     Authors: Mahesh Jethanandani (mjethanandani at gmail.com),
              Keyur Patel (keyur at arrcus.com),
              Aravind Babu MahendraBabu (aramahen at cisco.com)";

  description
    "This module contains contains configuration and management
     information for BGP-LS, BGP-LS-SPF.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-02-09 {
    description
      "Initial Version";
    reference
      "RFC XXXX, BGP Model for Link State Distribution.";
  }
  // Groupings

  grouping lsdb-top {
    description
      "Details for all databases under an application instance.";

    container bgp-ls-topology {
      config false;
      description
        "Top level container for BGP-LS topology entries";

      container instances {
        description
          "Enclosing container for instance list";

        list instance {
          key "vrf-name protocol identifier";
          description
            "List of instances";

          leaf vrf-name {
            type string;
            description
              "Name of the VRF this database belongs to.";
          }

          leaf protocol {
            type bgp-ls-topo-t:protocol;
            description
              "Protocol originating the NLRI.";
            reference
              "RFC 9552: Distribution of Link-State and Traffic
               Engineering Information Using BGP, Section 5.2.";
          }

          leaf identifier {
            type uint64;
            description
              "Instance identifier identifying the IGP routing
               domain where the NLRI belongs.";
            reference
              "RFC 9552: Distribution of Link-State and Traffic
               Engineering Information Using BGP, Section 5.2.";
          }

          container nodes {
            description
              "BGP-LS topology entries for nodes";
            list ospf-node {
              key "is-as-scoped area-id router-id dr-identifier as";
              description
                "List of node types";

              leaf is-as-scoped {
                type boolean;
                description
                  "Is area ID valid?";
              }

              leaf area-id {
                type ietf-ospf-t:area-id-type;
                description
                  "Area ID.";
                reference
                  "RFC 9552: Distribution of Link-State and
                   Traffic Engineering Information Using BGP,
                   Section 5.2.1.";
              }

              leaf router-id {
                type ietf-rt-t:router-id;
                description
                  "Router ID.";
                reference
                  "RFC 9552: Distribution of Link-State and
                   Traffic Engineering Information Using BGP,
                   Section 5.2.1.";
              }

              leaf dr-identifier {
                type inet:ipv4-address;
                description
                  "Designated Router (DR) Identifier.";
                reference
                  "RFC 9552: Distribution of Link-State and
                   Traffic Engineering Information Using BGP,
                   Section 5.2.1.";
              }

              leaf as {
                type inet:as-number;
                description
                  "Autonomous System (AS) number associated with the
                   BGP process originating the NLRI.";
                reference
                  "RFC 9552: Distribution of Link-State and
                   Traffic Engineering Information Using BGP,
                   Section 5.2.1.";
              }

              uses bgp-ls-topo-node-attr;
            }

            list isis-node {
              key "system-id psn-id as";
              description
                "List of node types";

              leaf system-id {
                type ietf-isis-t:system-id;
                description
                  "System ID.";
                reference
                  "RFC 9552: Distribution of Link-State and
                   Traffic Engineering Information Using BGP,
                   Section 5.2.1.";
              }

              leaf psn-id {
                type uint8;
                description
                  "Pseudo Node Identifier (PSN ID).";
                reference
                  "RFC 9552: Distribution of Link-State and
                   Traffic Engineering Information Using BGP,
                   Section 5.2.1.";
              }

              leaf as {
                type inet:as-number;
                description
                  "Autonomous System (AS) number associated with the
                   BGP process originating the NLRI.";
                reference
                  "RFC 9552: Distribution of Link-State and
                   Traffic Engineering Information Using BGP,
                   Section 5.2.1.";
              }

              uses bgp-ls-topo-node-attr;
            }
          }

          container unknowns {
            description
              "BGP-LS topology entries for unknown NLRIs -- active
              when the nlri-type is unknown";
            list unknown {
              key "nlri";
              description
                "List of unknown types";

              leaf nlri {
                type yang:hex-string;
                description
                  "NLRI.";
                reference
                  "RFC 9552: Distribution of Link-State and Traffic
                   Engineering Information Using BGP, Section 5.2.";
              }

              leaf attributes {
                type yang:hex-string;
                description
                  "Attributes.";
                reference
                  "RFC 9552: Distribution of Link-State and Traffic
                   Engineering Information Using BGP, Section 5.3.";
              }
            }
          }
        }
      }
    }
  }
}
