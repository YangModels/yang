module lisp-address-types {
  namespace "urn:ietf:params:xml:ns:yang:lisp-address-types";
  prefix lisp;

  import ietf-inet-types {
    prefix inet;
  }
  import ietf-yang-types {
    prefix yang;
  }

  organization "IETF LISP (Locator/ID Separation Protocol) Working Group";
  contact
    "lisp@ietf.org";
  description
    "This YANG module defines the LISP Canonical Address Formats (LCAF)
     for LISP. The module can be extended by vendors
     to define vendor-specific parameters.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.

    ";

  revision 2015-03-23 {
    description
      "Initial revision.";
  }

  typedef instance-id-type {
    type uint32 {
      range "0..16777214";
    }
  }

  typedef simple-address {
    type union {
      type inet:ip-address;
      type yang:mac-address;
    }
  }

  grouping lcaf-address {
    leaf lcaf-type {
      type enumeration {
        enum "null";
        enum "afi-list";
        enum "instance-id";
        enum "as-number";
        enum "application-data";
        enum "geo-coordinates";
        enum "opaque-key";
        enum "nat-ttraversal";
        enum "nonce-locator";
        enum "multicast-info";
        enum "explicit-locator-path";
        enum "security-key";
        enum "source-dest-key";
        enum "replication-list";
        enum "json-data-model";
        enum "key-value-address";
        enum "encapsulation-format";
      }
    }
    choice address {
      container as-number {
        when "lcaf-type = as-number";
        leaf as {
          type inet:as-number;
        }
        leaf address {
          type simple-address;
        }
      }
      container sourc-dest-key {
        when "lcaf-type = source-dest-key";
        leaf source {
          type inet:ip-prefix;
        }
        leaf dest {
          type inet:ip-prefix;
        }
      }
      container explicit-locator-path {
        when "lcaf-type = explicit-locator-path";
        list hop {
          key "address";
          leaf address {
            type simple-address;
          }
          leaf lrs-bits {
            type bits {
              bit lookup;
              bit rloc-probe;
              bit strict;
            }
          }
        }
      }
    }
  }

  grouping lisp-address {
    leaf afi {
      type enumeration {
        enum "ipv4" {
          value 1;
        }
        enum "ipv6" {
          value 2;
        }
        enum "mac-address" {
          value 6;
        }
        enum "lcaf" {
          value 16387;
        }
      }
    }
    leaf instance-id {
      type instance-id-type;
    }
    choice address {
      case ipv4 {
        when "afi = ipv4";
        leaf ipv4 {
          type inet:ipv4-address;
        }
      }
      case ipv6 {
        when "afi = ipv6";
        leaf ipv6 {
          type inet:ipv6-address;
        }
      }
      case mac-address {
        when "afi = mac-address";
        leaf mac-address {
          type yang:mac-address;
        }
      }
      case lcaf {
        when "afi = lcaf";
        container lcaf {
          uses lcaf-address;
        }
      }
    }
  }
}
