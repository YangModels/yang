module ietf-mpls-l2vpn-svc {
    namespace "urn:ietf:params:xml:ns:yang:ietf-mpls-l2vpn-svc";
    prefix "mpls-l2vpn-svc";

    import ietf-inet-types
    {
        prefix inet;
    }

    organization "ietf";
    contact "ietf";
    description "mpls-l2vpn-svc";

    revision "2016-03-17" {
        description "Initial revision of mpls-l2vpn-service model.";
        reference "draft-hu-bess-l2vpn-service-yang-00.txt";
    }

    /* identities */

    identity link-discovery-protocol {
        description "Base identiy from which identities describing link discovery protocols are derived.";
    }

    identity lacp {
         base "link-discovery-protocol";
         description "This identity represents LACP";
    }

    identity lldp {
        base "link-discovery-protocol";
        description "This identity represents LLDP";
    }

    identity bpdu {
        base "link-discovery-protocol";
        description "This identity represens BPDU";
    }

    identity cpd {
        base "link-discovery-protocol";
        description "This identity represents CPD";
    }

    identity udld {
        base "link-discovery-protocol";
        description "This identity represens UDLD";
    }

    /* typedefs */
    typedef l2vpn-service-type {
        type enumeration {
            enum ethernet {
                description "Ethernet service";
            }
            enum ATM {
                description "Asynchronous Transfer Mode";
            }
            enum FR {
                description "Frame-Relay";
            }
            enum TDM {
                description "Time Division Multiplexing";
            }
        }
        description "L2VPN service type";
    }

    typedef l2vpn-signaling-type {
        type enumeration {
            enum static {
                description "Static configuration of labels (no signaling)";
            }
            enum ldp {
                description "Label Distribution Protocol (LDP) signaling";
            }
            enum bgp {
                description "Border Gateway Protocol (BGP) signaling";
            }
            enum mixed {
                description "Mixed";
            }
        }
        description "L2VPN signaling type";
    }

    typedef tunnel-signaling-type {
        type enumeration {
             enum static {
               value 0 ;
               description "static" ;
             }
             enum RSVP-TE {
               value 1 ;
               description "RSVP-TE" ;
             }
            enum LDP {
                value 2 ;
                description "LDP" ;
            }
          }
        description "tunnel signaling type." ;
    }

    typedef bgp-rt-type {
        type enumeration {
            enum import {
                description "For import";
            }
            enum export {
                description "For export";
            }
            enum both {
                description "For both import and export";
            }
        }
        description "BGP route-target type. Import from BGP YANG";
    }

    typedef cw-negotiation-type {
        type enumeration {
            enum "non-preferred" {
                description "No preference for control-word";
            }
            enum "preferred" {
                description "Prefer to have control-word negotiation";
            }
        }
        description "control-word negotiation preference type";
    }

    typedef link-discovery-protocol-type {
        type identityref {
            base "link-discovery-protocol";
        }
        description "This type is used to identify link discovery protocol";
    }

    typedef cc-type {
        type enumeration {
            enum pw-ach {
                description "PWE3 Control Word with 0001b as first nibble (PW-ACH, see [RFC4385])";
            }
            enum alert-label {
                description "MPLS Router Alert Label";
            }
            enum ttl {
                description "MPLS PW Label with TTL == 1";
            }
        }
        description "The defined values for CC(Control Channel) Types for MPLS PWs.";
    }

    typedef cv-type {
        type enumeration {
            enum ICMP-ping {
                description "ICMP-ping.";
            }
            enum LSP-ping {
                description "LSP-ping";
            }
            enum BFD-basic-ip {
                description "BFD basic ip";
            }
            enum BFD-basic-raw {
                description "BFD basic raw ";
            }
            enum BFD-signalling-ip {
                description "BFD signalling ip";
            }
            enum BFD-signalling-raw {
                description "BFD signalling raw";
            }
        }
        description "The defined values for CV(Connectivity Verification) Types for MPLS PWs";
    }

    typedef pipe-mode{
        type enumeration {
            enum "pipe" {
                value 0;
                description "regular pipe mode";
            }
            enum "short-pipe" {
                value 1;
                description "short pipe mode";
            }
            enum "uniform" {
                value 2;
                description "uniform pipe mode";
            }
        }
        description " ";
    }

    typedef pw-type {
        type enumeration {
            enum unknown {
                value 0 ;
                description "The PW type is unknown";
            }
            enum dlciOld {
                value 1 ;
                description "The PW type is dlciOld";
            }
            enum atmSdu {
                value 2 ;
                description "The PW type is atmSdu";
            }
            enum atmCell {
                value 3 ;
                description "The PW type is atmCell";
            }
            enum vlan {
                value 4 ;
                description "The PW type is vlan";
            }
            enum ethernet {
                value 5 ;
                description "The PW type is ethernet";
            }
            enum hdlc {
                value 6 ;
                description "The PW type is hdlc";
            }
            enum ppp {
                value 7 ;
                description "The PW type is ppp";
            }
            enum sdhCESoM {
                value 8 ;
                description "The PW type is sdhCESoM";
            }
            enum atmVCCn {
                value 9 ;
                description "The PW type is atmVCCn";
            }
            enum atmVPCn {
                value 10 ;
                description "The PW type is atmVPCn";
            }
            enum ipL2 {
                value 11 ;
                description "The PW type is ipL2";
            }
            enum atmVCC1 {
                value 12 ;
                description "The PW type is atmVCC1";
            }
            enum atmVPC1 {
                value 13 ;
                description "The PW type is atmVPC1";
            }
            enum atmPDU {
                value 14 ;
                description "The PW type is atmPDU";
            }
            enum frPort {
                value 15 ;
                description "The PW type is frPort";
            }
            enum sdhCEoP {
                value 16 ;
                description "The PW type is sdhCEoP";
            }
            enum saTopE1 {
                value 17 ;
                description "The PW type is saTopE1";
            }
            enum saTopT1 {
                value 18 ;
                description "The PW type is saTopT1";
            }
            enum saTopE3 {
                value 19 ;
                description "The PW type is saTopE3";
            }
            enum saTopT3 {
                value 20 ;
                description "The PW type is saTopT3";
            }
            enum ceSoPSNB {
                value 21 ;
                description "The PW type is ceSoPSNB";
            }
            enum tdmAAL1 {
                value 22 ;
                description "The PW type is tdmAAL1";
            }
            enum ceSoPSNC {
                value 23 ;
                description "The PW type is ceSoPSNC";
            }
            enum tdmAAL2 {
                value 24 ;
                description "The PW type is tdmAAL2";
            }
            enum dlciNew {
                value 25 ;
                description "The PW type is dlciNew";
            }
        }
        description "The PW type of the PW.";
    }

    typedef dscp2exp {
       type string;
       description "define the dscp to exp mapping";
       }

    typedef cos2exp {
       type string;
       description "define the cos to exp mapping";
      }

    typedef protect-type {
       type enumeration {
            enum unprotected {
                value 0 ;
                description "unprotected." ;
                }
            enum 1to1 {
                value 1 ;
                description "protect type is 1:1";
            }
            enum 1plus1 {
                value 2 ;
                description "protect type is 1+1";
            }
            enum dni-pw {
                value 3 ;
                description "protect type is dni-pw";
            }
            enum dni-ac {
                value 4 ;
                description "protect type is dni-ac";
            }

        }
        description "define the protect type";
    }

    typedef receive-mode {
       type enumeration {
            enum selective {
                value 0 ;
                description "receive mode is selective";
            }
            enum both {
                value 1 ;
                description "receive mode is both";
            }
        }
        description "define the receive mode";
    }

    typedef tunnel-mode {
      type enumeration {
           enum static {
              value 2 ;
              description "static tunnel" ;
             }
            enum RSVP-TE {
               value 0 ;
                description "RSVP-TE" ;
            }
            enum LDP {
                value 1 ;
            description "LDP" ;
            }

        }
        description "define the tunnel mode";
    }

    typedef hub-spoken {
       type enumeration {
           enum hub {
              value 0 ;
              description "the hub role in the network" ;
             }
            enum spoken {
               value 1 ;
                description "the spokend role in the network" ;
            }
        }
        description "define the hub spoken type";
    }
    grouping pw-template{
        description "pw-template";
        leaf name {
            type string;
            description "name";
        }

        leaf cw-negotiation {
            type cw-negotiation-type;
            default "preferred";
            description "control-word negotiation preference";
        }

        leaf cc {
            type cc-type;
            description "Control Channel Types";
        }

        leaf cv {
            type cv-type;
            description "Connectivity Verification Types";
        }
    }

    grouping qos-policy-grp {
       container qos-policy {
         leaf qos-dscp2exp {
                type dscp2exp;
                description "the dscp to exp mapping template";
              }
         leaf  qos-cos2exp {
                type cos2exp ;
                description "the cos to exp mapping template";
              }

         container qos-if-cars {
              leaf direction {
                type uint32;
                description "the direction of qos";
               }

              leaf cir {
                type uint32;
                description "the cir parameter for the car";
               }

              leaf pir {
                type uint32;
                description "the pir parameter for the car";
               }

              leaf cbs {
                type uint32;
                description "the cbs parameter for the car";
               }

              leaf pbs {
                 type uint32;
                 description "the pbs parameter for the car";
               }
            description "configuration the qos interface car parameters.";
           }
         description "qos policy container.";
       }
      description "qos policy template.";
    }

    grouping pseudowire{
        description "pseudowire";
        leaf name {
            type string;
            description "pseudowire name";
        }

        leaf asbr-id {
            type string;
            description "asbr name for the cross domain lsp";
        }
        leaf peer {
            type inet:ip-address;
            description "pw peer address, use IPv4";
        }

        leaf vcid {
            type uint32;
            description "pseudo-wire vcid";
        }

        leaf type {
            type pw-type;
            description "pseudo-wire type";
        }

        leaf tunnel-policy {
            type string;
            description "Used to override the tunnel policy name specified in the pseduowire template";
        }

        leaf request-vlanid {
            type uint16;
            description "request vlanid";
        }

        leaf vlan-tpid {
            type string;
            description "vlan tpid";
        }

        leaf cw-negotiation {
            type cw-negotiation-type;
            default "preferred";
            config false;
            description "control-word negotiation preference";
        }

        leaf cc {
            type cc-type;
            config false;
            description "Control Channel Types";
        }

        leaf cv {
            type cv-type;
            config false;
            description "Connectivity Verification Types";
        }
    }

    grouping attachment-circuit{
        description "attachment circuit";
        leaf name {
            type string;
            description "name";
        }

        leaf ac-nodeid{
            type string;
            description "The nodeid of the AC.";
        }

        leaf link-discovery-protocol-type{
            type link-discovery-protocol-type;
            description "link discovery protocol";
        }

        choice access-type{
            description "access-type";
            case port{
                description "port.";
            }

            case dot1q {
                description "Dot1Q";
                leaf dot1q-vlan-bitmap {
                    type int32 {
                        range "1..4094";
                    }
                    description "Dot1Q Vlan Bitmap." ;
                }
            }

            case qinq {
                description "QinQ";
                leaf qinq-svlan-bitmap {
                    type int32 {
                        range "1..4094";
                    }
                    description "QinQ svlan Bitmap." ;
                }

                leaf qinq-cvlan-bitmap {
                    type int32 {
                        range "1..4094";
                    }
                    description "QinQ cvlan Bitmap." ;
                }
            }
        }

        choice access-action {
            description "access type." ;
            case keep {
                description "keep." ;
            }
            case push {
                description "push." ;
                leaf push-vlan-id {
                    type int32 {
                        range "1..4094";
                    }
                    description "action vlan id." ;
                }
            }
            case pop {
                description "pop." ;
            }
            case swap {
                description "swap." ;
                leaf swap-vlan-id {
                    type int32 {
                        range "1..4094";
                    }
                    description "action vlan id." ;
                }
            }
        }
        uses qos-policy-grp;
    }

    grouping protect-policy-grp {
        leaf protect-type {
               type protect-type;
               description "protection-type";
             }

        leaf receive-mode {
               type receive-mode;
               description "receive-mode";
            }

        choice revertive-type {
            description "revertive-type";
             case never {
              description "never type";
              }
             case wtr {
               leaf revert-delay {
                type uint16;
                description "the revertive type is wtr";
                }
             }
        }

     description "define the group of protect-policy.";
    }

    grouping redundancy-grp {
         leaf ne-id {
            type string;
            description "the name of ne";
           }
         choice primary {
           mandatory true;
           description "primary options";
           case primary-pw {
             list primary-pw {
               key "name";
               leaf name {
                 type leafref {
                   path "../../../pw/name";
                 }
                 description "Reference a pseudowire";
               }
               description "A list of primary pseudowires";
             }
             description "primary-pw";
           }

           case primary-ac {
             leaf primary-ac {
               type leafref {
                 path "../../ac/name";
               }
               description "Reference an attachment circuit";
             }
             description "primary-ac";
           }
         }

         choice backup {
           description "backup options";
           case backup-pw {
             list backup-pw {
               key "name";
               leaf name {
                 type leafref {
                   path "../../../pw/name";
                 }
                 description "Reference an attachment circuit";
               }
               leaf precedence {
                 type uint32;
                 description "precedence of the pseudowire";
               }
               description "list of backup pseudowires";
             }
           }
           case backup-ac {
             leaf backup-ac {
               type leafref {
                 path "../../ac/name";
               }
               description "Reference an attachment circuit";
             }
             description "backup-ac";
           }
         }
         uses protect-policy-grp;
        description "define the redundancy group";
       }

    grouping vpws-service-policy-grp {
        list service-policy {
         key "id";
         leaf id {
           type uint8;
           description "the id of service policy";
         }

         uses redundancy-grp;
         description "the service policy list";

         leaf communicate-unit {
             type int32;
             description "ICCP id for dni-pw";
            }
        }
        description "service policy list";
      }

    grouping vpls-service-policy-grp {
        list service-policy {
         key "id";
         leaf id {
           type uint8;
           description "the id of service policy";
         }

         leaf split-horizon-group {
            type string;
            description "split horizon group for the vpls instance";
          }

         leaf pw-type {
           type pw-type;
           description "the pseudowires type";
         }

         uses redundancy-grp;
         description "the service policy list";
        }
        description "service policy";
    }

    grouping tunnel-policy-grp {
        container tunnel-policy {
           leaf tunnel-signaling-type {
             type tunnel-signaling-type;
             description "signaling-type";
            }
          leaf tunnel-mode {
             type tunnel-mode;
             description "tunnel-mode";
          }
         uses protect-policy-grp;
         description "tunnel policy";
        }
        description "tunnel policy group";
       }

    grouping multi-segment{
        leaf multi-segment-node{
            type string;
            description "The multi-segment nodeid of the PW.";
        }

        leaf designated-node{
            type boolean;
            description "The multi-segment nodeid of the PW must select.";
        }
        description "multi-segment group.";
    }

    container l2vpn {
        description "l2vpn";
        container common {
            description "common l2pn attributes";
            container pw-templates {
                description "pw-templates";
                list pw-template {
                    key "name";
                    uses pw-template;
                    description "pw-templates";
                }
            }
        }

        container vpws-instances {
            description "configure vpws-instances";
            list vpws-instance {
               key "name";
                leaf name {
                  type string;
                  description "the name of a vpws instance";
                }

               leaf description {
                 type string;
                 description "Description of the vpws instance";
                }

               leaf service-type {
                 type l2vpn-service-type;
                 default ethernet;
                 description "vpws service type";
                }

                leaf signaling-type {
                 type l2vpn-signaling-type;
                 mandatory true;
                 description "vpws signaling type";
                }

                list pw{
                 key "name";
                 uses pseudowire;
                 description "pseudowires";
                }

                list ac{
                 key "name";
                 uses attachment-circuit;
                 leaf pipe-type{
                   type pipe-mode;
                   description "pipe mode";
                }
                 description "attachment-circuit";

                }

                uses vpws-service-policy-grp;
                uses tunnel-policy-grp ;

                list master-multi-segment-nodes{
                  key "multi-segment-node";
                  uses multi-segment;
                  description "The master multi-segment nodeid of the PW.";
                }

                list slave-multi-segment-nodes{
                   key "multi-segment-node";
                   uses multi-segment;
                   description "The slave multi-segment nodeid of the PW.";
                }

                description "vpws service instance list";

            }
        }

        container vpls-instances {
            description "configure vpls-instances";
            list vpls-instance {
               key "name";
                leaf name {
                  type string;
                  description "the name of a vpls instance";
                }

               leaf description {
                 type string;
                 description "Description of the vpls instance";
                }

                leaf mac-withdraw {
                  type boolean;
                  description "Withdraw MAC";
                }

                container bgp-parameters {
                   leaf route-distinguisher {
                     type string;
                     description "BGP RD";
                   }

                   list vpn-targets {
                     key rt-value;
                     description "Route Targets";

                     leaf rt-value {
                        type string;
                        description "Route-Target value";
                    }

                     leaf rt-type {
                        type bgp-rt-type;
                        mandatory true;
                        description "Type of RT";
                     }
                   }

                   container discovery {
                      description "BGP parameters for discovery";
                      leaf vpn-id {
                        type string;
                        description "VPN ID";
                      }
                   }
                 description "Parameters for BGP";
                }

               leaf service-type {
                 type l2vpn-service-type;
                 default ethernet;
                 description "vpls service type";
                }

                leaf signaling-type {
                 type l2vpn-signaling-type;
                 mandatory true;
                 description "vpls signaling type";
                }

                list pw{
                 key "name";
                 uses pseudowire;
                 leaf hub-spoken {
                   type hub-spoken;
                   description "hub-spoken role";
                  }
                 description "pseudowires";
                }

                list ac{
                 key "name";
                 uses attachment-circuit;
                 leaf split-horizon-group {
                   type string;
                   description "split horizon group for the vpls instance";
                  }
                 description "attachment-circuit";

                }

                uses vpls-service-policy-grp;
                uses tunnel-policy-grp ;

                list master-multi-segment-nodes{
                  key "multi-segment-node";
                  uses multi-segment;
                  description "The master multi-segment nodeid of the PW.";
                }

                list slave-multi-segment-nodes{
                   key "multi-segment-node";
                   uses multi-segment;
                   description "The slave multi-segment nodeid of the PW.";
                }
                description "vpls service instance list";
            }
        }
    }
}
