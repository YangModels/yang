module ietf-nrp {
  yang-version 1.1;
  namespace "urn:ietf:params:xml:ns:yang:ietf-nrp";
  prefix nrp;

  import ietf-network {
    prefix nw;
    reference
      "RFC 8345: A YANG Data Model for Network Topologies,
                 Section 6.1";
  }
  import ietf-network-topology {
    prefix nt;
    reference
      "RFC 8345: A YANG Data Model for Network Topologies,
                 Section 6.2";
  }
  import ietf-routing-types {
    prefix rt-types;
    reference
      "RFC 8294: Common YANG Data Types for the Routing Area";
  }
  import ietf-vpn-common {
    prefix vpn-common;
    reference
      "RFC 9181: A Common YANG Data Model for Layer 2 and Layer 3
                 VPNs";
  }
  import ietf-te-packet-types {
    prefix te-packet-types;
    reference
      "RFC 8776: Traffic Engineering Common YANG Types";
  }
  import ietf-inet-types {
    prefix inet;
    reference
      "RFC 9911: Common YANG Data Types";
  }
  import ietf-access-control-list {
    prefix acl;
    reference
      "RFC 8519: YANG Data Model for Network Access Control Lists
                 (ACLs)";
  }
  import ietf-srv6-types {
    prefix srv6-types;
    reference
      "draft-ietf-spring-srv6-yang-base: YANG Data Model for SRv6 Base";
  }
  import ietf-topology-filter {
    prefix topo-filt;
    reference
      "draft-ietf-teas-yang-topology-filter: YANG Data Model
       for Topology Filter";
  }

  organization
    "IETF Traffic Engineering Architecture and Signaling (TEAS)
     Working Group";
  contact
    "WG Web:   <https://datatracker.ietf.org/wg/teas/>
     WG List:  <mailto:teas@ietf.org>

     Editor:   Bo Wu
            <mailto:lana.wubo@huawei.com>

     Editor:   Dhruv Dhody
            <mailto:dhruv.ietf@gmail.com>

     Editor:   Vishnu Pavan Beeram
               <mailto:vbeeram@juniper.net>

     Editor:   Tarek Saad
               <mailto:tsaad.net@gmail.com>

     Editor:   Shaofu Peng
               <mailto:peng.shaofu@zte.com.cn>";
  description
    "This YANG module defines a data model for
     Network Resource Partitions (NRPs) management.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
        (https://trustee.ietf.org/license-info).

     This version of this YANG module is part of RFC XXXX
     (https://www.rfc-editor.org/info/rfcXXXX); see the RFC itself
     for full legal notices.";

  revision 2026-06-01 {
    description
      "Initial revision.";
    reference
      "RFC XXXX: YANG Data Models for Network Resource
                 Partitions (NRPs)";
  }

  /* Features - NRP Selector Mechanisms */

  feature ipv4-selector {
    description
      "Indicates support for IPv4-derived NRP selection
       (destination prefix based).";
  }

  feature ipv6-hbh-selector {
    description
      "Indicates support for dedicated IPv6 Hop?by?Hop
       extension header selector ID.";
  }

  feature srv6-selector {
    description
      "Indicates support for SRv6 SID?based NRP selection.";
  }

  feature ipv6-destination-selector {
    description
      "Indicates support for IPv6 destination prefix?based
       NRP selection.";
  }

  feature mpls-mna-selector {
    description
      "Indicates support for in?stack MPLS MNA?based
       NRP selection (NRPS13, NRPS20, ENRPS20).";
  }

  feature mpls-post-stack-selector {
    description
      "Indicates support for post?stack MPLS PSD?based
       NRP selection.";
  }

  feature acl-selector {
    description
      "Indicates support for ACL?based NRP selection.";
  }

  /*
   * I D E N T I T I E S
   */

  identity nrp-partition-mode {
    description
      "Base identity for NRP partition type.";
  }

  identity control-plane-partition {
    base nrp-partition-mode;
    description
      "NRP control plane partition.";
  }

  identity data-plane-partition {
    base nrp-partition-mode;
    description
      "NRP data plane partition.";
  }

  identity hybrid-plane-partition {
    base nrp-partition-mode;
    description
      "Both control and data planes partitions of NRP.";
  }

  identity nrp-link-partition-type {
    description
      "Base identity for NRP interface partition type.";
  }

  identity virtual-interface {
    base nrp-link-partition-type;
    description
      "Identity for NRP virtual interface or sub-interface partition,
       e.g., FlexE.";
  }

  identity queue-partition {
    base nrp-link-partition-type;
    description
      "Identity for NRP queue partition type.";
  }

  /*
   * T Y P E D E F S
   */

  typedef acl-ref {
    type leafref {
      path "/acl:acls/acl:acl/acl:name";
    }
    description
      "Used to reference an ACL.";
  }

  typedef topo-filter-ref {
    type leafref {
      path "/nw:networks/topo-filt:topology-filters/"
         + "topo-filt:topology-filter/topo-filt:name";
    }
    description
      "This type is used to reference a Topology Filter.";
    reference
      "draft-ietf-teas-yang-topology-filter: YANG Data Model
       for Topology Filter";
  }

  /*
   * Grouping - NRP Resource Reservation
   */

  grouping resource-reservation {
    description
      "Grouping for NRP resource reservation.";
    container resource-reservation {
      description
        "Container for NRP resource reservation.";
      choice max-bw-type {
        description
          "Choice of maximum bandwidth specification.";
        case bw-value {
          leaf maximum-bandwidth {
            type uint64;
            units "bits/second";
            description
              "The maximum bandwidth allocated to an NRP
               - specified as absolute value.";
          }
        }
        case bw-percentage {
          leaf maximum-bandwidth-percent {
            type rt-types:percentage;
            description
              "The maximum bandwidth allocated to an NRP
               - specified as percentage of link
               capacity.";
          }
        }
      }
    }
  }

  /*
   * Grouping - NRP Selector Identifier Configuration
   */

  grouping selector-id {
    description
      "Grouping for NRP selector identifier (NRP Selector ID)
       configuration.";
    container selector-id {
      description
        "Container for NRP selector ID.  It can contain one or more
         selector mechanisms (IPv4 prefixes, IPv6 Hop-by-Hop options,
         SRv6 SIDs, MPLS labels, or ACLs) depending on the features
         supported by the implementation.";
      container ipv4-derived {
        if-feature "ipv4-selector";
        description
          "Container for IPv4 NRP selector ID.";
        leaf-list destination-prefix {
          type inet:ipv4-prefix;
          description
            "Any prefix from the specified set of IPv4
             destination prefixes can be the selector ID.";
        }
      }
      container ipv6 {
        if-feature
          "ipv6-hbh-selector or srv6-selector or
           ipv6-destination-selector";
        description
          "Container for IPv6 NRP selector ID.";
        choice selector-type {
          description
            "Choices for IPv6 selector ID type.";
          case dedicated {
            if-feature "ipv6-hbh-selector";
            leaf ipv6-hbh-eh {
              type uint32;
              description
                "The selector ID carried in Hop-by-Hop option of
                 IPv6 extension header.";
              reference
                "draft-ietf-6man-enhanced-vpn-vtn-id: Carrying
                 Network Resource (NRP) related Information in IPv6
                 Extension Header";
            }
          }
          case srv6-derived {
            if-feature "srv6-selector";
            leaf-list srv6-sid {
              type srv6-types:srv6-sid;
              description
                "Any SID from the specified set of SRv6 SID can
                 be the NRP selector ID.";
              reference
                "draft-ietf-spring-sr-for-enhanced-vpn: Segment
                 Routing based Network Resource Partition (NRP) for
                 Enhanced VPN";
            }
          }
          case ipv6-destination-derived {
            if-feature "ipv6-destination-selector";
            leaf-list destination-prefix {
              type inet:ipv6-prefix;
              description
                "Any prefix from the specified set of IPv6
                 destination prefixes can be the NRP selector ID.";
            }
          }
        }
      }
      container mpls {
        if-feature "mpls-mna-selector or mpls-post-stack-selector";
        description
          "Container for MPLS NRP selector ID. Supports both
           In-Stack (MNA) and Post-Stack (PSD) encoding mechanisms.";
        choice mpls-encapsulation {
          description
            "Selects the MPLS NRP Selector encoding mechanism.";
          case mna-in-stack {
            if-feature "mpls-mna-selector";
            description
              "In-Stack NRP Selector action.
               Refers to draft-ietf-mpls-mna-nrp-selector.";
            leaf in-stack-identifier {
              type uint32;
              must
                "(../identifier-format='nrps13' and . <= 8191) or
                 (../identifier-format='nrps20' and . <= 1048575) or
                 (../identifier-format='enrps20' and . <= 1048575)" {
                error-message
                  "NRP Selector value exceeds format range";
              }
              description
                "The NRP Selector value. The valid range depends on the
                 encoding format (13-bit or 20-bit) selected.";
            }
            leaf identifier-format {
              type enumeration {
                enum nrps13 {
                  description
                    "13-bit NRP Selector (NRPS13).
                     Value range: 0-8191.";
                }
                enum nrps20 {
                  description
                    "20-bit NRP Selector (NRPS20).
                     Value range: 0-1048575.";
                }
                enum enrps20 {
                  description
                    "20-bit Extended NRP Selector (ENRPS20) compatible
                     with Entropy Label. Value range: 0-1048575.";
                }
              }
              description
                "Specifies the encoding format for the In-Stack
                 NRP Selector.";
            }
          }
          case post-stack {
            if-feature "mpls-post-stack-selector";
            description
              "Post-Stack NRP Selector (PS-NRP).
               Refers to draft-ietf-mpls-mna-psd-nrp-selector.";
            leaf post-stack-identifier {
              type uint32 {
                range "0..4294967295"; // 2^32 - 1
              }
              description
                "The 32-bit Post-Stack NRP Selector.";
            }
          }
        }
      }
      leaf-list acl-ref {
        if-feature "acl-selector";
        type acl-ref;
        description
          "NRP selection is done based on the specified list of
           ACLs.";
        reference
          "RFC 8519: YANG Data Model for Network Access Control Lists
                     (ACLs)";
      }
    }
  }

  /*
   * Grouping - NRP QoS Per-Hop Behavior (PHB) profiles
   */

  grouping qos-profiles {
    description
      "Grouping for NRP QoS profiles.";
    container qos-profiles {
      description
        "Container for profiles.";
      list phb-profile-identifier {
        key "id";
        description
          "List of PHB profiles.";
        leaf id {
          type string {
            length "1..max";
          }
          description
            "Uniquely identifies the PHB.
             The profile only has significance within the service
             provider's administrative domain";
        }
      }
    }
  }

  /*
   * Grouping - NRP QoS Per-Hop Behavior (PHB) profile
   */

  grouping phb-profile-ref {
    description
      "Grouping for NRP QoS Per-Hop Behavior (PHB) profile.";
    leaf phb-profile {
      type leafref {
        path "/nw:networks/nrp:nrp-policies/"
           + "nrp:qos-profiles/nrp:phb-profile-identifier/nrp:id";
      }
      description
        "PHB profile identifier, specifying the forwarding treatment
         of packets belonging to a specific NRP selector ID, such as
         bandwidth control, congestion control
         (e.g., Section 3.4 of [RFC3644]).
         The PHB may be standard PHB, such as Assured Forwarding (AF),
         Expedited Forwarding (EF), or a customized local policy,
         such as 'High', 'Low', 'Standard'.";
    }
  }

  /*
   * Grouping - NRP IGP congruent
   */

  grouping igp-congruent {
    description
      "Grouping for NRP IGP congruent attributes.";
    container igp-congruent {
      presence "Indicates NRP IGP congruency.";
      description
        "The presence of the container node describes NRP IGP
         congruent, which indicates that the NRP instance uses the
         same IGP topology with the specified 'multi-topology-id'
         and/or 'algo-id'. That is, the nodes and termination point
         of the NRP topology and the IGP topology are the same,
         while the link attributes of the NRP are different from
         those of the IGP.
         If not explicitly configured, both
         (multi-topology-id, algo-id) pair default to 0 (standard
         topology with standard SPF algorithm), corresponding to
         the base IGP instance.";
      leaf multi-topology-id {
        type uint32;
        default "0";
        description
          "Indicates the MT-id of the NRP IGP instance.
           MT-id 0 is reserved for the standard topology";
        reference
          "RFC 5120:  M-ISIS: Multi Topology (MT) Routing in
           Intermediate System to Intermediate Systems (IS-ISs)
           RFC 4915:  Multi-Topology (MT) Routing in OSPF";
      }
      leaf algo-id {
        type uint32;
        default "0";
        description
          "Indicates the algo-id of the NRP IGP instance.
           algo-id 0 is reserved for the standard SPF algorithm";
        reference
          "RFC 9350: IGP Flexible Algorithm";
      }
      leaf sharing {
        type boolean;
        description
          "'true' if the NRP IGP instance can be shared with
           other NRPs;
           'false' if the NRP IGP instance is dedicated
           to this NRP.";
      }
    }
  }

  /*
   * Grouping - NRP Topology Filter
   */

  grouping topology-filter {
    description
      "Grouping for NRP filter topology.";
    container filters {
      description
        "Container for filters.";
      list filter {
        key "filter-ref";
        description
          "List of filters.";
        leaf filter-ref {
          type topo-filter-ref;
          description
            "Reference to a specific topology filter from the
             list of global topology filters.";
        }
        uses resource-reservation;
        uses selector-id;
        uses phb-profile-ref;
      }
    }
  }

  /*
   * Grouping - NRP Select Topology
   */

  grouping select-topology {
    description
      "NRP topology specified by selection.";
    container select {
      description
        "The container of NRP select topology.";
      list topology-group {
        key "group-id";
        description
          "List of groups for NRP topology elements (node or links)
           that share common attributes.";
        leaf group-id {
          type string {
            length "1..max";
          }
          description
            "The NRP topology group identifier.";
        }
        /*The base topology reference. All links in
        the list below must belong to this specific
        network.*/
        uses nw:network-ref;
        list link {
          key "link-ref";
          description
            "A list of links with common attributes that are
             part of the referenced network";
          leaf link-ref {
            type leafref {
              path "/nw:networks/nw:network"
                 + "[nw:network-id=current()/../../nrp:network-ref]"
                 + "/nt:link/nt:link-id";
            }
            description
              "A reference to a link in the base topology specified
               by the 'network-ref' sibling node.";
          }
        }
        uses resource-reservation;
        leaf link-partition-type {
          type identityref {
            base nrp-link-partition-type;
          }
          description
            "Indicates the resource reservation type of an NRP link.";
        }
        uses phb-profile-ref;
      }
    }
  }

  /*
   * Grouping - NRP Policy
   */

  grouping nrp-pol {
    description
      "Grouping for NRP policies.";
    container nrp-policies {
      description
        "Container for nrp policies.";
      uses qos-profiles;
      list nrp-policy {
        key "name";
        unique "nrp-id";
        description
          "List of NRP policies.";
        leaf name {
          type string {
            length "1..max";
          }
          description
            "A string that uniquely identifies the NRP policy.";
        }
        leaf nrp-id {
          type uint32;
          mandatory true;
          description
            "A 32-bit ID that uniquely identifies the NRP
             created by the enforcement of this NRP policy.";
        }
        leaf mode {
          type identityref {
            base nrp-partition-mode;
          }
          mandatory true;
          description
            "Indicates the resource partition mode of the NRP, such
             as control plane partition, data plane partition,
             or hybrid partition.";
        }
        uses resource-reservation;
        uses selector-id;
        uses phb-profile-ref;
        container topology {
          description
            "Container for NRP topology.";
          uses igp-congruent;
          choice topology-type {
            description
              "Choice of NRP topology type.";
            case selection {
              uses select-topology;
            }
            case filter {
              uses topology-filter;
            }
          }
        }
      }
    }
  }

  /*
   * Grouping - NRP Selector ID State
   */

  grouping selector-id-state {
    description
      "The grouping of NRP selector ID state.";
    container selector-id {
      config false;
      description
        "The container of NRP selector ID.";
      leaf srv6 {
        type srv6-types:srv6-sid;
        description
          "SRv6 SID value.";
      }
      leaf mpls-nrp-selector {
        type uint32;
        description
          "MPLS NRP selector value.";
      }
    }
  }

  // nrp-link-statistics

  grouping statistics-per-link {
    description
      "Statistics attributes per NRP link.";
    container statistics {
      config false;
      description
        "Statistics for NRP link.";
      uses vpn-common:service-status;
      uses nrp-bandwidth-metrics;
      uses te-packet-types:one-way-performance-metrics-packet;
    }
  }

  /*
   * Grouping - NRP node attributes
   */

  grouping node-nrp-attributes {
    description
      "NRP node scope attributes.";
    container nrp-node-attributes {
      config false;
      description
        "Containing NRP attributes.";
      uses selector-id-state;
    }
  }

  /*
   * Grouping - NRP Link Attributes
   */

  grouping link-nrp-attributes {
    description
      "NRP link scope attributes.";
    container nrp-link-attributes {
      config false;
      description
        "Contains NRP link attributes.";
      leaf link-partition-type {
        type identityref {
          base nrp-link-partition-type;
        }
        description
          "Indicates the resource partition type of an NRP link.";
      }
      leaf bandwidth-value {
        type uint64;
        units "bits/second";
        description
          "Bandwidth allocation for the NRP as absolute value.";
      }
      uses selector-id-state;
      uses statistics-per-link;
    }
  }

  /*
   * Grouping - NRP Bandwidth Metrics
   */

  grouping nrp-bandwidth-metrics {
    description
      "Grouping for NRP bandwidth metrics.";
    leaf one-way-available-bandwidth {
      type uint64;
      units "bits/second";
      description
        "Available bandwidth that is defined to be NRP link
         bandwidth minus bandwidth utilization.";
    }
    leaf one-way-utilized-bandwidth {
      type uint64;
      units "bits/second";
      description
        "Bandwidth utilization that represents the actual
         utilization of the link (i.e., as measured in the router).";
    }
  }

  /*
   * Grouping - NRPs Node Attributes
   */

  grouping node-nrp-list-attributes {
    description
      "Grouping for NRPs nodes attributes.";
    container node-nrp-list {
      config false;
      description
        "Containing NRPs attributes.";
      list nrp {
        key "nrp-id";
        description
          "List of NRPs.";
        leaf nrp-id {
          type uint32;
          description
            "NRP identifier";
        }
        uses node-nrp-attributes;
      }
    }
  }

  /*
   * Grouping - NRPs Link Attributes
   */

  grouping link-nrp-list-attributes {
    description
      "Grouping for NRPs link attributes.";
    container link-nrp-list {
      config false;
      description
        "Contains NRPs link attributes.";
      list nrp {
        key "nrp-id";
        description
          "List of NRPs.";
        leaf nrp-id {
          type uint32;
          description
            "NRP identifier";
        }
        uses link-nrp-attributes;
      }
    }
  }

  // nrp-network-type

  grouping nrp-network-type {
    description
      "Identifies the network type to be NRP.";
    container nrp {
      presence "Indicates NRP network topology.";
      description
        "The presence of the container node indicates NRP network.";
    }
  }

  /*
   * Augment - Network Resource Partition Policies.
   */

  augment "/nw:networks" {
    description
      "Augments networks with NRP policies.";
    uses nrp-pol;
  }

  /*
   * Augment - NRP type.
   */

  augment "/nw:networks/nw:network/nw:network-types" {
    description
      "Indicates the network type of NRP";
    uses nrp-network-type;
  }

  /*
   * Augment - NRP node operational status.
   */

  augment "/nw:networks/nw:network/nw:node" {
    description
      "Augments node with NRP state attributes.";
    choice nrp-attachment-type {
      config false;
      description
        "Determines how NRP information is attached to node:
         single-nrp for NRP-specific topology, multi-nrp for
         native topology with multiple NRPs.";
      case single-nrp {
        when '../nw:network-types/nrp:nrp' {
          description
            "Condition: only applies to NRP network topologies.";
        }
        uses node-nrp-attributes;
      }
      case multi-nrp {
        description
          "Native topology with NRPs node operational status.";
        uses node-nrp-list-attributes;
      }
    }
  }

  /*
   * Augment - NRP link operational status.
   */

  augment "/nw:networks/nw:network/nt:link" {
    description
      "Augments link with NRP state attributes.";
    choice nrp-attachment-type {
      config false;
      description
        "Determines how NRP information is attached to link:
         single-nrp for NRP-specific topology, multi-nrp for
         native topology with multiple NRPs.";
      case single-nrp {
        when '../nw:network-types/nrp:nrp' {
          description
            "Condition: only applies to NRP network topology.";
        }
        uses link-nrp-attributes;
      }
      case multi-nrp {
        /*Native topology with NRPs link operational status.*/
        description
          "Native topology with NRPs link operational status.";
        uses link-nrp-list-attributes;
      }
    }
  }
}
