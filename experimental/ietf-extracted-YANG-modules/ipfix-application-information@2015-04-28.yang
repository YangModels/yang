module ipfix-application-information {
  yang-version 1;

  namespace "urn:ietf:params:xml:ns:yang:"
            + "ipfix-application-information";

  prefix ipfix-app-info;

  organization
     "IETF SFC (Service Function Chaining) Working Group";

  contact
      "Editor: Christophe Fontaine
       christophe.fontaine@qosmos.com

       Editor: Reinaldo Penno
       rapenno@gmail.com";

  description
     "This module contains a collection of YANG definitions for
      the configuration of application ids.

      Copyright (c) 2015 IETF Trust and the persons identified as
      authors of the code.  All rights reserved.

      Redistribution and use in source and binary forms, with or
      without modification, is permitted pursuant to, and subject
      to the license terms contained in, the Simplified BSD License
      set forth in Section 4.c of the IETF Trust's Legal Provisions
      Relating to IETF Documents
      (http://trustee.ietf.org/license-info).";

  revision 2015-04-28 {
    description "Initial revision";
    reference
       "draft-penno-sfc-appid : Using Application Identification in
        Services Function Chaining Metadata";
  }

  /*
   * Typedefs
   */

  typedef application-id-ref {
      type leafref {
          path "/ipfix-app-info:application-id-dictionary/"
          + "ipfix-app-info:application-id/ipfix-app-info"
          + ":application-name";
      }
      description "This type is used by data models that need
                   to reference an application-id";
  }

  typedef classification-engine-id {
    type enumeration {
      enum "IANA-L3" {
        value 1;
        description
          "IANA-L3";
      }
      enum "PANA-L3" {
        value 2;
        description
          "PANA-L3";
      }
      enum "IANA-L4" {
        value 3;
        description
          "IANA-L4";
      }
      enum "PANA-L4" {
        value 4;
        description
          "PANA-L4";
      }
      enum "USER-Defined" {
        value 6;
        description
          "USER-Defined";
      }
      enum "PANA-L2" {
        value 12;
        description
          "PANA-L2";
      }
      enum "PANA-L7" {
        value 13;
        description
          "PANA-L7";
      }
      enum "ETHERTYPE" {
        value 18;
        description
          "ETHERTYPE";
      }
      enum "LLC" {
        value 19;
        description
          "LLC";
      }
      enum "PANA-L7-PEN" {
        value 20;
        description
          "PANA-L7-PEN";
      }
    }
    description
      "The definitions for Classification engine ID names.";
    reference
       "RFC 6759: Cisco Systems Export of Application Information
        in IP Flow Information Export (IPFIX)";
  }
  /*
   * Configuration data nodes
   */

  container class-id-dictionary {
      description "Dictionary for classification ids";
      list class-id {
          key "name";
          unique "id";
          leaf id {
              type uint8;
              description "Classification identifier";
          }
          leaf name {
              type string;
              description "classification Engine name";
          }
          leaf description {
              type string;
              description "Description of the class-id";
          }
          description "A list of all classification ids";
      }
  }

  container application-id-dictionary {
      description "Dictionary for application ids";
      list application-id {
          key "application-name";
          unique "class-id pen selector-id";
          leaf class-id {
              type leafref {
                  path "/ipfix-app-info:class-id-dictionary/"
                       + "ipfix-app-info:class-id/ipfix-app-info:id";
              }
              mandatory true;
              description "Application Name";
          }
          leaf pen {
              type uint32;
              mandatory true;
              description "Private Entreprise Number, only relevant
                           when used with appropriate class-id.
                           Set to 0 when not used.";
          }
          leaf selector-id {
              type uint32 {
                  range "0..16777216";
              }
              mandatory true;
              description "Selector identifier";
          }
          leaf application-name {
              type string;
              mandatory true;
              description "The name of the application";
          }
          leaf application-description {
              type string;
              description "The description of the application";
          }
          leaf application-category-name {
              type string;
              description "An attribute that provides a first-
                           level categorization for each
                           Application ID.  Examples include
                           browsing, email, file-sharing,
                           gaming, instant messaging, voice-
                           and-video, etc.
                           The category attribute is encoded by
                           the application-category-name
                           Information Element";
          }
          leaf application-sub-category-name {
              type string;
              description "An attribute that provides a second-
                           level categorization for each
                           Application ID.  Examples include
                           backup-systems, client-server,
                           database, routing-protocol, etc.
                           The sub-category attribute is
                           encoded by the
                           application-sub-category-name
                           Information Element";
          }
          leaf application-group-name {
              type string;
              description "An attribute that groups multiple
                           Application IDs that belong to the
                           same networking application.  For
                           example, the ftp-group contains
                           ftp-data (port 20), ftp (port 20),
                           ni-ftp (port 47), sftp (port 115),
                           bftp (port 152), ftp-agent(port
                           574), ftps-data (port 989).  The
                           application-group attribute is
                           encoded by the application-group-name
                           Information Element";
           }
          description "A list of all applications";
      }
  }
}
