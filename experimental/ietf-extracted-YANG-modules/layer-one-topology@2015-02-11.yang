module layer-one-topology { 
  yang-version 1; 

  namespace "urn:ietf:params:xml:ns:yang:layer-one-topology"; 
  prefix l1topo; 

  import ietf-inet-types {  
  prefix inet;  
  } 

  organization "Internet Engineering Task Force (IETF) I2RS WG"; 
  contact 
    "ID-draft editor: zhang.xian@huawei.com"; 
  description 
    "This module defines a data-plan technology/protocol independent 
Layer One topology data model."; 

  revision 2015-02-11 { 
    description 
      "Initial version"; 

    reference 
     "TBD: draft-zhang-i2rs-l1-topo-yang-model-00.txt"; 
  } 
  /* 
   * Typedefs 
   */ 

  typedef topology-id { 
    type inet:uri; 
  } 

  typedef node-id { 
    type inet:ip-address; 
  } 

  typedef interface-id { 
    type union {  
       type inet:ip-address; // IPv4 or IPv6 address 
       type int32;          // Unnumbered   
    }  
    description 
    "the identifier of an interface within a node, supporting both 
numbered/unumbered"; 
  } 

  typedef link-id { 
   type inet:ip-address; // IPv4 or IPv6 address  
    description 
    "the identifier of a link"; 
  } 

  typedef switching-capabilities {    
    type enumeration {  
      enum "psc-1" {          
        value 1;  
        description  
          "Packet-Switch Capable-1 (PSC-1)";  
      }  
      enum "evpl" {  
        value 30;  
        description  
          "Ethernet Virtual Private Line (EVPL)";  
      }  

      enum "pbb-te"{ 
      value 40; 
      description 
        "802_1 PBB-TE"; 
      } 
      enum "l2sc" {  
        value 51;  
        description  
          "Layer-2 Switch Capable (L2SC)";  
      }  
      enum "tdm" {  
        value 100;  
        description  
          "Time-Division-Multiplex Capable (TDM)";  
      }  
      enum "otn-tdm" {  
        value 110;  
        description  
          "OTN-TDM Capable";  
      }  
      enum "lsc" {  
        value 150;  
        description  
          "Lambda-Switch Capable (LSC)";  
      }  
      enum "fsc" {  
        value 200;  
        description  
          "Fiber-Switch Capable (FSC)";  
      }  
    }  

    description 
     "Switching capability of an interface.  
     Only a subset of the above-mentioned values are applicable to 
Layer 1 network. Here it is included for completeness and will later 
be updated if a base model is augmented to create layer 1 network 
topology YANG data model."; 

    reference 
     "The definition of switching types, their values and the 
relevant RFCs (i.e., RFC3471, 4328) can be found at: 
     http://www.iana.org/assignments/gmpls-sig-parameters/gmpls-
sig-parameters.xhtml#gmpls-sig-parameters-3"; 
  }  

  typedef encoding-types {  
    type enumeration {  
      enum "packet" {          
        value 1;  
        description  
          "Packet";  
      }  
      enum "ethernet" {          
        value 2;  
        description  
           "Ethernet";  
      }  
      enum "pdh" {          
        value 3;  
        description  
          "PDH";  
      }  
      enum "sdh-sonet" {          
        value 5;  
        description  
          "SDH/SONET";  
      }  
      enum "digital-wrapper" {          
        value 7;  
        description  
          "Digital Wrapper";  
      }  
      enum "lambda" {          
        value 8;  
        description  
          "Lambda(photonic)";  
      }  
      enum "fiber" {          
        value 9;  
        description  
          "Fiber";  
      }  
      enum "fiber-channel" {          
        value 11;  
        description  
          "FiberChannel";  
      }  
      enum "oduk" {          
        value 12;  
        description  
          "G.709 OKUk (Digital Path)";  
      }  
      enum "optical-channel" {          
        value 13;  
        description  
          "G.709 Optical Channel";  
      }  
      enum "line" {          
        value 14;  
        description  
          "Line (e.g., 8B/10B)";  
      } 
    }  
    description  
      "The encoding type supported by an interface or link.  
       Not all encoding types are applicable to Layer one network 
nodes. They are included here for completeness and will be updated 
if a base model is available to augment so as to build a layer-one 
specific YANG data model.";  
    reference 
     "The definition of encoding types, their values and the 
relevant RFCs (RFC3471, RFC4328, RFC6004) can be found at 
http://www.iana.org/assignments/gmpls-sig-parameters/gmpls-sig-
parameters.xhtml#gmpls-sig-parameters-3"; 
  } 

  /* 
   * Groupings 
   */ 

  grouping srlg-attribute {  
    description  
      "Shared Risk Link Group Attributes";  
    reference  
      "RFC 4203: OSPF Extensions in Support of Generalized Multi-
Protocol Label Switching (GMPLS)";  
    list srlg-values {  
      key "srlg-value";  
      leaf srlg-value {  
        type uint32;  
      }  
    }  
  }  

  /* 
   * Configuration data nodes 
   */ 

  container layer-one-topology { 
    list topology { 
      key "topology-id"; 
      leaf topology-id { 
        type topology-id; 
      } 

      leaf name { 
        type string; 
      } 

      list supporting-topology { 
        key "topo-ref"; 
        leaf topo-ref { 
          type leafref { 
            path "/layer-one-topology/topology/topology-id"; 
          } 
        description 
         "a Layer-One network might be supported by a lower layer 
network and this is a pointer to the suporting topology if there is 
one"; 
        } 
      } 

      list node { 
        key "node-id"; 
        leaf node-id { 
          type node-id; 
        } 
        list interface { 
          key "interface-id"; 
          leaf interface-id { 
            type interface-id; 
          } 
          container adaptation-capability { 
            presence "to define adaptation capability for different 
technologies."; 
           description 
             "TBD"; 
          } 
        } 
        list connectivity-matrix { 
          key "id"; 

          description 
           "This describes the connectivity contraints within a 
node in the network. It can  be one matrix or a set of matrixes. 
Further details, read the reference provided below."; 
          reference 
            "https://tools.ietf.org/html/draft-ietf-ccamp-general-
constraint-encode-16 Section 2.1";  
          leaf id { 
            type uint32; 
          } 
          leaf type { 
            type enumeration { 
              enum fixed { 
                value 0; 
              } 
              enum dynamic { 
                value 1; 
              } 
            } 

            description 
            "This field describes the attribute of a connectivity 
matrix, i.e., whether it is fixed or switched."; 
          } 
          list in-interface { 
            key "interface-ref"; 

          description 
             "This list describes a (sub)-set of ingoing-
interfaces within a node that may have connectivity constraints. 
           Note: directionality may not be relevant and it is 
decided by the dir parameter."; 

            leaf interface-ref {             
            type leafref { 
                path "/layer-one-
topology/topology/node/interface/interface-id"; 
              } 
            } 
          } 
          list out-interface { 
            key "interface-ref"; 

          description 
           "This list describes a (sub)-set of ingoing-
interfaces within a node that may have connectivity constraints. 
           Note: directionality may not be relevant and it is 
decided by the dir parameter."; 

            leaf interface-ref { 
              type leafref { 
                path "/layer-one-
topology/topology/node/interface/interface-id"; 
              } 
            } 
          } 
          leaf dir{ 
            type enumeration{ 
            enum "uni-dir"{ 
              description 
                "the matrix is unidirectional."; 
            } 
            enum "bi-dir"{ 
              description 
                "this matrix is bidirecdtional."; 
            } 
            } 
          } 
        } 
      } 

      list link { 
      key "link-id"; 
      leaf link-id { 
          type link-id; 
          description 
            "remaining issue: if there is no IP addresses 
associated with this link,  
            what would be the key?"; 
      } 

        container local { 
         leaf local-node { 
           type leafref { 
            path "/l1topo:layer-one-topology/topology/node/node-id"; 
           } 
         } 
         leaf local-interface { 
           type leafref { 
            path "/l1topo:layer-one-
topology/topology/node/interface/interface-id"; 
           } 
         } 
      } 
      container remote { 
         leaf remote-node { 
           type leafref { 
              path "/l1topo:layer-one-topology/topology/node/node-
id"; 
           } 
         } 
         leaf remote-interface { 
           type leafref { 
            path "/l1topo:layer-one-
topology/topology/node/interface/interface-id"; 
           } 
         } 
      } 
      list supporting-path { 
         key "supporting-path-index"; 
         leaf supporting-path-index { 
           type uint32; 
         } 
         leaf topo-ref { 
           type leafref { 
            path "/l1topo:layer-one-topology/topology/topology-id"; 
           } 
         } 
         container server-path-identifier { 
           presence "Define server path identifier."; 
         } 
         container server-path-srlg { 
           uses srlg-attribute; 
         } 
      } 

      container te-attributes { 
         leaf link-index { 
           type uint64; 
         } 
         leaf information-source { 
          type enumeration {  
            enum "unknown" {  
              description  
               "The source is unknown";  
            }  
            enum "locally-configured" {  
              description  
               "Configured TE link";  
            }  
            enum "ospfv2" {  
              description  
               "OSPFv2";  
            }  
            enum "ospfv3" {  
              description  
               "OSPFv3";  
            }  
            enum "isis" {  
              description  
               "ISIS";  
            }  
           } 
           config false;  

           description   
            "Indicates the source of the information about the link. 
             remaining issue: if configuration of a link is allowed, 
what additional types are needed to add?";  
         } 
         leaf credibility-preference { 
           type uint16; 
           config false; 
         } 
         leaf admin-status {  
           type enumeration {  
             enum up {  
              value 1;  
              description  
                "up";  
            }  
            enum down {  
              value 2;  
              description  
                "down";  
            }  
            enum testing {  
              value 3;  
              description  
                "testing - in some test mode.";  
            }  
          }  
          description  
            "The adminstrative state of the link.";  
          reference 
           "RFC2863: The Interfaces Group MIB."; 
        }  
        leaf oper-status {  
          type enumeration {  
            enum up {  
              value 1;  
              description  
                "up";  
            }  
            enum down {  
              value 2;  
              description  
                "down";  
            }  
            enum testing {  
              value 3;  
              description  
                "testing - in some test mode";  
            }  
            enum unknown {  
              value 4;  
              description  
                "unknown - status cannot be determined for some 
reason.";  
            } 
            enum dormant{ 
              value 5; 
            } 
          }  
          config false; 
          description  
            "The current operational state of the link.";  
          reference 
           "RFC2863: The Interfaces Group MIB."; 
        }  
        leaf area-id {  
          type binary {  
            length 1..13;  
          }  
          description  
            "This object indicates the area identifier of the IGP, 
it can identify either a OSPF or ISIS area.";  
           reference 
           "RFC4920:  Crankback Signaling Extensions for MPLS and 
GMPLS RSVP-TE."; 
        } 

        leaf max-link-bandwidth { 
          type decimal64 { 
            fraction-digits 2; 
          } 
          description 
           "the max bandwidth supported by this link"; 
        } 

        list unreserved-bandwidth { 
          key "priority"; 
          max-elements "8"; 

          description 
           "This describes the unreserved bandwidth (in 
Bytes/second) on a level basis ( level 0-7)."; 

          leaf priority { 
            type uint8{ 
            range "0..7"; 
            } 
          } 
          leaf bandwidth { 
            type decimal64 { 
              fraction-digits 2; 
            } 
          } 
        } 

        leaf distance { 
         type  uint32; 
         units "kilometers"; 

         config false; 
         description 
           "the distance this link spans."; 
        } 
        leaf te-default-metric { 
          type uint32; 
        } 

        leaf link-protection-type { 
          type enumeration {  
             enum "extra-traffic" {  
              description "Extra traffic";  
            }  
             enum "unprotected" {  
              description "unprotected";  
            }  
            enum "shared" {  
              description "Shared";  
            }  
            enum "1-for-1" {  
              description "Dedicated one for one protection";  
            }  
            enum "1-plus-1" {  
              description "Dedicated one plus one protection";  
            }  
            enum "enhanced" {  
              description "a protection type that is more reliable 
than Dedicated 1-plus-1, e.g., 4 fiber BLSR/MS-SPRING.";  
            }  
          }  
          description  
            "Link Protection Type configured for this link"; 
          reference 
           "RFC3471: Generalized MUlti-Protocol Label Switching 
(GMPLS) Signaling Functional Description.";  
        } 
        list interface-Switching-capability { 
          key "switching-capability"; 
          leaf switching-capability { 
            type switching-capabilities; 
          } 
          leaf encoding { 
            type encoding-types; 
            description 
              "the encoding type supported by this link."; 
          } 
          list max-lsp-bandwidth { 
            key "priority"; 
            max-elements "8"; 
            leaf priority { 
              type uint8 { 
                range "0..7"; 
              } 
            } 
            leaf bandwidth {  
              type decimal64 {  
                fraction-digits 2; 
              } 
            } 
            description 
             "remaining issue: to check how is used."; 
          } 
          container switching-capability-specific-information { 
            presence "to define switch capability specific 
information for technology specific network (e.g., OTN)."; 
          } 
        } 
        container srlg { 
          uses srlg-attribute; 
        } 
      } 
    } 
  } 
  }   
}
