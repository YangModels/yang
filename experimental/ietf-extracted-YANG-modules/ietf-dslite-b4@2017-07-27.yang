module ietf-dslite-b4 {
    namespace "urn:ietf:params:xml:ns:yang:ietf-dslite-b4";
    prefix dslite-b4;

    import ietf-inet-types { prefix inet; }

    organization "Softwire Working Group";
    contact
     "Mohamed Boucadair <mohamed.boucadair@orange.com>
      Christian Jacquenet <christian.jacquenet@orange.com>
      Senthil Sivakumar <ssenthil@cisco.com>";

   description
      "This module is a YANG module for DS-Lite B4 implementations.

      Copyright (c) 2017 IETF Trust and the persons identified as
      authors of the code.  All rights reserved.
      Redistribution and use in source and binary forms, with or
      without modification, is permitted pursuant to, and subject
      to the license terms contained in, the Simplified BSD License
      set forth in Section 4.c of the IETF Trust's Legal Provisions
      Relating to IETF Documents
      (http://trustee.ietf.org/license-info).

      This version of this YANG module is part of RFC XXXX; see
      the RFC itself for full legal notices.";

    revision 2017-07-27 {
      description "Separate B4 from AFTR.";
       reference "-ietf-04";
    }

container dslite-b4 {

    description
     "dslite-b4";

    leaf enable {
        type boolean;
        description
         "Enable/disable dslite-b4 function.";
    }

    container dslite-b4-instances {
       description
         "dslite-b4 instances";

        list dslite-b4-instance {
            key "id";
              description
                "a dslite-b4 instance.";

           leaf id {
              type uint32;
              description
                "dslite-b4 instance identifier.";
           }

           leaf name {
              type string;
              description
                "A name associated with the dslite-b4 instance.";
           }

          leaf aftr-ipv6-addr {
              type inet:ipv6-address;
              mandatory true;
              description
                 "The AFTR's IPv6 address.";

              reference
                 "RFC 6333.";
           }

    leaf ipv4-address {
        type inet:ipv4-address;
        default "192.0.0.2";
        description
          "IPv4 address of the DS-Lite B4.
          192.0.0.0/29 is reserved for the B4 element
          [RFC6333].
          This address can be used to report ICMP
          problems and will appear in traceroute
          outputs.";

        reference
             "RFC 6333.";
    }

    leaf tunnel-mtu {
        type uint16;
        description
            "Configures a tunnel MTU.
            [RFC6908] specifies that since
            fragmentation and reassembly is not
            optimal, the operator should do
            everything possible to eliminate
            the need for it.  If the operator uses
            simple IPv4-in-IPv6 softwire, it is
            recommended that the MTU size of the IPv6
            network between the B4 and the AFTR
            accounts for the additional overhead
            (40 bytes).";

         reference
             "RFC 6908.";
    }

    leaf v6-v4-dscp-preservation {
        type boolean;
        mandatory true;
        description
         "Copies the DSCP value from the IPv6 header
         and vice versa.
         According to Section 2.10 of [RFC6908],
         operators should use this model
         by provisioning the network such that
         the AFTR copies the DSCP value in the IPv4
         header to the Traffic Class field in
         the IPv6 header, after the encapsulation
         for the downstream traffic.";
    }
    }
  }
 }
}
