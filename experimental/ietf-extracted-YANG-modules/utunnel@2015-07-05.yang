module utunnel  {
    namespace "urn:ietf:params:xml:ns:yang:ietf-utunnel";
    // replace with IANA namespace when assigned
    prefix "utunnel";

    import ietf-inet-types {
        prefix "inet";
    }

    import ietf-routing {
        prefix "rt";
    }

    organization "huawei";
    contact
       "lizhenbin@huawei.com
        xiachen@huawei.com
        vinods.kumar@huawei.com";

    description "unified tunnel model";
    revision "2015-07-05" {
        description "Initial revision";
        reference "TBD";
    }

    typedef tunnel-id {
        type uint32;
        description
            "An identifier for a tunnel.";
    }

    typedef tunnel-name {
         type string {
             length "1..64";
         }
    }

    typedef tunnel-protocol{
        type enumeration {
            enum ldp {
                value "0";
            }
            enum rsvp-te {
                value "1";
            }
            enum bgp {
                value "2";
            }
            enum cr-static-lsp {
                value "3";
            }
            enum gre {
                value "4";
            }
            enum ipsec {
                value "5";
            }
            enum vxlan {
                value "6";
            }
            enum segment-routing-best-effort {
                value "7";
            }
            enum segment-routing-te {
                value "8";
            }
        }
    }
    typedef tunnel-status {
        type enumeration {
            enum up {
                value "0";
                description
                "The status of tunnel is up.";
            }
            enum down {
                value "1";
                description
                "The status of tunnel is down.";
            }
        }
    }

    container utunnel{
        config false;
        description "The information of unified tunnel. The tunnels include p2p, mp2p and p2mp tunnel.
         P2p and mp2p tunnel use the same container with name p2ptunnels. P2mp tunnel is defined later.";

        container p2ptunnels{
            list tunnel {
                key "vrf-name tunnel-protocol tunnel-id";
                leaf vrf-name {
                    type rt:routing-instance-ref;
                    description "The name of vrf. Some tunnels like ldp can be from specific vrf or default vrf.
                                 And some tunnels like rsvp-te are only from the default vrf.";
                }
                leaf tunnel-protocol {
                    type tunnel-protocol;
                    description "The type of tunnel protocol which can be ldp, gre, bgp etc.";
                }
                leaf tunnel-id {
                    type tunnel-id;
                    description "The identifier of tunnel which can be uniquely represented a tunnel with vrf-name and tunnel-protocol.";
                }
                leaf tunnel-name {
                    type tunnel-name;
                    description "The name of tunnel.";
                }
                leaf oper-status {
                    type tunnel-status;
                    description "The status of tunnel which can be up or down.";
                }
                container address-family {
                    description "ipv4 or ipv6 address family.";

                    container ipv4 {
                        description "IPv4 address family.";
                        leaf destination {
                            type inet:ipv4-address;
                            description "The destination is ipv4 address.";
                        }
                    }  // ipv4
                    container ipv6 {
                        description "IPv6 address family.";
                        leaf destination {
                            type inet:ipv6-address;
                            description "The destination is ipv6 address.";
                        }
                    }  // ipv6
                }
            }
        }
    }
}
