module ietf-poweff-static {
  yang-version 1.1;
  namespace "urn:ietf:params:xml:ns:yang:ietf-poweff-static";
  prefix ietf-poweff-static;

  import ietf-poweff-sensors {
    prefix ietf-poweff-sensors;
  }
  import ietf-lmo {
    prefix ietf-lmo;
  }
  import ietf-lmo-assets-inventory {
    prefix ietf-lmo-asset;
  }
  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
    Editor:  Marisol Palmero
              <mailto:mpalmero@cisco.com>          ";
  description
    "This YANG module includes power and energy efficiency
    Product Data. Data for a specific asset that aligns to values
    provided by the manufacturer can be classified as âstaticâ
    since they are unlikely to change during the lifetime of the
    product/asset.
    They are typically available in a form of data sheets or any kind
    of simulation tools.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";

  revision 2023-10-12 {
    description
      "Initial revision to document power static data";
    reference
      "RFC XXXX: ...";
  }
  augment /ietf-lmo:lmos/ietf-lmo:lmo/ietf-lmo:inst {
    when "derived-from-or-self(../ietf-lmo:lmo-class, "+
         " 'ietf-lmo-asset:asset')";
    description
      "Assets attributes related to power static attributes";

    uses ietf-poweff-sensors:power-static-g;
  }
}
