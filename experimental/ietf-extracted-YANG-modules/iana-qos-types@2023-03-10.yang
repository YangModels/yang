module iana-qos-types {
  yang-version 1.1;
  namespace "urn:ietf:params:xml:ns:yang:iana-qos-types";
  prefix qos-types;

  organization
    "IETF Routing Area Working Group";

  contact
    "WG Web:   <https://datatracker.ietf.org/wg/rtgwg/>
     WG List:  <mailto:rtgwg@ietf.org>

     Editor:   Aseem Choudhary
               <mailto:asechoud@cisco.com>
     Editor:   Mahesh Jethanandani
               <mailto:mjethanandani@gmail.com>";

  description
    "This module contains type definitions for all QoS types.

     Copyright (c) 2022 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2023-03-10 {
    description
      "Initial version";
    reference
      "RFC XXXX: YANG Models for Quality of Service (QoS).";
  }

  /*
   * Features.
   */
  feature child-policy {
    description
      " This feature allows configuration of hierarchical policy.";
  }
  feature count {
    description
      "This feature allows action configuration to enable
       counter in a classifier";
  }
  feature named-counter {
    description
      "This feature allows action configuration to enable
       named counter in a classifier";
  }

  /*
   * Identities.
   */
  identity policy-type {
    description
      "This base identity type defines policy-types";
  }
  identity diffserv-policy-type {
    base policy-type;
    description
      "This defines ip policy-type";
  }
  identity ipv4-diffserv-policy-type {
    base policy-type;
    description
      "This defines ipv4 policy-type";
  }
  identity ipv6-diffserv-policy-type {
    base policy-type;
    description
      "This defines ipv6 policy-type";
  }
  identity queue-policy-type {
    base policy-type;
    description
      "This defines queue policy-type";
  }
  identity scheduler-policy-type {
    base policy-type;
    description
      "This defines scheduler policy-type";
  }

  identity action-type {
    description
      "This base identity type defines action-types";
  }
  identity dscp-marking {
    base action-type;
    description
      "dscp marking action type";
  }
  identity meter-inline {
    base action-type;
    description
      "meter-inline action type";
  }
  identity meter-reference {
    base action-type;
    description
      "meter reference action type";
  }
  identity queue {
    base action-type;
    description
      "queue action type";
  }
  identity scheduler {
    base action-type;
    description
      "scheduler action type";
  }
  identity discard {
    base action-type;
    description
      "discard action type";
  }
  identity child-policy {
    if-feature child-policy;
    base action-type;
    description
      "child-policy action type";
  }
  identity count {
    if-feature count;
    base action-type;
    description
      "count action type";
  }
  identity named-counter {
    if-feature named-counter;
    base action-type;
    description
      "name counter action type";
  }
  identity queue-policy-name {
    base action-type;
    description
      "queue policy name";
  }

  identity meter-type {
    description
      "This base identity type defines meter types";
  }
  identity one-rate-two-color {
    base meter-type;
    description
      "one rate two color meter type";
  }
  identity one-rate-tri-color {
    base meter-type;
    description
      "one rate three color meter type";
  }
  identity two-rate-tri-color {
    base meter-type;
    description
      "two rate three color meter action type";
  }

  identity drop-type {
    description
      "drop algorithm";
  }
  identity tail-drop {
    base drop-type;
    description
      "tail drop algorithm";
  }
  identity red {
    base drop-type;
    description
      "Random Early Detect drop algorithm";
  }
  identity wred {
    base drop-type;
    description
      "Weighted Random Early Detect drop algorithm";
  }

  identity rate-unit-type {
    description
      "base rate-unit type";
  }
  identity bits-per-second {
    base rate-unit-type;
    description
      "bits per second identity";
  }
  identity kilo-bits-per-second {
    base rate-unit-type;
    description
      "kilo bits per second identity";
  }
  identity mega-bits-per-second {
    base rate-unit-type;
    description
      "mega bits per second identity";
  }
  identity giga-bits-per-second {
    base rate-unit-type;
    description
      "mega bits per second identity";
  }
  identity percent {
    base rate-unit-type;
    description
      "percentage";
  }

  identity burst-unit-type {
    description
      "base burst-unit type";
  }
  identity bytes {
    base burst-unit-type;
    description
      "bytes";
  }
  identity kilo-bytes {
    base burst-unit-type;
    description
      "kilo bytes";
  }
  identity mega-bytes {
    base burst-unit-type;
    description
      "mega bytes";
  }
  identity millisecond {
    base burst-unit-type;
    description
      "milli seconds";
  }
  identity microsecond {
    base burst-unit-type;
    description
      "micro seconds";
  }
  identity red-threshold-unit {
    description
      "base red-unit type";
  }
  identity red-threshold-bytes {
    base red-threshold-unit;
    description
      "bytes";
  }
  identity red-threshold-kb {
    base red-threshold-unit;
    description
      "kilo bytes";
  }
  identity red-threshold-mb {
    base red-threshold-unit;
    description
      "mega bytes";
  }
  identity red-threshold-ms {
    base red-threshold-unit;
    description
      "milli seconds";
  }
  identity red-threshold-us {
    base red-threshold-unit;
    description
      "micro seconds";
  }
  identity red-threshold-pc {
    base red-threshold-unit;
    description
      "per-centage";
  }
  identity red-theshold-pt {
    base red-threshold-unit;
    description
      "per-thousand";
  }
  identity red-threshold-pm {
    base red-threshold-unit;
    description
      "per-million";
  }
  identity wred-color-type {
    description
      "base wred color type";
  }
  identity wred-color-dscp {
    base wred-color-type;
    description
      "dscp wred color type";
  }

  identity probability-unit {
    description
      "base probability unit type";
  }
  identity probability-pc {
    base probability-unit;
    description
      "probability in percentage";
  }
  identity probability-pt {
    base probability-unit;
    description
      "probability in per thousand";
  }
  identity probability-pm {
    base probability-unit;
    description
      "probability in per million";
  }
  identity probability-denominator {
    base probability-unit;
    description
      "probability value is denominator value
       while numerator is always 1";
  }

  identity filter-type {
    description
      "This is identity of base filter-type";
  }

  identity dscp {
    base filter-type;
    description
      "Differentiated services code point filter-type";
  }
  identity source-ipv4-prefix {
    base filter-type;
    description
      "source ipv4 prefix filter-type";
  }
  identity destination-ipv4-prefix {
    base filter-type;
    description
      "destination ipv4 prefix filter-type";
  }
  identity source-ipv6-prefix {
    base filter-type;
    description
      "source ipv6 prefix filter-type";
  }
  identity destination-ipv6-prefix {
    base filter-type;
    description
      "destination ipv6 prefix filter-type";
  }
  identity source-port {
    base filter-type;
    description
      "source port filter-type";
  }
  identity destination-port {
    base filter-type;
    description
      "destination port filter-type";
  }
  identity protocol {
    base filter-type;
    description
      "protocol type filter-type";
  }
  identity traffic-group-name {
    base filter-type;
    description
      "traffic-group filter type";
  }
  identity filter-match-all {
    base filter-type;
    description
      "Traffic-group filter type";
  }

  typedef match-operation-type {
    type enumeration {
      enum match-all {
        description
          "Classifier entry filters logical AND operation";
      }
      enum match-any {
        description
          "Classifier entry filters logical OR operation";
      }
    }
    default "match-all";
    description
      "Filter match logical operation type";
  }

  identity direction {
    description
      "This is identity of traffic direction";
  }
  identity inbound {
    base direction;
    description
      "Direction of traffic coming into the network entry";
  }
  identity outbound {
    base direction;
    description
      "Direction of traffic going out of the network entry";
  }
  identity meter-action-type {
    description
      "Base identify for actions related to metering";
  }
  identity action-drop {
    base meter-action-type;
      description
        "Drop packets that conform/exceed/violate to the set value.";
  }
  identity action-transmit {
    base meter-action-type;
      description
        "Transmit packets that conform/exceed/violate to the set
         value.";
  }
  identity action-mark {
    base meter-action-type;
      description
        "Mark packets that conform/exceed/violate to the set value.";
  }

  identity clear-counters-type {
    description
      "Base identify for clear interface counters related options";
  }
  identity all-counters {
    base clear-counters-type;
      description
        "clear all counters in both directions";
  }
  identity inbound-counters {
    base clear-counters-type;
      description
        "clear counters in inbound direction";
  }
  identity outbound-counters {
    base clear-counters-type;
      description
        "clear counters in outbound direction";
  }
}
