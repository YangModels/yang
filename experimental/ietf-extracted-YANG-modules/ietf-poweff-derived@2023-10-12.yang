module ietf-poweff-derived {
  yang-version 1.1;
  namespace "urn:ietf:params:xml:ns:yang:ietf-poweff-derived";
  prefix ietf-poweff-derived;

  import ietf-poweff-sensors {
    prefix ietf-poweff-sensors;
  }
  import ietf-lmo {
    prefix ietf-lmo;
  }
  import ietf-lmo-assets-inventory {
    prefix ietf-lmo-asset;
  }
  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
    Editor:  Marisol Palmero
              <mailto:mpalmero@cisco.com>";
  description
    "This YANG module includes power derived values per asset.
    Typically, power derived values will be calculated on the
    receiver, even those values may be provided by the devices as
    well.
    Typically we expect chassis to report total psu-input-power and
    psu-output-power but ptr-bps-ratio may be derived on the receiver
    side.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";

  revision 2023-10-12 {
    description
      "Initial revision to document power derived data";
    reference
      "RFC XXXX: ...";
  }

  augment /ietf-lmo:lmos/ietf-lmo:lmo/ietf-lmo:inst {
    when "derived-from-or-self(../ietf-lmo:lmo-class, "+
         " 'ietf-lmo-asset:asset')";
    description
      "Power derived attributes related to assets";

    uses ietf-poweff-sensors:power-derived-g;
  }
}
