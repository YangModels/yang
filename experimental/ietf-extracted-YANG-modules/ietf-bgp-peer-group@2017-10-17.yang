submodule ietf-bgp-peer-group {
  belongs-to ietf-bgp {
    prefix "bgp";
  }

  import ietf-routing-policy {
    prefix rpol;
  }

  // Include the common submodule
  include ietf-bgp-common;
  include ietf-bgp-common-multiprotocol;
  include ietf-bgp-common-structure;

  // meta
  organization
    "IETF IDR Working Group";

  contact
    "WG Web:   <http://tools.ietf.org/wg/idr>
     WG List:  <idr@ietf.org>

     Editor:  Mahesh Jethanandani (mjethanandani@gmail.com)
     Authors: Keyur Patel,
              Mahesh Jethanandani,
              Susan Hares";

  description
    "This sub-module contains groupings that are specific to the
    peer-group context of the BGP module.";

  revision "2017-10-17" {
    description
      "Initial Version";
    reference
      "RFC XXX, BGP Model for Service Provider Network.";
  }

  grouping bgp-peer-group-config {
    description
      "Configuration parameters relating to a base BGP peer group
       that are not also applicable to any other context (e.g.,
       neighbor)";

    leaf peer-group-name {
      type string;
      description
        "Name of the BGP peer-group";
    }

  }

  grouping bgp-peer-group-afi-safi-list {
    description
      "List of address-families associated with the BGP peer-group";

    list afi-safi {
      key "afi-safi-name";

      description
        "AFI,SAFI configuration available for the
        neighbour or group";

      uses bgp-common-mp-afi-safi-config;

      container graceful-restart {
        description
          "Parameters relating to BGP graceful-restart";

        uses bgp-common-mp-afi-safi-graceful-restart-config;
      }

      uses bgp-common-route-selection-options;
      uses bgp-common-global-group-use-multiple-paths;
      uses bgp-common-mp-all-afi-safi-list-contents;
    }
  }

  grouping bgp-peer-group-base {
    description
      "Parameters related to a BGP group";

    uses bgp-peer-group-config;
    uses bgp-common-neighbor-group-config;
    uses bgp-common-state;

    container timers {
      description
        "Timers related to a BGP peer-group";

      uses bgp-common-neighbor-group-timers-config;
    }

    container transport {
      description
        "Transport session parameters for the BGP peer-group";

      uses bgp-common-neighbor-group-transport-config;
    }

    container error-handling {
      description
        "Error handling parameters used for the BGP peer-group";

      uses bgp-common-neighbor-group-error-handling-config;
    }

    container graceful-restart {
      description
        "Parameters relating the graceful restart mechanism for BGP";

      uses bgp-common-graceful-restart-config;
    }

    uses bgp-common-structure-neighbor-group-logging-options;
    uses bgp-common-structure-neighbor-group-ebgp-multihop;
    uses bgp-common-structure-neighbor-group-route-reflector;
    uses bgp-common-structure-neighbor-group-as-path-options;
    uses bgp-common-structure-neighbor-group-add-paths;
    uses bgp-common-global-group-use-multiple-paths;
    uses rpol:apply-policy-group;

    container afi-safis {
      description
        "Per-address-family configuration parameters associated with
        thegroup";
      uses bgp-peer-group-afi-safi-list;
    }
  }

  grouping bgp-peer-group-list {
    description
      "The list of BGP peer groups";

    list peer-group {
      key "peer-group-name";
      description
        "List of BGP peer-groups configured on the local system -
         uniquely identified by peer-group name";

      uses bgp-peer-group-base;
    }
  }
}
