module service-function {

  namespace "urn:cisco:params:xml:ns:yang:sfc-sf";

  prefix sfc-sf;

  import ietf-inet-types { prefix inet; }
  import ietf-yang-types { prefix yang; }
  import service-function-type {prefix sfc-sft;}
  import service-locator {prefix sfc-sl;}

  organization "Cisco Systems, Inc.";
  contact "Reinaldo Penno <repenno@cisco.com>";

  description
    "This module contains a collection of YANG definitions for
     managing service function.

     It follows closely the constructs of
     http://tools.ietf.org/html/draft-ietf-netmod-interfaces-cfg-12

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
    "Changes based on Opendaylight Testing.";
  }

  typedef service-function-ref {
    type leafref {
      path "/sfc-sf:service-functions/sfc-sf:service-function/sfc-sf:name";
    }
    description
      "This type is used by data models that need to reference
       configured service functions.";
  }

  grouping service-function-entry {
    leaf name {
      type string;
      description
          "The name of the service function.";
    }
    leaf type {
      type string;
      mandatory true;
      description
        "Service Function Type from service-function-type.yang.";
    }
    leaf ip-mgmt-address {
      type inet:ip-address;
    }
    container sf-data-plane-locator {
      uses sfc-sl:data-plane-locator;
    }

    leaf service-function-forwarder {
      type string;
      mandatory true;
      description
        "The service function forwarders associated with this Service Function";
    }
  }

  container service-functions {
    description
      "A network or application based packet
      treatment, application, compute or storage resource, used
      singularly or in concert with other service functions within a
      service chain to enable a service offered by an operator.

      A non-exhaustive list of Service Functions includes: firewalls,
      WAN and application acceleration, Deep Packet Inspection (DPI),
      server load balancers, NAT44 [RFC3022], NAT64 [RFC6146], HOST_ID
      injection, HTTP Header Enrichment functions, TCP optimizer, etc.";

    list service-function {
      key "name";
      uses service-function-entry;
    }
  }

  container service-functions-state {
    config false;
    list service-function-state {
      description
        "A service chain defines the required functions and
        associated order (service-function1 --> service-function 2) that
        must be applied to packets and/or frames.  A service chain does
        not specify the network location or specific instance of service
        functions (e.g. firewall1 vs. firewall2).";
      key "name";
      leaf name {
        type string;
        description
          "the name of the service function";
      }
      leaf-list sf-service-function-path {
        type string;
        description
        "A list of all service function paths that contain this service function";
      }
    }
  }

  rpc delete-all-service-function {
  }

  rpc put-service-function {
    input {
      uses service-function-entry;
    }
  }
  rpc read-service-function {
    input {
      leaf name {
        type string;
        mandatory true;
        description "The name of the service function.";
      }
    }
    output {
      uses service-function-entry;
    }
  }

  rpc delete-service-function {
    input {
      leaf name {
        type string;
        mandatory true;
        description "The name of the service function.";
      }
    }
  }
}
