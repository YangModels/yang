module ietf-resource-mgmt{
  yang-version 1;
  namespace "urn:ietf:params:xml:ns:yang:ietf-resource-mgmt";
  // replace with IANA namespace when assigned
  prefix "resource";

  organization "huawei";
  contact
    "lizhenbin@huawei.com
     jescia.chenxia@huawei.com";

  description "The yang data model defines the configuration and operation of resource management.
               The initial version includes only label management.";

  revision "2015-12-16" {
    description "2015-10-15: Initial revision"+
                "2015-12-16: Add description for list and container";
    reference "TBD";
  }

  typedef label-type {
    type enumeration {
      enum static {
        description "The label is used for static configuration.";
      }
      enum dynamic {
        description "The label is used by dynamic mpls signalling protocol like ldp, rsvp.";
      }
      enum block {
        description "The label is used by mpls protocol like kompella bgp with a block of labels allocated.";
      }
    }
    description
      "The type of label and the label space is partitioned according to the label type.";
  }

  typedef label-app {
    type enumeration {
      enum p2p-rsvp-te {
        description "The label is allocated for RSVP-TE point-to-point lsp.";
      }
      enum p2p-ldp {
        description "The label is allocated for LDP point-to-point lsp.";
      }
      enum bgp {
        description "The label is allocated for labeled BGP(RFC3107).";
      }
      enum sr {
        description "The label is allocated for segment-routing.";
      }
      enum l2vpn {
        description "The label is allocated for l2vpn.";
      }
      enum l3vpn {
        description "The label is allocated for l3vpn.";
      }
      enum static-pw {
        description "The label is allocated for static pseudowire.";
      }
      enum static-lsp {
        description "The label is allocated for static lsp.";
      }
      enum mpls-tp-lsp {
        description "The label is allocated for static mpls tp lsp.";
      }
      enum p2mp-ldp {
        description "The label is allocated for LDP point-to-multipoint lsp.";
      }
      enum mp2mp-ldp {
        description "The label is allocated for LDP multipoint-to-multipoint lsp.";
      }
    }
    description
      "The application which the label is allocated for.";
  }

  container resource-cfg{
    description "It includes writable configuration objects about all
                 kinds of resources. The initial version includes only
                 label management.";
    container mpls-label-cfg{
      description "It defines the configuration objects about mpls label.";
      container label-space-cfg{
        description "It defines the type of label space and a list of label
                     spaces.";
        list label-spaces {
          key "label-type";
          description "List of label spaces. Each label space defines for one type of label space.";

          leaf label-type {
            type label-type;
            description "The type of label and the label sapce is partitioned
                         according to the labe type.";
          }

          list multiple-label-spaces {
            key "label-begin label-end";
     description "List of discrete label spaces.";

            leaf label-begin {
              type uint32;
              description "The lower-bound label.";
            }

            leaf label-end {
              type uint32;
              description "The upper-bound label.";
            }
          }
        }
      }
    }
  }

  container resource-state{
    description "The configuration and operation of resource management.
                 The initial version includes only label management.";

    container mpls-label-state{
      description "The configuration and operation of mpls label management.";
      container label-space-state{
        config false;
        description "The label space.";

        list label-spaces {
          key "label-type";
          description "List of label spaces. Each label space defines for one type of label space.";

          leaf label-type {
            type label-type;
            description "The type of label and the label sapce is partitioned
                         according to the labe type.";
          }

          leaf label-total-number {
            type uint32;
            description "The total number of labels belonging to one type of
                         label space.";
          }

          leaf label-available-total-number {
            type uint32;
            description "The total number of available labels belonging to one
                         type of label space.";
          }

          list multiple-label-spaces {
            key "label-begin label-end";
            description "List of discrete label spaces.";

            leaf label-begin {
              type uint32;
              description "The lower-bound label.";
            }

            leaf label-end {
              type uint32;
              description "The upper-bound label.";
            }
            leaf label-available-number {
              type uint32;
              config false;
              description "The total number of available labels in one label
                           segment belonging to one type of label space.";
            }
          }
        }
      }

      container used-label{
        config false;
        description "Used labels.";

        list used-labels {
          key "label-value";
          description "List of used labels.";

          leaf label-value {
            type uint32;
            description "The value of the used label.";
          }

          leaf label-app {
            type label-app;
            description "The application which the label is allocated for.";
          }

          leaf label-type {
            type label-type;
            description "The type of label and the label sapce is partitioned
                         according to the labe type.";
          }
        }
      }

      container used-label-statistics{
        config false;
        description "The statistics of used labels for each application applying for labels.";

        list used-label-statistics {
          key "label-app";
          description "The list of the statistics of used labels.";

          leaf label-app {
            type label-app;
            description "The application which the label is allocated for.";
          }
          leaf used-label-count {
            type uint32;
            description "The count of used labels the special aplication occupies.";
          }
        }
      }

      container available-label{
        config false;
        description "Available labels.";

        list available-labels {
          key "label-type";
          description "List of available labels.";

          leaf label-type {
            type label-type;
            description "The type of label and the label sapce is partitioned
                         according to the labe type.";
          }

          list label-segments {
            key "label-begin label-end";
            description "List of label segments.";

            leaf label-begin {
              type uint32;
              description "The lower-bound label.";
            }

            leaf label-end {
              type uint32;
              description "The upper-bound label.";
            }
          }
        }
      }
    }
  }
}
