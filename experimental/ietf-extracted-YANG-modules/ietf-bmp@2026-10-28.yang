module ietf-bmp {
  yang-version 1.1;
  namespace "urn:ietf:params:xml:ns:yang:ietf-bmp";
  prefix bmp;

  import ietf-yang-types {
    prefix yang;
    reference
      "RFC 9911: Common YANG Data Types";
  }
  import ietf-inet-types {
    prefix inet;
    reference
      "RFC 9911: Common YANG Data Types";
  }
  import ietf-netconf-acm {
    prefix nacm;
    reference
      "RFC 8341: Network Configuration Access Control Model";
  }
  import ietf-routing-policy {
    prefix rt-pol;
    description
      "This module is only needed if the feature
       bmp-filter-based-on-route-policy is set";
    reference
      "RFC 9067: A YANG Data Model for Routing Policy";
  }
  import ietf-network-instance {
    prefix ni;
    reference
      "RFC 8529: YANG Data Model for Network Instances";
  }
  import ietf-interfaces {
    prefix if;
    reference
      "RFC 8343: A YANG Data Model for Interface Management";
  }

  organization
    "IETF GROW Working Group";
  contact
    "WG Web:   <https://datatracker.ietf.org/wg/grow/>
     WG List:  <mailto:grow@ietf.org>

     Author:  Camilo Cardona
        <mailto:camilo@ntt.net>

     Author:  Paolo Lucente
        <mailto:paolo@ntt.net>

     Author:  Thomas Graf
        <mailto:thomas.graf@swisscom.com>

     Author:  Benoit Claise
        <mailto:benoit@everything-ops.net>

     Author:  Dhananjay Patki
        <mailto:dhpatki@cisco.com>

     Author:  Prasad S. Narasimha
        <mailto:snprasad@cisco.com>";
  description
    "This module defines a YANG data model for configuration and
     monitoring of the BGP Monitoring Protocol (BMP).

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be
     found at the
     'YANG Parameters' registry group
     (https://www.iana.org/assignments/yang-parameters).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.
    ";
  reference
    "RFC 4271: A Border Gateway Protocol 4 (BGP-4).
     RFC 4760: Multiprotocol Extensions for BGP-4.
     RFC 5065: Autonomous System Confederations for BGP.
     RFC 8671: Support for Adj-RIB-Out in the BGP Monitoring
     Protocol (BMP).
     RFC 7854: BGP Monitoring Protocol (BMP).
     RFC 9293: Transmission Control Protocol (TCP) Specification.
     RFC 9069: Support for Local RIB in the BGP Monitoring
     Protocol (BMP).
     RFC 9648: YANG Data Model for TCP.";

  revision 2026-10-28 {
    description
      "initial version";
    reference
      "RFC XXXX: A YANG Data Model for BMP.";
  }

  feature bmp-filter-based-on-route-policy {
    description
      "This feature means that the device
       is capable of filtering prefixes in BMP monitoring sessions";
  }

  /* These identities are defined locally to avoid a dependency on
   * draft-ietf-idr-bgp-model. */
  /* BGP AFI-SAFI Type Identities. */

  identity afi-safi-type {
    description
      "Base identity type for AFI,SAFI tuples for BGP-4";
    reference
      "RFC4760: Multiprotocol Extensions for BGP-4.";
  }

  identity ipv4-unicast {
    base afi-safi-type;
    description
      "IPv4 unicast (AFI,SAFI = 1,1)";
    reference
      "RFC4760: Multiprotocol Extensions for BGP-4.";
  }

  identity ipv6-unicast {
    base afi-safi-type;
    description
      "IPv6 unicast (AFI,SAFI = 2,1)";
    reference
      "RFC4760: Multiprotocol Extensions for BGP-4.";
  }

  /* End of temporal objects */

  identity bmp-peer-selectors {
    description
      "Generic Identity for selecting peers";
  }

  identity all-peers {
    base bmp-peer-selectors;
    description
      "This identity selects all peers under the RIB.
       When used, it acts as a default configuration.";
  }

  identity bmp-ni-types {
    description
      "Identities for selecting one or more network instances for
       configuration";
  }

  identity all-ni {
    base bmp-ni-types;
    description
      "This identity is an explicit way
       to select all network instances.";
  }

  identity global-ni {
    base bmp-ni-types;
    description
      "Identity for Selecting the global or main network instance";
  }

  identity non-global-ni {
    base bmp-ni-types;
    description
      "This identity is an explicit way
       to select all network instances except the global one.";
  }

  /* This type is defined locally to avoid a dependency on
   * draft-ietf-idr-bgp-model. */
  /* BGP Peer-Types */

  typedef peer-type {
    type enumeration {
      enum internal {
        description
          "Internal (IBGP) peer";
      }
      enum external {
        description
          "External (EBGP) peer";
      }
      enum confederation-internal {
        description
          "Confederation Internal (IBGP) peer.";
      }
      enum confederation-external {
        description
          "Confederation External (EBGP) peer.";
      }
    }
    description
      "Labels a peer or peer group as explicitly internal,
       external, or the related confederation type.";
    reference
      "RFC 4271: A Border Gateway Protocol 4 (BGP-4), Sec 1.1.
       RFC 5065: Autonomous System Confederations for BGP.";
  }

  /* End of temporal objects */

  grouping bmp-ip-connection-grouping {
    description
      "Common parameters for establishing connectivity
       to a BMP monitoring station.";
    choice passive-or-active {
      mandatory true;
      description
        "Selects whether the device initiates
         (active) or waits for (passive)
         the connection to the monitoring station,
         as described in RFC 7854 Section 3.2.";
      case active {
        description
          "Device initiates the connection to
           the monitoring station.";
        container active {
          description
            "The device starts the connection to
             the monitoring station";
          leaf network-instance {
            type leafref {
              path "/ni:network-instances/ni:network-instance/"
                 + "ni:name";
            }
            description
              "Network instance used to reach the monitoring
               station.
               Defaults to the global network instance
               if not specified.";
          }
          leaf station-address {
            type inet:ip-address;
            mandatory true;
            description
              "IP address of the monitoring station.";
          }
          leaf station-port {
            type inet:port-number;
            mandatory true;
            description
              "Port number of the monitoring station.";
          }
          choice local-endpoint {
            mandatory true;
            description
              "Local endpoint for the connection.";
            case monitored-router-address {
              leaf monitored-router-address {
                type inet:ip-address;
                description
                  "Local IP address to source the connection.";
              }
            }
            case monitored-router-interface {
              leaf monitored-router-interface {
                type if:interface-ref;
                description
                  "Local interface to source the connection.";
              }
            }
          }
          leaf monitored-router-port {
            type inet:port-number;
            description
              "Optional local port for the active connection.";
          }
        }
      }
      case passive {
        description
          "Device waits for incoming connection at a local
           endpoint.";
        container passive {
          description
            "Parameters for passively accepting
             a connection from the monitoring station.";
          leaf network-instance {
            type leafref {
              path "/ni:network-instances/ni:network-instance/"
                 + "ni:name";
            }
            description
              "Network instance used for the passive connection.
               Defaults to the global network instance if not
               specified.";
          }
          leaf station-address {
            type inet:ip-address;
            mandatory true;
            description
              "IP address of the monitoring station.";
          }
          leaf station-port {
            type inet:port-number;
            description
              "Optional value identifying the origin port of the
               connection. If provided, it MUST match the receiving
               connection.";
          }
          choice local-endpoint {
            mandatory true;
            description
              "Local endpoint for the connection.";
            case monitored-router-address {
              leaf monitored-router-address {
                type inet:ip-address;
                description
                  "Local IP address to accept the connection.";
              }
            }
            case monitored-router-interface {
              leaf monitored-router-interface {
                type if:interface-ref;
                description
                  "Local interface to accept the connection.";
              }
            }
          }
          leaf monitored-router-port {
            type inet:port-number;
            mandatory true;
            description
              "Local port to accept the connection.";
          }
        }
      }
    }
    leaf dscp {
      type inet:dscp;
      description
        "DSCP value for marking traffic to the monitoring station.";
      reference
        "RFC 9911: Common YANG Data Types";
    }
  }

  grouping route-monitoring-peer-grouping {
    description
      "General configuration options for route monitoring
       of a peer.";
    container filters {
      description
        "Filters for selecting which routes to export to
         the monitoring station.";
      container policy-filter {
        if-feature "bmp-filter-based-on-route-policy";
        description
          "Filter routes using a routing policy from the
           rt-pol module.
           The policy should only contain accept/reject actions
           and match prefix sets.";
        leaf-list export-policy {
          type leafref {
            path "/rt-pol:routing-policy/"
               + "rt-pol:policy-definitions/"
               + "rt-pol:policy-definition/rt-pol:name";
            require-instance true;
          }
          ordered-by user;
          description
            "Ordered list of policy names used to select
             routes for export.";
        }
        leaf default-export-policy {
          type rt-pol:default-policy-type;
          default "accept-route";
          description
            "Default action if no export policy matches.";
        }
      }
    }
  }

  grouping bmp-peer-ribs-filter-grouping {
    description
      "Configuration containers for RIBs under the main
       BMP container.";
    container address-families {
      description
        "List of address families for route monitoring.";
      list address-family {
        key "id";
        description
          "Address family identifier.";
        leaf id {
          type identityref {
            base afi-safi-type;
          }
          description
            "Address family identifier.";
        }
        leaf enabled {
          type boolean;
          default "true";
          description
            "Enables route monitoring messages for this address
             family.";
        }
        container peers-configurations {
          description
            "Each peer under this BGP instance can be configured by
             at most one of the following containers.
             If the peer is not covered by any,
             then no BMP route monitoring message
             should include information from/to that peer.
             If the peer is covered by more than one, then the
             priority is:
             1. peer
             2. peer-groups
             3. peer-type
             4. peer-selectors

             New child containers or new bmp-peer-selectors
             instances SHOULD provide a way of unambiguously
             selecting which configuration container should
             be selected
             for a peer in case of multiple matches.";
          container peers {
            description
              "Configuration for individual peers.";
            list peer {
              key "id";
              description
                "Peer identifier.";
              leaf id {
                type string;
                description
                  "Identifier of the peer.";
              }
              leaf enabled {
                type boolean;
                default "true";
                description
                  "Enables route monitoring messages for this peer.";
              }
              uses route-monitoring-peer-grouping;
            }
          }
          container peer-groups {
            description
              "Configuration for peer groups.";
            list peer-group {
              key "id";
              description
                "Peer group identifier.";
              leaf id {
                type string;
                description
                  "Identifier of the peer group.";
              }
              leaf enabled {
                type boolean;
                default "true";
                description
                  "Enables route monitoring messages for
                   this peer group.";
              }
              uses route-monitoring-peer-grouping;
            }
          }
          container peer-selectors {
            description
              "Configuration for peers selected by BMP peer
               selectors.";
            list peer-selector {
              key "id";
              description
                "Identification of peers
                 for which BMP data is sent to
                 the collector using a peer type
                 defined by a bmp-peer-selectors
                 identity.
                 For instance, to create a default for all
                 peers use the all-peers identity";
              leaf id {
                type identityref {
                  base bmp-peer-selectors;
                }
                description
                  "BMP peer selector identity.";
              }
              leaf enabled {
                type boolean;
                default "true";
                description
                  "Enables route monitoring messages
                   for the peer(s).";
              }
              uses route-monitoring-peer-grouping;
            }
          }
          container peer-types {
            description
              "Generic identification of peers to configure.";
            list peer-type {
              key "id";
              description
                "Identification of peers
                 for which BMP data is sent to the collector
                 using BGP peer-type (e.g. internal, external)
                ";
              leaf id {
                type peer-type;
                description
                  "BGP peer type.";
              }
              leaf enabled {
                type boolean;
                default "true";
                description
                  "Enables route monitoring messages
                   for the peer(s).";
              }
              uses route-monitoring-peer-grouping;
            }
          }
        }
      }
    }
  }

  grouping generic-network-instance-grouping {
    description
      "Generic configuration of a network instance.";
    leaf enabled {
      type boolean;
      default "true";
      description
        "Enables route monitoring
         messages for the network instance.";
    }
    container adj-rib-in-pre {
      description
        "Configuration for the adj-rib-in pre-policy.";
      reference
        "RFC7854: BGP Monitoring Protocol (BMP), Section 2.";
      uses bmp-peer-ribs-filter-grouping;
    }
    container adj-rib-in-post {
      description
        "Configuration for the adj-rib-in post-policy";
      reference
        "RFC7854: BGP Monitoring Protocol (BMP), Section 2.";
      uses bmp-peer-ribs-filter-grouping;
    }
    container local-rib {
      description
        "Configuration for the local-rib.";
      reference
        "RFC9069: Support for Local RIB in the BGP Monitoring
         Protocol (BMP), Section 3.";
      container address-families {
        description
          "List of address families to enable for local-rib.";
        list address-family {
          key "id";
          description
            "Address family to enable for local-rib";
          leaf id {
            type identityref {
              base afi-safi-type;
            }
            description
              "Address family id to enable for local-rib";
          }
          uses route-monitoring-peer-grouping;
        }
      }
    }
    container adj-rib-out-pre {
      description
        "Configuration for the adj-rib-out pre-policy";
      reference
        "RFC8671: Support for Adj-RIB-Out in the BGP Monitoring
         Protocol (BMP) , Section 3.";
      uses bmp-peer-ribs-filter-grouping;
    }
    container adj-rib-out-post {
      description
        "Configuration for the adj-rib-out post-policy";
      reference
        "RFC8671: Support for Adj-RIB-Out in the BGP Monitoring
         Protocol (BMP) , Section 3.";
      uses bmp-peer-ribs-filter-grouping;
    }
  }

  grouping route-monitoring-sources {
    description
      "Configuration of route monitoring sources.";
    reference
      "RFC7854:  BGP Monitoring Protocol, Section 5.";
    container network-instance-configuration {
      description
        "This container offers options for configuring BMP
         route-monitoring messages for each network instance either
         selecting it through its name or through a
         network-instance-selectors.

         Network-instance-selectors are instances of bmp-ni-types
         that select one or more network instances for configuration.
         For instance, all-ni to configure all network
         instances (serving as a default).

         Network-instance can be at most configured by one of the
         containers. If the network instance is not covered by any,
         then no BMP route monitoring message should include that
         network instance. If more than one container matches
         the network instance, the priority for selecting the
         container to use for configuration is:

         1. For any named network instance, the configuration
            under the element listed with its name under the
            network-instance container.
         2. If the global-ni network-instance type exists,
            it SHOULD  be used for the global-ni.
            However, if the global-ni
            has an explicit name, and it is configured, then
            from the previous rule, the explicit network
            instance name configuration SHOULD be used.
         3. The configuration under network-instance-groups of type
            non-global-ni if existing and not the global
            network instance.
         4. the configuration under network-instance-groups under the
            element all-ni.

         If the implementation has a name for the global network
         instance (e.g. 'main') it can be configure directly under
         the network-instances container.

         New identities under bmp-ni-types or augmentations of this
         container in the future SHOULD provide a clear way of
         selecting the configuration container for a network-instance
         without ambiguity.";
      container network-instances {
        description
          "Configuration for specific network instances";
        list network-instance {
          key "id";
          description
            "Network instance to monitor using BMP.";
          leaf id {
            type leafref {
              path "/ni:network-instances/ni:network-instance/"
                 + "ni:name";
            }
            description
              "Name of the network instance.";
          }
          uses generic-network-instance-grouping;
        }
      }
      container network-instance-selectors {
        description
          "Configuration of network instances. Uses
           bmp-ni-types to identify one or a group of
           network instances to configure.";
        list network-instance-selector {
          key "id";
          description
            "Network instance(s) to monitor using BMP.";
          leaf id {
            type identityref {
              base bmp-ni-types;
            }
            description
              "Configures one or multiple network instances selected
               based on a bmp-ni-types identity (e.g.
               all-ni for all of them).";
          }
          uses generic-network-instance-grouping;
        }
      }
    }
  }

  container bmp {
    description
      "Top-level container for BMP configuration.";
    container monitoring-stations {
      description
        "List of BMP monitoring stations.";
      list monitoring-station {
        key "id";
        description
          "Configuration for a BMP monitoring station.";
        leaf id {
          type string;
          description
            "Unique identifier for the monitoring station.";
        }
        leaf description {
          type string;
          description
            "Description of the BMP monitoring station.";
        }
        container connection {
          description
            "Connection parameters for the monitoring station.";
          uses bmp-ip-connection-grouping;
          container tcp-options {
            description
              "TCP options for the connection to the monitoring
               station.";
            leaf mtu-discovery {
              type boolean;
              default "true";
              description
                "Enables path MTU discovery for the TCP sessions
                 (true) or disables it (false).";
              reference
                "RFC 9293: Transmission Control Protocol (TCP).
                 RFC 9648: YANG Data Model for TCP,
                 see leaf pmtud for reference.";
            }
          }
          leaf initial-delay {
            type uint32;
            units "seconds";
            default "0";
            description
              "Initial delay before connecting to the monitoring
               station.
               Useful for allowing BGP sessions to stabilize
               before starting BMP.";
          }
          container backoff {
            description
              "Configures the backoff strategy after a connection
               retry";
            reference
              "RFC7854 Section 3.2";
            choice backoff-options {
              description
                "Options for backoff strategies";
              reference
                "RFC7854 Section 3.2";
              case simple-exponential {
                description
                  "Simple exponential backoff with limits.";
                container simple-exponential {
                  description
                    "Simple exponential backoff with limits.
                     Starts with the initial backoff and doubles
                     the backoff after every retry until reaching the
                     maximum backoff.";
                  leaf initial-backoff {
                    type uint32;
                    units "seconds";
                    default "30";
                    description
                      "Initial backoff time";
                  }
                  leaf maximum-backoff {
                    type uint32;
                    units "seconds";
                    default "720";
                    description
                      "Maximum backoff time";
                  }
                }
              }
            }
          }
        }
        container bmp-data {
          description
            "Configuration of BMP data sent to the monitoring
             station.";
          leaf initiation-message {
            type string;
            description
              "User-defined message to append to the
               initiation message.";
            reference
              "RFC7854:  BGP Monitoring Protocol,
               Section 4.3 and 4.4";
          }
          container statistics-report {
            presence "Enable BMP statistics report.";
            description
              "Configuration for periodic statistics reports.";
            reference
              "RFC7854:  BGP Monitoring Protocol,
               Section 4.8";
            leaf statistics-interval {
              type uint32;
              units "seconds";
              mandatory true;
              description
                "Interval between statistics report messages.";
            }
          }
          container route-monitoring {
            description
              "Configuration of the data sources for
               route-monitoring messages";
            uses route-monitoring-sources;
          }
          container route-mirroring {
            presence "Enable BMP route mirroring to the monitoring
                      station.";
            description
              "Configuration for route mirroring to the
               monitoring station.";
          }
        }
        container session-stats {
          config false;
          description
            "Operational statistics for the monitoring station.
             Counters are reset after each successful
             connection or reset.";
          grouping bmp-af-stats-with-peers-grouping {
            description
              "Generic statistics for an address family that can be
               disaggregated by peers";
            container peers-stats {
              description
                "Peer stats";
              list peer {
                key "id";
                description
                  "List of peers";
                leaf id {
                  type string;
                  description
                    "Peer id";
                }
                leaf enabled {
                  type boolean;
                  description
                    "Indicates if route monitoring messages are
                     currently enabled for the peer under this
                     network instance, address family, and RIB.";
                }
                leaf total-route-mnt-updated-prefixes-per-peer {
                  type uint64;
                  description
                    "Number of prefixes updated for this peer.";
                }
                leaf total-route-mnt-withdraw-prefixes-per-peer {
                  type uint64;
                  description
                    "Number of prefixes withdrawn for this peer.";
                }
              }
            }
          }

          grouping bmp-af-stats-grouping {
            description
              "Group for statistics for an address family.";
            leaf enabled {
              type boolean;
              description
                "Indicates if any route monitoring messages
                 are currently enabled for the address family
                 within the RIB.";
            }
            leaf total-route-monitoring-updated-prefixes-per-af {
              type uint64;
              description
                "Number of prefixes updated for this address
                 family.";
            }
            leaf total-route-monitoring-withdraw-prefixes-per-af {
              type uint64;
              description
                "Number of prefixes withdrawn for this address
                 family.";
            }
          }

          grouping bmp-rib-with-peers-stats-grouping {
            description
              "Generic statistics for a RIB with peers.";
            container address-families {
              description
                "List of address families to list stats.";
              list address-family {
                key "id";
                description
                  "Address family to enable for local-rib";
                leaf id {
                  type identityref {
                    base afi-safi-type;
                  }
                  description
                    "Address family ID for local-rib.";
                }
                uses bmp-af-stats-grouping;
                uses bmp-af-stats-with-peers-grouping;
              }
            }
          }

          grouping bmp-rib-stats-grouping {
            description
              "Generic statistics per RIB.";
            leaf enabled {
              type boolean;
              description
                "Indicates if any Route Monitoring messages are
                 currently enabled for the RIB.";
            }
            leaf total-route-mirroring-messages-per-rib {
              type uint64;
              description
                "Number of route-mirroring messages sent for
                 this RIB.";
            }
          }

          leaf discontinuity-time {
            type yang:date-and-time;
            mandatory true;
            description
              "The time on the most recent occasion at which any
               one or more of this station's counters suffered a
               discontinuity. If no such discontinuities have
               occurred since the last re-initialization of the
               local management subsystem, then this node contains
               the time the local management subsystem
               re-initialized itself.";
          }
          leaf established-session {
            type boolean;
            description
              "Indicates if the session is currently
               established.";
          }
          leaf total-route-monitoring-messages {
            type uint64;
            description
              "Number of route-monitoring messages sent.";
          }
          leaf total-statistics-messages {
            type uint64;
            description
              "Number of statistics messages sent.";
          }
          leaf total-peer-down-messages {
            type uint64;
            description
              "Number of peer-down messages sent.";
          }
          leaf total-peer-up-messages {
            type uint64;
            description
              "Number of peer-up messages sent.";
          }
          leaf total-initiation-messages {
            type uint64;
            description
              "Number of initiation messages sent";
          }
          leaf total-route-mirroring-messages {
            type uint64;
            description
              "Number of route-mirroring messages sent.";
          }
          leaf total-termination-messages {
            type uint64;
            description
              "Number of termination messages sent.";
          }
          container route-monitoring-stats {
            description
              "Statistics of route monitoring messages disaggregated
               by RIB and peers where applicable.";
            container network-instances-stats {
              description
                "Stats per network-instance";
              list network-instance {
                key "network-instance-name";
                description
                  "Network instance stats list";
                leaf network-instance-name {
                  type leafref {
                    path "/ni:network-instances/ni:network-instance/"
                       + "ni:name";
                  }
                  description
                    "Name of the network instance.";
                }
                leaf enabled {
                  type boolean;
                  description
                    "Indicates if route monitoring messages are
                     currently enabled for the network instance.";
                }
                leaf total-route-mirroring-messages-per-ni {
                  type uint64;
                  description
                    "Number of route-mirroring messages sent for
                     this network instance.";
                }
                container ribs-stats {
                  description
                    "Statistics for the different RIBs.";
                  container adj-rib-in-pre {
                    description
                      "Statistics for adj-rib-in-pre.";
                    uses bmp-rib-stats-grouping;
                    uses bmp-rib-with-peers-stats-grouping;
                  }
                  container adj-rib-in-post {
                    description
                      "Statistics for adj-rib-in-post";
                    uses bmp-rib-stats-grouping;
                    uses bmp-rib-with-peers-stats-grouping;
                  }
                  container local-rib {
                    description
                      "Statistics for local-rib";
                    uses bmp-rib-stats-grouping;
                    container address-families {
                      description
                        "List of address families to for stats.";
                      list address-family {
                        key "id";
                        description
                          "Address family to enable for local-rib";
                        leaf id {
                          type identityref {
                            base afi-safi-type;
                          }
                          description
                            "Address family ID for local-rib";
                        }
                        uses bmp-af-stats-grouping;
                      }
                    }
                  }
                  container adj-rib-out-pre {
                    description
                      "Statistics for adj-rib-out-pre";
                    uses bmp-rib-stats-grouping;
                    uses bmp-rib-with-peers-stats-grouping;
                  }
                  container adj-rib-out-post {
                    description
                      "Statistics for adj-rib-out-post";
                    uses bmp-rib-stats-grouping;
                    uses bmp-rib-with-peers-stats-grouping;
                  }
                }
              }
            }
          }
        }
        container actions {
          description
            "Container with actions for BMP operation.";
          action session-reset {
            description
              "Resets the session for a station.";
          }
          action session-counter-reset {
            description
              "Resets the counters of a BMP monitoring station.";
          }
          nacm:default-deny-all;
        }
      }
    }
  }
}
