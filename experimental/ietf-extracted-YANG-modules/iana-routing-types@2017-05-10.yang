module iana-routing-types {

  namespace "urn:ietf:params:xml:ns:yang:iana-routing-types";
  prefix "iana-rt-types";

  organization "IETF Routing Area Working Group (rtgwg)";

  contact
      "Routing Area Working Group - <rtgwg@ietf.org>";

  description
    "This module contains a collection of YANG data types
     considered defined by IANA and used for routing
     protocols.

     Copyright (c) 2017 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     The key words 'MUST', 'MUST NOT', 'REQUIRED', 'SHALL', 'SHALL
     NOT', 'SHOULD', 'SHOULD NOT', 'RECOMMENDED', 'MAY', and
     'OPTIONAL' in the module text are to be interpreted as described
     in RFC 2119.

     This version of this YANG module is part of RFC XXXX;
     see the RFC itself for full legal notices.";

  revision 2017-05-10 {
    description
      "Initial revision.";
    reference
      "RFC TBD: IANA Routing YANG Data Types";
  }

  /*** Collection of IANA types related to routing ***/

  /*** IANA address family Identies ***/
  identity address-family {
    description
      "Base identity from which identities describing address
       families are derived.";
  }
  identity ipv4 {
    base address-family;
    description
        "IPv4 Address Family - IANA Registry Assigned Number: 1";
  }
  identity ipv6 {
    base address-family;
    description
        "IPv6 Address Family - IANA Registry Assigned Number: 2";
  }
  identity nsap {
    base address-family;
    description
        "OSI Network Service Access Point (NSAP) Address Family -
         IANA Registry Assigned Number: 3";
  }
  identity hdlc {
    base address-family;
    description
        "High-Level Data Link Control (HDLC) Address Family -
         IANA Registry Assigned Number: 4";
  }
  identity bbn1822 {
    base address-family;
    description
        "Bolt, Beranek, and Newman Report 1822 (BBN 1822)
         Address Family - IANA Registry Assigned Number: 5";
  }
  identity ieee802 {
    base address-family;
    description
        "IEEE 802 Committee Address Family (aka, MAC address) -
         IANA Registry Assigned Number: 6";
  }
  identity e163 {
    base address-family;
    description
        "ITU-T E.163 Address Family -
         IANA Registry Assigned Number: 7";
  }
  identity e164 {
    base address-family;
    description
        "ITU-T E.164 (SMDS, Frame Relay, ATM) Address Family -
         IANA Registry Assigned Number: 8";
  }
  identity f69 {
    base address-family;
    description
        "ITU-T F.69 (Telex) Address Family -
         IANA Registry Assigned Number: 9";
  }
  identity x121 {
    base address-family;
    description
        "ITU-T X.121 (X.25, Frame Relay) Address Family -
         IANA Registry Assigned Number: 10";
  }
  identity ipx {
    base address-family;
    description
        "Novell Internetwork Packet Exchange (IPX)
         Address Family - IANA Registry Assigned Number: 11";
  }
  identity appletalk {
    base address-family;
    description
        "Apple AppleTalk Address Family -
         IANA Registry Assigned Number: 12";
  }
  identity decnet-iv {
    base address-family;
    description
        "Digital Equipment DECnet Phase IV Address Family -
         IANA Registry Assigned Number: 13";
  }
  identity vines {
    base address-family;
    description
        "Banyan Vines Address Family -
         IANA Registry Assigned Number: 14";
  }
  identity e164-nsap {
    base address-family;
    description
        "ITU-T E.164 with NSAP sub-address Address Family -
         IANA Registry Assigned Number: 15";
  }
  identity dns {
    base address-family;
    description
        "Domain Name System (DNS) Address Family -
         IANA Registry Assigned Number: 16";
  }
  identity distinguished-name {
    base address-family;
    description
        "Distinguished Name Address Family -
         IANA Registry Assigned Number: 17";
  }
  identity as-num {
    base address-family;
    description
        "AS Number Family -
         IANA Registry Assigned Number: 18";
  }
  identity xtp-v4 {
    base address-family;
    description
        "Xpress Transport Protocol (XTP) over IPv4
         Address Family - IANA Registry Assigned Number: 19";
  }
  identity xtp-v6 {
    base address-family;
    description
        "Xpress Transport Protocol (XTP) over IPv4
         Address Family - IANA Registry Assigned Number: 20";
  }
  identity xtp-native {
    base address-family;
    description
        "Xpress Transport Protocol (XTP) native mode
         Address Family - IANA Registry Assigned Number: 21";
  }
  identity fc-port {
    base address-family;
    description
        "Fibre Channel (FC) World-Wide Port Name
         Address Family - IANA Registry Assigned Number: 22";
  }
  identity fc-node {
    base address-family;
    description
        "Fibre Channel (FC) World-Wide Node Name
         Address Family - IANA Registry Assigned Number: 23";
  }
  identity gwid {
    base address-family;
    description
        "ATM Gateway Identifier (GWID) Number Family -
         IANA Registry Assigned Number: 24";
  }
  identity l2vpn {
    base address-family;
    description
        "Layer-2 VPN (L2VPN) Address Family -
         IANA Registry Assigned Number: 25";
  }
  identity mpls-tp-section-eid {
    base address-family;
    description
        "MPLS-TP Section Endpoint Identifier Address Family -
         IANA Registry Assigned Number: 26";
  }
  identity mpls-tp-lsp-eid {
    base address-family;
    description
        "MPLS-TP LSP Endpoint Identifier Address Family -
         IANA Registry Assigned Number: 27";
  }
  identity mpls-tp-pwe-eid {
    base address-family;
    description
        "MPLS-TP Pseudowire Endpoint Identifier
         Address Family - IANA Registry Assigned Number: 28";
  }
  identity mt-v4 {
    base address-family;
    description
        "Multi-Topology IPv4 Address Family -
         Address Family - IANA Registry Assigned Number: 29";
  }
  identity mt-v6 {
    base address-family;
    description
        "Multi-Topology IPv6 Address Family -
         Address Family - IANA Registry Assigned Number: 30";
  }
  identity eigrp-common-sf {
    base address-family;
    description
        "Enhanced Interior Gateway Routing Protocol (EIGRP)
         Common Service Family Address Family -
         IANA Registry Assigned Number: 16384";
  }
  identity eigrp-v4-sf {
    base address-family;
    description
        "Enhanced Interior Gateway Routing Protocol (EIGRP)
         IPv4 Service Family Address Family -
         IANA Registry Assigned Number: 16385";
  }
  identity eigrp-v6-sf {
    base address-family;
    description
        "Enhanced Interior Gateway Routing Protocol (EIGRP)
         IPv6 Service Family Address Family -
         IANA Registry Assigned Number: 16386";
  }
  identity lcaf {
    base address-family;
    description
        "LISP Canonical Address Format (LCAF)
         Address Family - IANA Registry Assigned Number: 16387";
  }
  identity bgp-ls {
    base address-family;
    description
        "Border Gatway Protocol - Link State (BGP-LS)
         Address Family - IANA Registry Assigned Number: 16388";
  }
  identity mac-48 {
    base address-family;
    description
        "IEEE 48-bit Media Access Control (MAC)
         Address Family - IANA Registry Assigned Number: 16389";
  }
  identity mac-64 {
    base address-family;
    description
        "IEEE 64-bit Media Access Control (MAC)
         Address Family - IANA Registry Assigned Number: 16390";
  }
  identity trill-oui {
    base address-family;
    description
        "TRILL IEEE Organizationally Unique Identifier (OUI) -
         Address Family - IANA Registry Assigned Number: 16391";
  }
  identity trill-mac-24 {
    base address-family;
    description
        "TRILL Final 3 octets of 48-bit MAC address
         Address Family - IANA Registry Assigned Number: 16392";
  }
  identity trill-mac-48 {
    base address-family;
    description
        "TRILL Final 5 octets of 64-bit MAC address
         Address Family - IANA Registry Assigned Number: 16393";
  }
  identity trill-rbridge-port-id {
    base address-family;
    description
        "TRILL Remote Bridge (RBridge) Port ID
         Address Family - IANA Registry Assigned Number: 16394";
  }
  identity trill-nickname {
    base address-family;
    description
        "TRILL Nickname
         Address Family - IANA Registry Assigned Number: 16395";
  }

  /*** Subsequent Address Family for Multi-Protocol BGP */
  identity bgp-safi {
    description
      "Base identity from which identities describing BGP
       Subsequent Address Family Identifier (SAFI) - RFC 4760.";
  }

  identity unicast-safi {
    base bgp-safi;
    description
      "Unicast SAFI -
       IANA Registry Assigned Number: 1";
  }

  identity multicast-safi {
    base bgp-safi;
    description
      "Multicast SAFI -
       IANA Registry Assigned Number: 2";
  }

  identity labeled-unicast-safi {
    base bgp-safi;
    description
      "Labeled Unicast SAFI -
       IANA Registry Assigned Number: 4";
  }

  identity multicast-vpn-safi {
    base bgp-safi;
    description
      "Multicast VPN SAFI -
       IANA Registry Assigned Number: 5";
  }

  identity pseudowire-safi {
    base bgp-safi;
    description
      "Multi-segment Pseudowire VPN SAFI -
       IANA Registry Assigned Number: 6";
  }

  identity tunnel-enap-safi {
    base bgp-safi;
    description
      "Tunnel Encap SAFI -
       IANA Registry Assigned Number: 7";
  }

  identity mcast-vpls-safi {
    base bgp-safi;
    description
      "Multicast Virtual Private LAN Service (VPLS) SAFI -
       IANA Registry Assigned Number: 8";
  }

  identity tunnel-safi {
    base bgp-safi;
    description
      "Tunnel SAFI -
       IANA Registry Assigned Number: 64";
  }

  identity vpls-safi {
    base bgp-safi;
    description
      "Virtual Private LAN Service (VPLS) SAFI -
       IANA Registry Assigned Number: 65";
  }

  identity mdt-safi {
    base bgp-safi;
    description
      "Multicast Distribution Tree (MDT) SAFI -
       IANA Registry Assigned Number: 66";
  }

  identity v4-over-v6-safi {
    base bgp-safi;
    description
      "IPv4 over IPv6 SAFI -
       IANA Registry Assigned Number: 67";
  }

  identity v6-over-v4-safi {
    base bgp-safi;
    description
      "IPv6 over IPv4 SAFI -
       IANA Registry Assigned Number: 68";
  }

  identity l1-vpn-auto-discovery-safi {
    base bgp-safi;
    description
      "Layer-1 VPN Auto Discovery SAFI -
       IANA Registry Assigned Number: 69";
  }

  identity evpn-safi {
    base bgp-safi;
    description
      "Ethernet VPN (EVPN) SAFI -
       IANA Registry Assigned Number: 70";
  }

  identity bgp-ls-safi {
    base bgp-safi;
    description
      "BGP Link-State (BGP-LS) SAFI -
       IANA Registry Assigned Number: 71";
  }

  identity bgp-ls-vpn-safi {
    base bgp-safi;
    description
      "BGP Link-State (BGP-LS) VPN SAFI -
       IANA Registry Assigned Number: 72";
  }

  identity sr-te-safi {
    base bgp-safi;
    description
      "Segment Routing - Traffic Engineering (SR-TE) SAFI -
       IANA Registry Assigned Number: 73";
  }

  identity labeled-vpn-safi {
    base bgp-safi;
    description
      "MPLS Labeled VPN SAFI -
       IANA Registry Assigned Number: 128";
  }

  identity multicast-mpls-vpn-safi {
    base bgp-safi;
    description
      "Multicast for BGP/MPLS IP VPN SAFI -
       IANA Registry Assigned Number: 129";
  }

  identity route-target-safi {
    base bgp-safi;
    description
      "Route Target SAFI -
       IANA Registry Assigned Number: 132";
  }

  identity ipv4-flow-spec-safi {
    base bgp-safi;
    description
      "IPv4 Flow Specification SAFI -
       IANA Registry Assigned Number: 133";
  }

  identity vpnv4-flow-spec-safi {
    base bgp-safi;
    description
      "IPv4 VPN Flow Specification SAFI -
       IANA Registry Assigned Number: 134";
  }
}
