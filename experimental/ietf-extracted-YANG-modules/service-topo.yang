module service-topo {
     yang-version 1;
     namespace "urn:TBD:params:xml:ns:yang:service-topo";
     prefix stopo;
     import ietf-inet-types {
       prefix inet;
     }
     organization "IETF I2RS Working Group";
     contact
       "wangzitao@huawei.com";
     description
       "This module defines service topology yang data model";
     typedef node-id {
       type inet:uri;
     }
     typedef network-id {
       type inet:uri;
     }
     typedef link-id {
       type inet:uri;
     }
container service-topologies {
description
"Contains configuration related data. Within the container
is list of service topologies.";

list service-topology{
key "service-topo-id";
description
"Define the list of service-topology within the network";

leaf service-topo-id{
type network-id;
 description
"the identifier for a service topology";}

leaf node-count{
type uint32;
description
"Number of nodes within a service topology.";}

container topology-type{
  description
 " This container contains several leaf to specify the topology type,
   such as NETCONF or I2RS. A service topology can even have
   multiple types simultaneously. And this container can
   be used to augment the service topology model by topology specifics.";}

container topology-extension{
description
 " The topology-extension container can be used to augment
the service topology model by topology specifics.";}

list underlay-topologies {
key "topology-id";
   description
"Define the list of underlay-topologies within the service-topology list";

leaf topology-id {
 type network-id;
   description
 "It is presumed that a datastore will contain many topologies. To
  distinguish between topologies it is vital to have UNIQUE
  topology identifiers.";}
}

list node {
key "node-id";
description
"Define the list of node within the service-topology list";

leaf node-id {
type node-id;
description
"The identifier of a node in the service topology.";}

list termination-point{
key "termination-point-id";
description
"Define the list of termination-point within the node list";

leaf termination-point-id {
type node-id;
description
"The identifier of the termination point of the node";}

list support-termination-points{
key "support-point-id";
description
"Define the list of support-point-id within the termination-point list";

leaf support-point-id {
type node-id;
description
"the identifier of the support node of the termination point";}
}

container termination-point-extension{
description
"The termination-point-extension container can be used to augment
the service topology model by topology specifics.";}
}

container node-type{
description
"The node-type container can used to indicate the type node,
such classifier, a sf or a sff. And this container can be used
to augment the service topology model by topology specifics. ";

leaf classifier-node {
type string;
description
"To indicate the node is a classifier";}

leaf sf-node {
type string;
description
"To indicate the node is a service function(sf)";}
leaf sff-node {
type string;
description
" To indicate the node is a service function forward(sff)";}
}

list next-hop{
key "hop-id";
description
"Define the list of next-hop within the node list";

leaf hop-id {
type node-id;
description
"The identifier of the next hop of the node";}
}

container node-extension{
description
" The node-extension container can be used to augment
the service topology model by topology specific nodes.";

container classifier-extension {
description
"The classifier-extension container contains the extensions
of the classifier";}

container sf-node-extension {
description
"The sf-extension container contains the extensions of the sf.";}

container sff-node-extension {
description
" The sff-extension container contains the extensions of the sff. ";}
}
} //end the node list

list segment{
key "segment-id";
description
"Define the list of segment within the service-topology list.";

leaf segment-id{
type link-id;
description
" The segment-id leaf can be used to distinguish
the different service segment.";}

container source{
description
"The source container contains the source node
and the termination point reference list.";

leaf source-id{
type node-id;
description
"The identifier of the source node of the segment.";}
list termination-point-reference{

key "source-support-id";
leaf source-support-id{
type node-id;
description
"The identifier of the termination point of the source node.";}
}//end the termination-point-reference list
}//end the source container

container destination{
description
"The destination container contains the source node
and the termination point reference list.";
leaf destination-id{
type node-id;
description
"The identifier of the destination node of the segment.";}
list termination-point-reference{
key "destination-support-id";
leaf destination-support-id{
type node-id;
description
"The identifier of the termination point of the source node.";}
}//end the termination-point-reference list
}//end the destination container

container direction{
leaf unidirection{
type boolean;
description
"Indicates whether the segment is unidirection or not.";}
leaf bidirection{
type boolean;
description
"Indicates whether the segment is bidirection or not.";}
} //end the direction container

container segment-extension{
description
"The segment-extension container can be used to augment
the segment list by segment specifics. Such as
netconf segment extension, i2rs segment extension.";

container netconf-segment-extension {
description
"To contain the netconf segment extension.";}
container i2rs-segment-extension {
description
"To contain the i2rs segment extension.";}
} //end the segment-extension container
}//end the segment list
}//end the service-topology list
}
}
