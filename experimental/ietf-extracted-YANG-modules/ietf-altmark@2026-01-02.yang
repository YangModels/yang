module ietf-altmark {
  yang-version 1.1;
  namespace "urn:ietf:params:xml:ns:yang:ietf-altmark";
  prefix "altmark";

  import ietf-access-control-list {
    prefix "acl";
    reference
      "RFC 8519: YANG Data Model for Network Access Control
       Lists (ACLs)";
  }

  import ietf-interfaces {
    prefix "if";
    reference
      "RFC 8343: A YANG Data Model for Interface Management";
  }

  import ietf-lime-time-types {
    prefix "lime";
    reference
      "RFC 8532: Generic YANG Data Model for the Management of
       Operations, Administration, and Maintenance (OAM) Protocols
       That Use Connectionless Communications";
  }

  organization
    "IETF IPPM (IP Performance Metrics) Working Group";

  contact
    "WG Web: <https://datatracker.ietf.org/wg/ippm>
     WG List: <ippm@ietf.org>
     Author: thomas.graf@swisscom.com
     Author: wangminxue@chinamobile.com
     Author: giuseppe.fioccola@huawei.com
     Author: zhoutianran@huawei.com
     Author: xiao.min2@zte.com.cn";

  description
    "This YANG module specifies a vendor-independent data
     model for the Alternate Marking (AltMark).
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-01-02 {
    description "First revision.";
    reference "RFC XXXX: A YANG Data Model for Alternate-Marking";
  }

 /*
  * FEATURES
  */

  feature altmark
  {
    description
      "This feature indicated that the Alternate-Marking Method is
      supported.";
    reference
      "RFC 9341: Alternate-Marking Method;
       RFC 9342: Clustered Alternate-Marking Method";
  }

 /*
  * IDENTITIES
  */

  identity filter {
    description
      "Base identity to represent a filter. A filter is used to
      specify the flow to which the AltMark method is applied.";
  }
  identity acl-filter {
    base filter;
    description
      "Apply ACL rules to specify the flow.";
  }

  identity method {
    description
      "Base identity to represent the method type.";
  }

  identity single-marking {
    base method;
    description
      "The AltMark Single-Marking method.";
  }

  identity double-marking  {
    base method;
    description
      "The AltMark Double-Marking method.";
  }

  identity protocol {
    description
      "Base identity to represent the protocol. It's used to
       indicate the protocol for the application of the AltMark
       method.";
  }

  identity ipv6 {
    base protocol;
    description
      "The AltMark method is applied to IPv6 protocol.";
    reference
      "RFC 9343: IPv6 Application of the Alternate-Marking Method";
  }

  identity srh  {
    base protocol;
    description
      "The AltMark method is applied to SRH.";
    reference
      "[I-D.fz-spring-srv6-alt-mark]: Application of the
      Alternate Marking Method to the Segment Routing Header";
  }

  identity mpls  {
    base protocol;
    description
      "The AltMark method is applied to MPLS.";
    reference
      "RFC 9714: Application of the Alternate Marking Method
      to the MPLS Label Stack";
  }

  identity node-action {
    description
      "Base identity to represent the node actions. It's used to
       indicate what action the node will take.";
  }

  identity action-marking {
    base node-action;
    description
      "It indicates that the node must mark the AltMark data field,
      according to the operations described in RFC 9341 and
      RFC 9342";
  }

  identity action-unmarking {
    base node-action;
    description
      "It indicates that the node must unmark the AltMark data field,
      according to the operations described in RFC 9341 and
      RFC 9342";
  }

  identity action-read {
    base node-action;
    description
      "It indicates the node only reads the AltMark data,
      according to the operations described in RFC 9341 and
      RFC 9342";
  }

  identity measurement-period {
    description
      "It indicates the AltMark Period.";
  }

  identity flow-mon-id {
    description
      "It indicates the FlowMonID.";
  }

  identity measurement-mode {
    description
      "It indicates the measurement mode.";
  }

  identity hbh-measurement {
    base measurement-mode;
    description
      "It indicates that hop-by-hop measurements can be enabled.";
  }

  identity e2e-measurement {
    base measurement-mode;
    description
      "It indicates that end-to-end measurements can be enabled.";
  }

  identity enable-loss-measurement {
    description
      "It indicates that loss measurements are enabled.";
    }

   identity enable-delay-measurement {
    description
      "It indicates that delay measurements are enabled.";
    }

 /*
  * TYPE DEFINITIONS
  */

  typedef altmark-filter-type {
    type identityref {
      base filter;
    }
    description
      "It specifies a known type of filter.";
  }

  typedef altmark-node-action {
    type identityref {
      base node-action;
    }
    description
      "It specifies a node action.";
  }

  typedef altmark-method-type {
    type identityref {
      base method;
    }
    description
      "It specifies the AltMark method used.";
  }

  typedef altmark-protocol-type {
    type identityref {
      base protocol;
    }
    description
      "It specifies a known type of carrier protocol for the AltMark
       data.";
  }

  typedef altmark-measurement-mode {
    type identityref {
      base measurement-mode;
    }
    description
      "It specifies the measurement mode.";
  }

 /*
  * GROUP DEFINITIONS
  */

  grouping altmark-filter {
    description "A grouping for AltMark filter definition";

    leaf filter-type {
      type altmark-filter-type;
      description "filter type";
    }

    leaf ace-name {
      when "derived-from-or-self(../filter-type,
      'altmark:acl-filter')";
      type leafref {
        path "/acl:acls/acl:acl/acl:aces/acl:ace/acl:name";
      }
      description "The Access Control Entry name is used to
      refer to an ACL specification.";
    }
  }

  grouping measurement-mode {
    description
      "A grouping for measurement mode.";

    leaf hbh-measurement {
      type boolean;
      default false;
      description
        "This object indicates that hop-by-hop measurements can be
        enabled.";
    }

    leaf e2e-measurement {
      type boolean;
      default false;
      description
        "This object indicates that end-to-end measurements can be
        enabled.";
    }
  }

  grouping altmark-setup {
    description
      "A grouping for AltMark profile.";

    leaf node-action {
      type altmark-node-action;
      default action-read;
      description
        "This object indicates the action that the node needs to
         take, i.e. marking/read/unmarking.";
    }

    leaf measurement-period {
      type uint64;
      description
      "It specifies the AltMark marking period.";
    }

    leaf flow-mon-id {
      type uint32;
      description
      "It specifies the FlowMonID.
      A 20-bit flow identifier. The field is set at the marking node.
      The FlowMonID can be uniformly assigned by a central controller
      or algorithmically generated by the marking node.
      The latter approach cannot guarantee the uniqueness of the
      FlowMonID, yet the conflict probability is small due to the
      large space.
      FlowMonID is used to identify the flow and to correlate the
      exported data of the same flow from multiple nodes and from
      multiple packets.";
    }

   }

  grouping altmark-admin-config {
    description
      "AltMark top-level administrative configuration.";

    leaf enabled {
      type boolean;
      default false;
      description
        "This object is to control the availability of configuration.
         It MUST be true before anything in the
         /altmark/altmark-profile can be edited.
         If false, any configuration in place is not used.";
    }
  }

 /*
  * DATA NODES
  */

  container AltMark {
    description "AltMark top level container";

    container altmark-info {
      config false;
      description
        "Describes information such as units or timestamp format
        that assists monitoring systems in the interpretation of the
        AltMark data.";

      leaf timestamp-type {
        type identityref {
          base lime:timestamp-type;
        }
        description
          "Type of timestamp, such as Truncated PTP or NTP.";
      }

      list available-interface {
        key "if-name";
        description
          "A list of available interfaces that support
          Alternate-Marking.";
        leaf if-name {
          type if:interface-ref;
          description "This is a reference to the Interface name.";
        }
      }
    }

    container altmark-profiles {
      description
        "Contains the AltMark profiles.";

      container admin-config {
        description
          "Contains all the administrative configurations related to
           the AltMark functionalities";

        uses altmark-admin-config;
      }

      list altmark-profile {
      if-feature altmark;
      key "profile-name";
      description
          "It describes the list of the AltMark profiles configured
          on the node";
      leaf profile-name {
          type string{
            length "1..300";
          }
        description
            "Unique identifier for each AltMark profile.";
        }

      container filter {
          uses altmark-filter;
          description
            "The filter which is used to indicate the flow where
            the AltMark is applied.";
        }

      leaf method-type {
          type altmark-method-type;
          description
            "This item is used to indicate the AltMark method.";
        }

      leaf protocol-type {
          type altmark-protocol-type;
          description
            "This item is used to indicate the carrier protocol where
            the AltMark is applied.";
        }

        uses altmark-setup;

        uses measurement-mode;

        leaf enable-loss-measurement {
            type boolean;
            default false;
            description
            "If true, it indicates that loss measurements are
            enabled.";
          }

        leaf enable-delay-measurement {
            type boolean;
            default false;
            description
            "If true, it indicates that delay measurements are
            enabled.";
          }

      }
     }
    }
}
