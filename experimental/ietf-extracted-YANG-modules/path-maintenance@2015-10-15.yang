submodule path-maintenance {
    belongs-to sfc-control-planes {
        prefix sfc-control-planes;
    }
    organization "ETRI.";
    contact
     "M-K. Shin mkshin@etri.re.kr
      M-J Choi mjchoi@kangwon.ac.kr";

    description
    "This module checks the aliveness of a SFP.
    This receive SFP name and returns aliveness
    result which is true or false value.";
    revision 2015-10-15{
        reference
        "draft-shin-sfc-control-plane-yang-00 -
        Yang Data Model for Service Function Chaining Control Plane";
    }
    container path-maintenance {
        description
        "This container checks the aliveness of a SFP.
        This receive SFP name and returns aliveness result
        which is true or false value.";

        leaf sfp-name {
            type string;
            description
            "The name of service function path.";
        }
        leaf aliveness-of-sfp {
            type boolean;
            description
            "Aliveness flag of the service function.";
        }
    }
    rpc check-path-aliveness {
        description "Check a path aliveness.";
        input  {
            leaf sfc-name {
                type string;
                description
                "The name of service function path.";
            }
        }
        output {
            leaf Aliveness {
                type boolean;
                description
                "Aliveness flag of the service function.";
            }
        }
    }
}
