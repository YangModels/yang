module ietf-bier-te {

  yang-version 1.1;

  namespace "urn:ietf:params:xml:ns:yang:ietf-bier-te";

  prefix bier-te;

  import ietf-routing {
    prefix "rt";
    reference
      "RFC 8349: A YANG Data Model for Routing Management
                 (NMDA Version)";
  }

  import ietf-interfaces {
    prefix "if";
    reference
      "RFC 8343: A YANG Data Model for Interface Management";
  }

  import ietf-routing-types {
    prefix "rt-types";
    reference
      "RFC 8294: Common YANG Data Types for the Routing Area";
  }

  organization " IETF BIER (Bit Indexed Explicit Replication)
                 Working Group";
  contact
    "WG Web:   <http://tools.ietf.org/wg/bier/>
     WG List:  <mailto:bier@ietf.org>

     Editor:   Zheng Zhang
               <mailto:zhang.zheng@zte.com.cn>
     Editor:   Cui Wang
               <mailto:wang.cui1@zte.com.cn>
     Editor:   Ran Chen
               <mailto:chen.ran@zte.com.cn>
     Editor:   Fangwei Hu
               <mailto:hu.fangwei@zte.com.cn>
     Editor:   Mahesh Sivakumar
               <mailto:masivaku@cisco.com>
     Editor:   Huanan Chen
               <mailto:chenhuanan@gsta.com>
    ";

  description
    "The module defines the YANG definitions for Traffic
     Engineering for Bit Index Explicit Replication (BIER-TE).

     Copyright (c) 2020 IETF Trust and the persons identified as
     authors of the code.  All rights reserved.

     Redistribution and use in source and binary forms, with or
     without modification, is permitted pursuant to, and subject
     to the license terms contained in, the Simplified BSD
     License set forth in Section 4.c of the IETF Trust's Legal
     Provisions Relating to IETF Documents
     (https://trustee.ietf.org/license-info).

     This version of this YANG module is part of RFC XXXX
     (https://www.rfc-editor.org/info/rfcXXXX); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2020-02-05 {
    description
    "Initial revision.";
    reference
      "I-D.ietf-bier-te-arch: Traffic Engineering for Bit Index
       Explicit Replication (BIER-TE)";
  }

  /*
  * Features
  */
  feature bier-te-frr {
    description
      "Support Fast Re-route feature in BIER TE.";
    reference
      "I-D.eckert-bier-te-frr: Protection Methods for BIER-TE";
  }
  feature bier-te-ecmp {
    description
      "Support ECMP feature in BIER TE.";
    reference
      "I-D.ietf-bier-te-arch: Traffic Engineering for Bit Index
       Explicit Replication (BIER-TE), section 3.2.3";
  }

  /*
   * Identities
   */

  identity bier-te {
    base rt:control-plane-protocol;
    description
      "Identity for the Traffic Engineering for Bit Index Explicit
       Replication (BIER-TE).";
    reference
      "I-D.ietf-bier-te-arch: Traffic Engineering for Bit Index
       Explicit Replication (BIER-TE)";
  }

  grouping bit-string {
    description
      "The bit string which each bit represents an adjacency.
       It is encapsulated in BIER header.";
    reference
        "I-D.ietf-bier-te-arch: Traffic Engineering for Bit Index
         Explicit Replication (BIER-TE), section 3.3.
         RFC8279: Multicast Using Bit Index Explicit Replication
         (BIER).
         RFC8296: Encapsulation for Bit Index Explicit Replication
         (BIER) in MPLS and Non-MPLS Networks.";

    list bit-string {
      key "index";
      description
        "As the definition in RFC 8279, the bit-string lengths are
         64, 128, 256, 512, 1024, 2048, 4096 bits. The according
         encapsulation is defined in RFC8296. BIER-TE uses the
         similar function for bit string.";

      leaf index {
        type uint8 {
          range "2..128";
        }
        description
          "The index of bit-mask. The minimum index value is 64 and
           the corresponding bit string length is 64 bits. The
           maximum index value is 128 and the corresponding
           bit-string length is 4096 bits.";
      }
      leaf bitmask {
        type uint32;
        description "The bit-string in 4-octet units.";
      }
    }
  } // bit-string

  grouping adj-type {
    description "The collection of all possible adjacency type.";

    leaf adj-type {
      type enumeration {
        enum p2p {
          description "Describes p2p adjacency.";
        }
        enum bfer {
          description "Describes bfer adjacency.";
        }
        enum leaf-bfer {
          description
            "Describes leaf-bfer adjacency. There is no next BFR that
             the packet should be forwarded.";
        }
        enum lan {
          description "Describes lan adjacency.";
        }
        enum spoke {
          description "Describes spoke adjacency of hub-and-spoke.";
        }
        enum ring-clockwise {
          description "Describes clockwise adjacency in ring.";
        }
        enum ring-counterclockwise {
          description "Describes counterclockwise adjacency in ring.";
        }
        enum ecmp {
          description
            "Describes ecmp adjacency. When the type is set to ecmp,
             the corresponding ecmp entry should be used to balance
             the load.";
        }
        enum virtual-link {
          description
            "Describes virtual adjacency between two indirect connect
             nodes.";
        }
        enum other {
          description "Describes other id type of adjacency.";
        }
      }
      description "The collection of all possible adjacency type.";
    }
  } // adj-type

  grouping te-bift-id {
    description "The index of BIER forwarding items. It usually
                 represents the combination of [SD, BSL, SI].";
    leaf type {
      type enumeration {
        enum mpls {
          description
            "The bift-id value is represent the BIER TE mpls
             forwarding plane. It is a mpls label.";
        }
        enum eth {
          description
            "The bift-id value is represent the BIER TE ethernet
             forwarding plane. It is an index of ethernet
             encapsulation.";
        }
        enum other {
          description "Describes other type of te-bift-id.";
        }
      }
      description "The types of BIER TE bift-id. If this type
                   is not set, mpls is default type.";
    }
    leaf value {
      type rt-types:mpls-label;
      mandatory true;
      description
        "The bift-id value of the forwarding item. It can be a mpls
         label or an index of ethernet encapsulation which is used
         to represent specific combination of [SD, BSL, SI]. The
         ethernet index value is the same range (20bits) as mpls
         label.";
    }
  } // te-bift-id

  grouping te-items {
    description "The BIER TE forwarding items collection.";

    container out-info {
      description
        "The information of out forwarding packets. Includes the
         outbound interface and the bift-id of next hop.";

      list out-if-list {
        key "fwd-intf";
        description
          "The outbound interface information for forwarding.";

        leaf fwd-intf {
          type if:interface-ref;
          mandatory true;
          description
            "The out interface of this forwarding item.";
        }
        leaf dnr-flag {
          type boolean;
          description
            "When the flag is set to 1, the BP of adjacency should not
             be reset when packet copies are created. The flag makes
             sense only when the forwarding type is 'connected'.";
        }
        container fwd-type {
          description
            "The collection of all possible forwarding types.";
          choice fwd-type {
            mandatory true;
            case connected {
              description
                "The forwarding type is connected. Mostly connected
                 interfaces.";
            }
            case routed {
              description
                "The forwarding type is routed. Mostly not connected
                 interfaces.";
            }
            case local-decap {
              description
                "Means that the packet should be decapsulated and
                 forward out of BIER domain.";
             }
            case other {
              description
                "Means that the packet should be discarded.";
            }
            description
              "The collection of all possible forwarding types.";
          }
        } // fwd-type

        container te-out-bift-id {
          description
            "The bift-id information corresponding to a specific
             outbound interface.";
          uses te-bift-id;
        }
      }
    }
  } // te-items

  /*
  * data nodes
  */
  augment "/rt:routing/rt:control-plane-protocols/"
       +"rt:control-plane-protocol" {
    description "The BIER TE information.";
    container bier-te {
      description "The BIER TE information container.";

      container te-adj {
        description "The BIER TE adjacency information.";
        list adj-if {
          key "name";
          description "List of BIER-TE interfaces.";
          leaf name {
            type if:interface-ref;
            description "Interface name reference.";
          }
          list subdomain {
            key "subdomain-id";
            description
              "The sub-domain which the interface belongs to.
               One interface can belong to many subdomains.";

            leaf subdomain-id {
              type uint16;
              description "The sub-domain-id of this sub-domain.";
              reference
                "RFC 8279: Multicast Using Bit Index Explicit
                 Replication (BIER)";
            }
            list si {
              key "si";
              description "The set identifier value.";

              leaf si{
                type uint16;
                mandatory true;
                description
                  "The set identifier of this forwarding item.";
              }
              leaf-list adj-id {
                type uint16;
                description "The ID of an adjacency.";
              }
            }
          }
          uses adj-type;
        }
      } // te-adj

      container te-fwd {
        description "The BIER TE forwarding information.";

        list subdomain {
          key "subdomain-id";
          description
            "The sub-domain which the interface belongs to.
             One interface can belong to many subdomains.";

          leaf subdomain-id {
            type uint16;
            description "The sub-domain-id of this sub-domain.";
            reference
              "RFC 8279: Multicast Using Bit Index Explicit
               Replication (BIER)";
          }
          list bsl {
            key "fwd-bsl";
            description "The forwarding items in one BSL.";
            leaf fwd-bsl {
              type uint16;
              description "The value of bitstringlength.";
            }
              list si {
                key "si";
                description
                  "The forwarding items in one combination of SD,
                   BSL and SI.";
                leaf si{
                  type uint16;
                  mandatory true;
                  description
                    "The set identifier of this forwarding item.";
                }
                            container te-bift-id {
                  description
                    "The bift-id which is used to locate the specific
                     forwarding item.";
                  uses te-bift-id;
                }

                list fwd-items {
                  key "te-bp";
                  description
                    "The forwarding information of one BIER TE item.";
                  leaf te-bp {
                    type uint16;
                    mandatory true;
                    description
                      "The bit index of a BIER TE forwarding item.";
                  }

                  leaf te-ecmp {
                    if-feature bier-te-ecmp;
                    type boolean;
                    description
                      "The list of the ecmp paths. When the type of
                       BP is set to ecmp, this interface ecmp list
                       should be used to balance the load on each
                       interface.";
                  }
                  uses te-items;

                  container te-frr {
                    if-feature bier-te-frr;
                    leaf frr-index {
                      type leafref {
                        path "../../../../../" +
                             "te-frr-items/btaft/frr-index";
                      }
                      description "The index of this frr path.";
                    }
                    container resetbitmask {
                      description
                        "The deleting bitmask of the forwarding item.";
                      uses bit-string;
                    }
                    description
                      "If this link is protected, frr items can be used to
                       forward flows when this link is down.";
                  } // te-frr
                } // fwd-items
              } // si
          } // bsl

          container te-frr-items {
            if-feature bier-te-frr;
            description "The TE fast re-route information.";
              list btaft {
              key "frr-index";
              description
                "The index of the frr paths. This item can be used
                 for multiple links protection in different SI.";
              leaf frr-index {
                type uint16;
                mandatory true;
                description "The frr item index.";
              }
              leaf frr-si{
                type uint16;
                mandatory true;
                description
                  "The set identifier of this forwarding item.";
              }
              leaf frr-bsl {
                type uint16;
                mandatory true;
                description "The value of bitstringlength.";
              }
              container addbitmask {
                description
                  "The adding bitmask of the forwarding item.
                   This item should be merged into the packet's
                   bit-string.";
                uses bit-string;
              }
            } // btaft
          } // te-frr-items
        } // subdomain
      } // te-fwd
    } // bier-te
  }

  /*
  * Notifications
  */
  notification bier-te-notification {
      description
        "The notification is sent when a condition changes.";
      list bp-is-zero {
          key "if-index";
          description "The adjacency id is zero. It is invalid.";
          leaf if-index {
              type if:interface-ref;
              description "The adjacency id is zero.";
          }
          uses adj-type;
      }
  }
}
