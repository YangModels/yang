module ietf-lisp-mapresolver {
  namespace "urn:ietf:params:xml:ns:yang:ietf-lisp-mapresolver";
  prefix lisp-mr;
  import ietf-lisp {
    prefix lisp;
  }
  import ietf-inet-types {
    prefix inet;
  }
  organization
   "IETF LISP (Locator/ID Separation Protocol) Working Group";
  contact
    "lisp@ietf.org";
  description
    "This YANG module defines the generic configuration
     data for a LISP Map-Resolver. The module can be extended by
     vendors to define vendor-specific configuration parameters
     and policies.

     Copyright (c) 2015 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 6338; see
     the RFC itself for full legal notices.
    ";
  revision 2015-07-02 {
    description
      "Initial revision.";
    reference
      "https://tools.ietf.org/html/rfc6833";
  }
  identity mr {
    base lisp:lisp-device;
    description
      "LISP Map-Resolver.";
  }
  augment "/lisp:lisp/lisp:devices/lisp:device" {
    when "lisp:type = lisp-mr:mr" {
      description
        "Augment is valid when LISP device type is Map-Resolver.";
    }
    description
      "This augments LISP devices list with Map-Resolver specific
       parameters.";
    container map-resolver-cfg {
      presence "LISP Map-Resolver operation enabled";
      description
        "Map-Resolver configuration parameters.";
      choice mapping-system {
        mandatory true;
        description
          "Mapping system interface.";
        container ddt-mapping-system {
          presence "DDT Mapping System in use";
          description
            "DDT mapping system interface.";
          leaf-list ddt-root {
            type inet:ip-address;
            description
              "List of DDT root addresses.";
          }
        }
        container alt-mapping-system{
          presence "ALT Mapping System in use";
          description
            "ALT mapping system interface.";
         // TBD
        }
      }
    }
  }
}
