module ietf-yang-opstate-metadata {
  namespace
    "urn:ietf:params:xml:ns:yang:ietf-yang-opstate-metadata";

  prefix "opstate";

  import ietf-yang-metadata {
    prefix "md";
  }

  organization
    "IETF NETCONF (Network Configuration Protocol) Working Group";

  contact
    "WG Web:   <http://tools.ietf.org/wg/netconf/>

     WG List:  <netconf@ietf.org>

     WG Chair: Mahesh Jethanandani
               <mjethanandani@gmail.com>

     WG Chair: Mehmet Ersue
               <mehmet.ersue@nsn.com>

     Editor:   Robert Wilton
               <rwilton@cisco.com>";

  description
    "This module defines YANG metadata to allow the reason why
     a config true node exists in the operational state datastore
     to be determined using YANG metadata.

     Copyright (c) 2016 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
      (http://trustee.ietf.org/license-info).

     This version of this YANG module is part of
     draft-wilton-netconf-opstate-metadata-00; see the Internet
     draft itself for full legal notices.";

  revision 2016-07-06 {
    description "Initial revision";

    reference
      "Internet draft: draft-wilton-netconf-opstate-metadata-00";
  }

  md:annotation cfg-status {
    type enumeration {
      enum applying {
        description
          "The configuration for the annotated node is currently
           changing (i.e. being created, deleted or changing in
           value) as part of an ongoing configuration operation";
      }
      enum applied {
        description
          "The configuration is fully applied.  The node exists in
           both the intended and applied datastores and has exactly
           the same value in both.";
      }
      enum applied-deviation {
        description
          "The configuration has been applied to the extend the
           server is able to, but the value in the applied
           configuration datastore does not exactly match the value
           in the intended configuration datastore.";
      }
      enum overridden {
        description
          "The configuration node value has been overridden by the
           same node in another configuration datastore.";
      }
      enum system-controlled {
        description
          "The configuration node only exists in the Operational
           State Datastore because it is system controlled. It is
           not present in the abstract applied configuration
           datastore.";
      }
      enum blocked {
        description
          "The system cannot apply the configuration because
           the required hardware resources are not present.  The
           configuration node does not exist in the applied
           configuration datastore.";
      }
      enum failed {
        description
          "The system cannot apply the configuration due to an
           error.  The configuration node does not exist in the
           applied configuration datastore.";
      }
    }
    description
      "Status indicates why a configuration node (i.e. config=true)
       in the operational-state datastore does not match the
       corresponding node in the intended config datastore";
  }

  md:annotation cfg-status-reason {
    when "../status = 'blocked' or ../status = 'failed'" {
      description
        "An optional status reason can be provided for blocked or
         failed configuration";
    }
    type string;
    description
      "Indicates the reason why the applied configuration node is
       blocked or failed";
  }
}
