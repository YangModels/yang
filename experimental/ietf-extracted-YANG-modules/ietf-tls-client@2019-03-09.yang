module ietf-tls-client {
  yang-version 1.1;
  namespace "urn:ietf:params:xml:ns:yang:ietf-tls-client";
  prefix "tlsc";

  import ietf-tls-common {
    prefix tlscmn;
    revision-date 2019-03-09; // stable grouping definitions
    reference
      "RFC XXXX: YANG Groupings for TLS Clients and TLS Servers";
  }

  import ietf-trust-anchors {
    prefix ta;
    reference
      "RFC YYYY: YANG Data Model for Global Trust Anchors";
  }

  import ietf-keystore {
    prefix ks;
    reference
      "RFC ZZZZ: YANG Data Model for a 'Keystore' Mechanism";
  }

  organization
   "IETF NETCONF (Network Configuration) Working Group";

  contact
   "WG Web:   <http://datatracker.ietf.org/wg/netconf/>
    WG List:  <mailto:netconf@ietf.org>
    Author:   Kent Watsen <mailto:kent+ietf@watsen.net>
    Author:   Gary Wu <mailto:garywu@cisco.com>";

  description
   "This module defines reusable groupings for TLS clients that
    can be used as a basis for specific TLS client instances.

    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 [RFC2119]
    [RFC8174] when, and only when, they appear in all
    capitals, as shown here.

    Copyright (c) 2019 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2019-03-09" {
    description
     "Initial version";
    reference
     "RFC XXXX: YANG Groupings for TLS Clients and TLS Servers";
  }

  // Features

  feature tls-client-hello-params-config {
    description
      "TLS hello message parameters are configurable on a TLS
       client.";
  }

  feature tls-client-keepalives {
    description
      "Per socket TLS keepalive parameters are configurable for
       TLS clients on the server implementing this feature.";
  }

  // Groupings

  grouping tls-client-grouping {
    description
      "A reusable grouping for configuring a TLS client without
       any consideration for how an underlying TCP session is
       established.";
    uses client-identity-grouping;
    uses server-auth-grouping;
    uses hello-params-grouping;
    uses keepalives-grouping;
  }

  grouping client-identity-grouping {
    description
      "A reusable grouping for configuring a TLS client identity.";
    container tls-client-identity {
      description
        "The credentials used by the client to authenticate to
         the TLS server.";

      choice auth-type {
        description
          "The authentication type.";
        container certificate {
          uses
            ks:local-or-keystore-end-entity-cert-with-key-grouping;
          description
            "A locally-defined or referenced certificate
             to be used for client authentication.";
          reference
            "RFC ZZZZ: YANG Data Model for a 'Keystore' Mechanism";
        }
      }
    }
  }

  grouping server-auth-grouping {
    description
      "A reusable grouping for configuring TLS server
       authentication.";
    container tls-server-auth {
      must 'pinned-ca-certs or pinned-server-certs';
      description
        "Trusted server identities.";
      leaf pinned-ca-certs {
        if-feature "ta:x509-certificates";
        type ta:pinned-certificates-ref;
        description
          "A reference to a list of certificate authority (CA)
           certificates used by the TLS client to authenticate
           TLS server certificates.  A server certificate is
           authenticated if it has a valid chain of trust to
           a configured pinned CA certificate.";
      }
      leaf pinned-server-certs {
        if-feature "ta:x509-certificates";
        type ta:pinned-certificates-ref;
        description
          "A reference to a list of server certificates used by
           the TLS client to authenticate TLS server certificates.
           A server certificate is authenticated if it is an
           exact match to a configured pinned server certificate.";
      }
    }
  }

  grouping hello-params-grouping {
    description
      "A reusable grouping for configuring a TLS transport
       parameters.";
    container tls-hello-params {
      if-feature tls-client-hello-params-config;
      uses tlscmn:hello-params-grouping;
      description
        "Configurable parameters for the TLS hello message.";
    }
  }

  grouping keepalives-grouping {
    description
      "A reusable grouping for configuring TLS client keepalive
       parameters.";
    container tls-keepalives {
      if-feature "tls-client-keepalives";
      description
        "Configures the keep-alive policy, to proactively test
         the aliveness of the TLS server.  An unresponsive
         TLS server is dropped after approximately max-wait
         * max-attempts seconds.";
      leaf max-wait {
        type uint16 {
          range "1..max";
        }
        units seconds;
        default 30;
        description
         "Sets the amount of time in seconds after which if no data
          has been received from the TLS server, a TLS-level message
          will be sent to test the aliveness of the TLS server.";
      }
      leaf max-attempts {
        type uint8;
        default 3;
        description
         "Sets the maximum number of sequential keep-alive messages
         that can fail to obtain a response from the TLS server
         before assuming the TLS server is no longer alive.";
      }
    }
  }
}
