module ietf-i2nsf-capability {
  yang-version 1.1;
  namespace
    "urn:ietf:params:xml:ns:yang:ietf-i2nsf-capability";
  prefix
    nsfcap;

  organization
    "IETF I2NSF (Interface to Network Security Functions)
     Working Group";

  contact
    "WG Web: <https://datatracker.ietf.org/wg/i2nsf/>
     WG List: <mailto:i2nsf@ietf.org>

     Editor: Susan Hares
     <mailto:shares@ndzh.com>

     Editor: Jaehoon (Paul) Jeong
     <mailto:pauljeong@skku.edu>

     Editor: Jinyong (Tim) Kim
     <mailto:timkim@skku.edu>

     Editor: Robert Moskowitz
     <mailto:rgm@htt-consult.com>

     Editor: Qiushi Lin
     <mailto:linqiushi@huawei.com>

     Editor: Patrick Lingga
     <mailto:patricklink@skku.edu>";

  description
    "This module is a YANG module for I2NSF Network Security
     Functions (NSFs)'s Capabilities.

     Copyright (c) 2022 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  // RFC Ed.: replace XXXX with an actual RFC number and remove
  // this note.

  revision "2022-03-23"{
    description "Initial revision.";
    reference
      "RFC XXXX: I2NSF Capability YANG Data Model";

    // RFC Ed.: replace XXXX with an actual RFC number and remove
    // this note.
  }

  /*
   * Identities
   */

  identity event {
    description
      "Base identity for I2NSF events.";
    reference
      "draft-ietf-i2nsf-nsf-monitoring-data-model-14: I2NSF NSF
       Monitoring Interface YANG Data Model - Event";
  }

  identity system-event {
    base event;
    description
      "Base identity for system event. System event (also called
       alert) is defined as a warning about any changes of
       configuration, any access violation, the information of
       sessions and traffic flows.";
    reference
      "draft-ietf-i2nsf-nsf-monitoring-data-model-14: I2NSF NSF
       Monitoring Interface YANG Data Model - System event";
  }

  identity system-alarm {
    base event;
    description
      "Base identity for system alarm. System alarm is defined as a
       warning related to service degradation in system hardware.";
    reference
      "draft-ietf-i2nsf-nsf-monitoring-data-model-14: I2NSF NSF
       Monitoring Interface YANG Data Model - System alarm";
  }

  identity access-violation {
    base system-event;
    description
      "Identity for access violation event. Access-violation system
       event is an event when a user tries to access (read, write,
       create, or delete) any information or execute commands
       above their privilege (i.e., not-conformant with the
       access profile).";
    reference
      "draft-ietf-i2nsf-nsf-monitoring-data-model-14: I2NSF NSF
       Monitoring Interface YANG Data Model - System event for access
       violation";
  }

  identity configuration-change {
    base system-event;
    description
      "Identity for configuration change event. Configuration change
       is a system event when a new configuration is added or an
       existing configuration is modified.";
    reference
      "draft-ietf-i2nsf-nsf-monitoring-data-model-14: I2NSF NSF
       Monitoring Interface YANG Data Model - System event for
       configuration change";
  }

  identity memory-alarm {
    base system-alarm;
    description
      "Memory is the hardware to store information temporarily or for
       a short period, i.e., Random Access Memory (RAM). A
       memory-alarm is emitted when the memory usage is exceeding
       the threshold.";
    reference
      "draft-ietf-i2nsf-nsf-monitoring-data-model-14: I2NSF NSF
       Monitoring Interface YANG Data Model - System alarm for
       memory";
  }

  identity cpu-alarm {
    base system-alarm;
    description
      "CPU is the Central Processing Unit that executes basic
       operations of the system. A cpu-alarm is emitted when the CPU
       usage is exceeding a threshold.";
    reference
      "draft-ietf-i2nsf-nsf-monitoring-data-model-14: I2NSF NSF
       Monitoring Interface YANG Data Model - System alarm for CPU";
  }

  identity disk-alarm {
    base system-alarm;
    description
      "Disk or storage is the hardware to store information for a
       long period, i.e., Hard Disk and Solid-State Drive. A
       disk-alarm is emitted when the disk usage is exceeding a
       threshold.";
    reference
      "draft-ietf-i2nsf-nsf-monitoring-data-model-14: I2NSF NSF
       Monitoring Interface YANG Data Model - System alarm for disk";
  }

  identity hardware-alarm {
    base system-alarm;
    description
      "A hardware alarm is emitted when a hardware failure (e.g.,
       CPU, memory, disk, or interface) is detected. A hardware
       failure is a malfunction within the electronic circuits or
       electromechanical components of the hardware that makes it
       unusable.";
    reference
      "draft-ietf-i2nsf-nsf-monitoring-data-model-14: I2NSF NSF
       Monitoring Interface YANG Data Model - System alarm for
       hardware";
  }

  identity interface-alarm {
    base system-alarm;
    description
      "Interface is the network interface for connecting a device
       with the network. The interface-alarm is emitted when the
       state of the interface is changed.";
    reference
      "draft-ietf-i2nsf-nsf-monitoring-data-model-14: I2NSF NSF
       Monitoring Interface YANG Data Model - System alarm for
       interface";
  }

  identity time {
    description
      "Base identity for time capabilities";
  }

  identity absolute-time {
    base time;
    description
      "absolute time capabilities.
       If a network security function has the absolute time
       capability, the network security function supports
       rule execution according to absolute time.";
  }

  identity periodic-time {
    base time;
    description
      "periodic time capabilities.
       If a network security function has the periodic time
       capability, the network security function supports
       rule execution according to periodic time.";
  }

  identity device-type {
    description
      "Base identity for device type condition capability. The
       capability for matching the source or destination device
       type.";
  }

  identity computer {
    base device-type;
    description
      "Identity for computer such as personal computer (PC)
       and server";
  }

  identity mobile-phone {
    base device-type;
    description
      "Identity for mobile-phone such as smartphone and
       cellphone";
  }

  identity voip-vocn-phone {
    base device-type;
    description
      "Identity for VoIP (Voice over Internet Protocol) or VoCN
       (Voice over Cellular Network, such as Voice over LTE or 5G)
       phone";
  }

  identity tablet {
    base device-type;
    description
      "Identity for tablet";
  }

  identity network-infrastructure-device {
    base device-type;
    description
      "Identity for network infrastructure devices
       such as switch, router, and access point";
  }

  identity iot {
    base device-type;
    description
      "Identity for Internet of Things (IoT) devices
       such as sensors, actuators, and low-power
       low-capacity computing devices";
  }

  identity ot {
    base device-type;
    description
      "Identity for Operational Technology (OT) devices (also
       known as industrial control systems) that interact
       with the physical environment and detect or cause direct
       change through the monitoring and control of devices,
       processes, and events such as programmable logic
       controllers (PLCs), digital oscilloscopes, building
       management systems (BMS), and fire control systems";
  }

  identity vehicle {
    base device-type;
    description
      "Identity for transportation vehicles that connect to and
       share data through the Internet over Vehicle-to-Everything
       (V2X) communications.";
  }

  identity user-condition {
    description
      "Base identity for user condition capability. This is the
       capability of mapping user(s) into their corresponding IP
       address";
  }

  identity user {
    base user-condition;
    description
      "Identity for user condition capability.
       A user (e.g., employee) can be mapped to an IP address of
       a computing device (e.g., computer, laptop, and virtual
       machine) which the user is using.";
  }

  identity group {
    base user-condition;
    description
      "Identity for group condition capability.
       A group (e.g., employees) can be mapped to multiple IP
       addresses of computing devices (e.g., computers, laptops,
       and virtual machines) which the group is using.";
  }

  identity geographic-location {
    description
      "Base identity for geographic location condition capability";
    reference
      "RFC 8805: A Format for Self-Published IP Geolocation Feeds -
       An access control for a geographical location (i.e.,
       geolocation) that has the corresponding IP prefix.";
  }

  identity source-location {
    base geographic-location;
    description
      "Identity for source geographic location condition capability";
    reference
      "RFC 8805: A Format for Self-Published IP Geolocation Feeds -
       An access control for a geographical location (i.e.,
       geolocation) that has the corresponding IP prefix.";
  }

  identity destination-location {
    base geographic-location;
    description
      "Identity for destination geographic location condition
       capability";
    reference
      "RFC 8805: A Format for Self-Published IP Geolocation Feeds -
       An access control for a geographical location (i.e.,
       geolocation) that has the corresponding IP prefix.";
  }

  identity directional {
    description
      "Base identity for directional traffic flow export capability";
    reference
      "RFC 5103: Bidirectional Flow Export Using IP Flow Information
       Export (IPFIX) - Terminology Unidirectional and Bidirectional
       Flow";
  }

  identity unidirectional {
    base directional;
    description
      "Identity for unidirectional traffic flow export.";
    reference
      "RFC 5103: Bidirectional Flow Export Using IP Flow Information
       Export (IPFIX) - Terminology Unidirectional Flow";
  }

  identity bidirectional {
    base directional;
    description
      "Identity for bidirectional traffic flow export.";
    reference
      "RFC 5103: Bidirectional Flow Export Using IP Flow Information
       Export (IPFIX) - Terminology Bidirectional Flow";
  }

  identity protocol {
    description
      "Base identity for protocols";
  }

  identity ethernet {
    base protocol;
    description
      "Base identity for Ethernet protocol.";
  }

  identity source-mac-address {
    base ethernet;
    description
      "Identity for the capability of matching Media Access Control
       (MAC) source address(es) condition capability.";
    reference
      "IEEE 802.3 - 2018: IEEE Standard for Ethernet";
  }

  identity destination-mac-address {
    base ethernet;
    description
      "Identity for the capability of matching Media Access Control
       (MAC) destination address(es) condition capability.";
    reference
      "IEEE 802.3 - 2018: IEEE Standard for Ethernet";
  }

  identity ether-type {
    base ethernet;
    description
      "Identity for the capability of matching the EtherType in
       Ethernet II and Length in Ethernet 802.3 of a packet.";
    reference
      "IEEE 802.3 - 2018: IEEE Standard for Ethernet";
  }
  identity ip {
    base protocol;
    description
      "Base identity for internet/network layer protocol,
       e.g., IPv4, IPv6, and ICMP.";
  }

  identity ipv4 {
    base ip;
    description
      "Base identity for IPv4 condition capability";
    reference
      "RFC 791: Internet Protocol";
  }

  identity ipv6 {
    base ip;
    description
      "Base identity for IPv6 condition capabilities";
    reference
      "RFC 8200: Internet Protocol, Version 6 (IPv6)
       Specification";
  }

  identity dscp {
    base ipv4;
    base ipv6;
    description
      "Identity for the capability of matching IPv4 annd IPv6
       Differentiated Services Codepoint (DSCP) condition";
    reference
      "RFC 791: Internet Protocol - Type of Service
       RFC 2474: Definition of the Differentiated
       Services Field (DS Field) in the IPv4 and
       IPv6 Headers
       RFC 8200: Internet Protocol, Version 6 (IPv6)
       Specification - Traffic Class";
  }

  identity ecn {
    base ipv4;
    base ipv6;
    description
      "Identity for the capability of matching IPv4 annd IPv6
       Explicit Congestion Notification (ECN) condition";
    reference
      "RFC 3168: The Addition of Explicit Congestion
       Notification (ECN) to IP.
       RFC 8311: Relaxing Restrictions on Explicit Congestion
       Notification (ECN) Experimentation";
  }

  identity total-length {
    base ipv4;
    base ipv6;
    description
      "Identity for the capability of matching IPv4 Total Length
       header field or IPv6 Payload Length header field.

       IPv4 Total Length is the length of datagram, measured in
       octets, including internet header and data.

       IPv6 Payload Length is the length of the IPv6 payload, i.e.,
       the rest of the packet following the IPv6 header, measured in
       octets.";
    reference
      "RFC 791: Internet Protocol - Total Length
       RFC 8200: Internet Protocol, Version 6 (IPv6)
       Specification - Payload Length";
  }

  identity ttl {
    base ipv4;
    base ipv6;
    description
      "Identity for the capability of matching IPv4 Time-To-Live
       (TTL) or IPv6 Hop Limit.";
    reference
      "RFC 791: Internet Protocol - Time To Live (TTL)
       RFC 8200: Internet Protocol, Version 6 (IPv6)
       Specification - Hop Limit";
  }

  identity next-header {
    base ipv4;
    base ipv6;
    description
      "Identity for the capability of matching IPv4 Protocol field
       and IPv6 Next Header field. Note that IPv4 Protocol field is
       equivalent to IPv6 Next Header field.";
    reference
      "IANA Website: Assigned Internet Protocol Numbers
       - Protocol Numbers
       RFC 791: Internet Protocol - Protocol
       RFC 8200: Internet Protocol, Version 6 (IPv6)
       Specification - Next Header";
  }

  identity source-address {
    base ipv4;
    base ipv6;
    description
      "Identity for the capability of matching IPv4 or IPv6 source
       address(es) condition capability.";
    reference
      "RFC 791: Internet Protocol - Address
       RFC 8200: Internet Protocol, Version 6 (IPv6)
       Specification - Source Address";
  }

  identity destination-address {
    base ipv4;
    base ipv6;
    description
      "Identity for the capability of matching IPv4 or IPv6
       destination address(es) condition capability.";
    reference
      "RFC 791: Internet Protocol - Address
       RFC 8200: Internet Protocol, Version 6 (IPv6)
       Specification - Destination Address";
  }

  identity flow-direction {
    base ipv4;
    base ipv6;
    description
      "Identity for flow direction of matching IPv4/IPv6 source
       or destination address(es) condition capability where a flow's
       direction is either unidirectional or bidirectional";
    reference
      "RFC 791: Internet Protocol
       RFC 8200: Internet Protocol, Version 6 (IPv6)
       Specification";
  }

  identity ihl {
    base ipv4;
    description
      "Identity for matching IPv4 header-length (IHL)
      condition capability";
    reference
      "RFC 791: Internet Protocol - Header Length";
  }

  identity identification {
    base ipv4;
    description
      "Identity for IPv4 identification condition capability.
       IPv4 ID field is used for fragmentation and reassembly.";
    reference
      "RFC 791: Internet Protocol - Identification
       RFC 6864: Updated Specification of the IPv4 ID Field -
       Fragmentation and Reassembly";
  }

  identity fragment-offset {
    base ipv4;
    description
      "Identity for matching IPv4 fragment offset
       condition capability";
    reference
      "RFC 791: Internet Protocol - Fragmentation Offset";
  }

  identity flow-label {
    base ipv6;
    description
      "Identity for matching IPv6 flow label
       condition capability";
    reference
      "RFC 8200: Internet Protocol, Version 6 (IPv6)
       Specification - Flow Label
       RFC 6437: IPv6 Flow Label Specification";
  }

  identity header-order {
    base ipv6;
    description
      "Identity for IPv6 extension header order condition
       capability";
    reference
      "RFC 8200: Internet Protocol, Version 6 (IPv6)
       Specification - Extension Header Order";
  }

  identity hop-by-hop {
    base ipv6;
    description
      "Identity for IPv6 hop by hop options header
       condition capability";
    reference
      "RFC 8200: Internet Protocol, Version 6 (IPv6)
      Specification - Hop-by-Hop Options Header";
  }

  identity routing-header {
    base ipv6;
    description
      "Identity for IPv6 routing header condition capability. This
       capability supports only a set of core IPv6 routing headers,
       not all defined routing headers and deprecated.";
    reference
      "RFC 8200: Internet Protocol, Version 6 (IPv6)
      Specification - Routing Header";
  }

  identity fragment-header {
    base ipv6;
    description
      "Identity for IPv6 fragment header condition
       capability";
    reference
      "RFC 8200: Internet Protocol, Version 6 (IPv6)
      Specification - Fragment Header";
  }

  identity destination-options {
    base ipv6;
    description
      "Identity for IPv6 destination options condition
       capability";
    reference
      "RFC 8200: Internet Protocol, Version 6 (IPv6)
      Specification - Destination Options";
  }

  identity transport-protocol {
    base protocol;
    description
      "Base identity for Layer 4 protocol condition capabilities,
       e.g., TCP, UDP, SCTP, and DCCP";
  }

  identity tcp {
    base transport-protocol;
    description
      "Base identity for TCP condition capabilities";
    reference
      "draft-ietf-tcpm-rfc793bis-25: Transmission Control Protocol
       (TCP) Specification";
  }

  identity udp {
    base transport-protocol;
    description
      "Base identity for UDP condition capabilities";
    reference
      "RFC 768: User Datagram Protocol";
  }

  identity sctp {
    base transport-protocol;
    description
      "Base identity for SCTP condition capabilities";
    reference
      "draft-ietf-tsvwg-rfc4960-bis-18: Stream Control Transmission
       Protocol";
  }

  identity dccp {
    base transport-protocol;
    description
      "Base identity for DCCP condition capabilities";
    reference
      "RFC 4340: Datagram Congestion Control Protocol";
  }

  identity source-port-number {
    base tcp;
    base udp;
    base sctp;
    base dccp;
    description
      "Identity for matching TCP, UDP, SCTP, and DCCP source port
       number condition capability";
    reference
      "draft-ietf-tcpm-rfc793bis-25: Transmission Control Protocol
       (TCP) Specification
       RFC 768: User Datagram Protocol
       draft-ietf-tsvwg-rfc4960-bis-18: Stream Control Transmission
       Protocol
       RFC 4340: Datagram Congestion Control Protocol";
  }

  identity destination-port-number {
    base tcp;
    base udp;
    base sctp;
    base dccp;
    description
      "Identity for matching TCP, UDP, SCTP, and DCCP destination
       port number condition capability";
    reference
      "draft-ietf-tcpm-rfc793bis-25: Transmission Control Protocol
       (TCP) Specification";
  }

  identity flags {
    base ipv4;
    base tcp;
    description
      "Identity for IPv4 flags and TCP control bits (flags) condition
       capability. Note that this should not be interpreted such that
       IPv4 flags and TCP flags are similar.
       The IPv4 flags is the three-bit field in IPv4 header to
       control and identify fragments.
       The TCP flags is the multiple one-bit fields after the
       reserved field in TCP header that indicates the connection
       states or provides additional information.";
    reference
      "RFC 791: Internet Protocol - Flags
       draft-ietf-tcpm-rfc793bis-25: Transmission Control Protocol
       (TCP) Specification - TCP Header Flags
       RFC 3168: The Addition of Explicit Congestion Notification
       (ECN) to IP - ECN-Echo (ECE) Flag and Congestion Window
       Reduced (CWR) Flag
       draft-ietf-tcpm-accurate-ecn-15: More Accurate ECN Feedback
       in TCP - ECN-Echo (ECE) Flag and Congestion Window Reduced
       (CWR) Flag";
  }

  identity options {
    base tcp;
    description
      "Identity for matching TCP options header field condition
       capability. When an NSF claims to have this capability, the
       NSF should be able to match the TCP options header field in
       binary.";
    reference
      "draft-ietf-tcpm-rfc793bis-25: Transmission Control Protocol
       (TCP) Specification
       RFC 6691: TCP Options and Maximum Segment Size
       RFC 7323: TCP Extensions for High Performance";
  }

  identity data-offset {
    base tcp;
    base dccp;
    description
      "Identity for matching TCP and DCCP Data Offset condition
       capability.
       The TCP Data Offset header field represents the size of the
       TCP header, expressed in 32-bit words.
       The DCCP Data Offset is the offset from the start of the
       packet's DCCP header to the start of its application data
       area, in 32-bit words.";
    reference
      "draft-ietf-tcpm-rfc793bis-25: Transmission Control Protocol
       (TCP) Specification - Data Offset
       RFC 4340: Datagram Congestion Control Protocol";
  }

  identity reserved {
    base tcp;
    description
      "Identity for TCP header reserved field condition capability.
       The set of control bits reserved for future used. The control
       bits are also known as flags. Must be zero in generated
       segments and must be ignored in received segments, if
       corresponding future features are unimplemented by the
       sending or receiving host.";
    reference
      "draft-ietf-tcpm-rfc793bis-25: Transmission Control Protocol
       (TCP) Specification";
  }

  identity window-size {
    base tcp;
    description
      "Identity for TCP header Window field condition capability.
       The number of data octets beginning with the one indicated
       in the acknowledgment field that the sender of this segment
       is willing to accept.";
    reference
      "draft-ietf-tcpm-rfc793bis-25: Transmission Control Protocol
       (TCP) Specification";
  }

  identity urgent-pointer {
    base tcp;
    description
      "Identity for TCP Urgent Pointer header field condition
       capability. The Urgent Pointer field in TCP describes the
       current value of urgent pointer as a positive offset from
       the sequence number in this segment. The urgent pointer
       points to the sequence number of the octet following the
       urgent data. This field is only be interpreted in segments
       with the URG control bit set.";
    reference
      "draft-ietf-tcpm-rfc793bis-25: Transmission Control Protocol
       (TCP) Specification";
  }

  identity length {
    base udp;
    base sctp;
    description
      "Identity for matching UDP length and SCTP chunk length
       condition capability.
       The UDP length is the length in octets of this user datagram
       including this header and the datagram. The UDP length can be
       smaller than the IP transport length for UDP transport layer
       options.
       The SCTP chunk length represents the size of the chunk in
       bytes including the SCTP Chunk type, Chunk flags, Chunk flags,
       and Chunk Value fields.";
    reference
      "RFC 768: User Datagram Protocol - Length
       draft-ietf-tsvwg-udp-options: Transport Options for UDP
       draft-ietf-tsvwg-rfc4960-bis-18: Stream Control Transmission
       Protocol - Chunk Length";
  }

  identity chunk-type {
    base sctp;
    description
      "Identity for SCTP chunk type condition capability";
    reference
      "draft-ietf-tsvwg-rfc4960-bis-18: Stream Control Transmission
       Protocol - Chunk Type";
  }

  identity service-code {
    base dccp;
    description
      "Identity for DCCP Service Code condition capability";
    reference
      "RFC 4340: Datagram Congestion Control Protocol
       RFC 5595: The Datagram Congestion Control Protocol (DCCP)
       Service Codes
       RFC 6335: Internet Assigned Numbers Authority (IANA)
       Procedures for the Management of the Service Name and
       Transport Protocol Port Number Registry - Service Code";
  }

  identity icmp {
    base protocol;
    description
      "Base identity for ICMPv4 and ICMPv6 condition capability";
    reference
      "RFC 792: Internet Control Message Protocol
       RFC 4443: Internet Control Message Protocol (ICMPv6)
       for the Internet Protocol Version 6 (IPv6) Specification
       - ICMPv6";
  }

  identity icmpv4 {
    base icmp;
    description
      "Base identity for ICMPv4 condition capability";
    reference
      "RFC 792: Internet Control Message Protocol";
  }

  identity icmpv6 {
    base icmp;
    description
      "Base identity for ICMPv6 condition capability";
    reference
      "RFC 4443: Internet Control Message Protocol (ICMPv6)
       for the Internet Protocol Ver sion 6 (IPv6) Specification
       - ICMPv6";
  }

  identity type {
    base icmpv4;
    base icmpv6;
    base dccp;
    description
      "Identity for ICMPv4, ICMPv6, and DCCP type condition
       capability";
    reference
      "RFC 792: Internet Control Message Protocol
       RFC 4443: Internet Control Message Protocol (ICMPv6)
       for the Internet Protocol Version 6 (IPv6) Specification
       - ICMPv6
       RFC 4340: Datagram Congestion Control Protocol";
  }

  identity code {
    base icmpv4;
    base icmpv6;
    description
      "Identity for ICMPv4 and ICMPv6 code condition capability";
    reference
      "RFC 792: Internet Control Message Protocol
       RFC 4443: Internet Control Message Protocol (ICMPv6)
       for the Internet Protocol Version 6 (IPv6) Specification
       - ICMPv6";
  }

  identity application-protocol {
    base protocol;
    description
      "Base identity for Application protocol. Note that a subset of
       application protocols (e.g., HTTP, HTTPS, FTP, POP3, and
       IMAP) are handled in this YANG module, rather than all
       the existing application protocols.";
  }

  identity http {
    base application-protocol;
    description
      "The identity for Hypertext Transfer Protocol version 1.1
       (HTTP/1.1).";
    reference
      "draft-ietf-httpbis-semantics-19: HTTP Semantics
       draft-ietf-httpbis-messaging-19: HTTP/1.1";
  }

  identity https {
    base application-protocol;
    description
      "The identity for Hypertext Transfer Protocol version 1.1
       (HTTP/1.1) over TLS.";
    reference
      "draft-ietf-httpbis-semantics-19: HTTP Semantics
       draft-ietf-httpbis-messaging-19: HTTP/1.1";
  }

  identity http2 {
    base application-protocol;
    description
      "The identity for Hypertext Transfer Protocol version 2
       (HTTP/2).";
    reference
      "draft-ietf-httpbis-http2bis-07: HTTP/2";
  }
  identity https2 {
    base application-protocol;
    description
      "The identity for Hypertext Transfer Protocol version 2
       (HTTP/2) over TLS.";
    reference
      "draft-ietf-httpbis-http2bis-07: HTTP/2";
  }

  identity ftp {
    base application-protocol;
    description
      "The identity for File Transfer Protocol.";
    reference
      "RFC 959: File Transfer Protocol (FTP)";
  }

  identity ssh {
    base application-protocol;
    description
      "The identity for Secure Shell (SSH) protocol.";
    reference
      "RFC 4250: The Secure Shell (SSH) Protocol";
  }

  identity telnet {
    base application-protocol;
    description
      "The identity for telnet.";
    reference
      "RFC 854: Telnet Protocol";
  }

  identity smtp {
    base application-protocol;
    description
      "The identity for Simple Mail Transfer Protocol.";
    reference
      "RFC 5321: Simple Mail Transfer Protocol (SMTP)";
  }

  identity pop3 {
    base application-protocol;
    description
      "The identity for Post Office Protocol 3 (POP3).";
    reference
      "RFC 1939: Post Office Protocol - Version 3 (POP3)";
  }
  identity pop3s {
    base application-protocol;
    description
      "The identity for Post Office Protocol 3 (POP3) over TLS";
    reference
      "RFC 1939: Post Office Protocol - Version 3 (POP3)
       RFC 2595: Using TLS with IMAP, POP3 and ACAP";
  }

  identity imap {
    base application-protocol;
    description
      "The identity for Internet Message Access Protocol (IMAP).";
    reference
      "RFC 9051: Internet Message Access Protocol (IMAP) - Version
       4rev2";
  }

  identity imaps {
    base application-protocol;
    description
      "The identity for Internet Message Access Protocol (IMAP) over
       TLS";
    reference
      "RFC 9051: Internet Message Access Protocol (IMAP) - Version
       4rev2
       RFC 2595: Using TLS with IMAP, POP3 and ACAP";
  }

  identity action {
    description
      "Base identity for action capability";
  }

  identity log-action {
    base action;
    description
      "Base identity for log-action capability";
  }

  identity ingress-action {
    base action;
    description
      "Base identity for ingress-action capability";
    reference
      "RFC 8329: Framework for Interface to Network Security
       Functions - Section 7.2";
  }
  identity egress-action {
    base action;
    description
      "Base identity for egress-action capability";
    reference
      "RFC 8329: Framework for Interface to Network Security
       Functions - Section 7.2";
  }

  identity default-action {
    base action;
    description
      "Base identity for default-action capability";
  }

  identity rule-log {
    base log-action;
    description
      "Identity for rule log. Log the policy rule that has been
       triggered.";
  }

  identity session-log {
    base log-action;
    description
      "Identity for session log. A session is a connection (i.e.,
       traffic flow) of a data plane that includes source and
       destination of IP addresses and transport port numbers with
       the protocol used. Log the session that triggered a policy
       rule.";
  }

  identity pass {
    base ingress-action;
    base egress-action;
    base default-action;
    description
      "Identity for pass action capability. The pass action allows
       packet or flow to go through the NSF entering or exiting the
       internal network.";
  }

  identity drop {
    base ingress-action;
    base egress-action;
    base default-action;
    description
      "Identity for drop action capability. The drop action denies
       a packet to go through the NSF entering or exiting the
       internal network without sending any response back to the
       source.";
  }

  identity reject {
    base ingress-action;
    base egress-action;
    base default-action;
    description
      "Identity for reject action capability. The reject action
       denies a packet to go through the NSF entering or exiting the
       internal network and sends a response back to the source.
       The response depends on the packet and implementation.
       For example, a TCP packet is rejected with TCP RST response
       or a UDP packet may be rejected with an ICMPv4 response
       message with Type 3 Code 3 or ICMPv6 response message
       Type 1 Code 4 (i.e., Destination Unreachable: Destination
       port unreachable) ";
  }

  identity mirror {
    base ingress-action;
    base egress-action;
    base default-action;
    description
      "Identity for mirror action capability. The mirror action
       copies packet and send it to the monitoring entity while still
       allow the packet or flow to go through the NSF.";
  }

  identity rate-limit {
    base ingress-action;
    base egress-action;
    base default-action;
    description
      "Identity for rate limiting action capability. The rate limit
       action limits the number of packets or flows that can go
       through the NSF by dropping packets or flows (randomly or
       systematically).";
  }

  identity invoke-signaling {
    base egress-action;
    description
      "Identity for invoke signaling action capability. The invoke
       signaling action is used to convey information of the event
       triggering this action to a monitoring entity";
  }

  identity tunnel-encapsulation {
    base egress-action;
    description
      "Identity for tunnel encapsulation action capability. The
       tunnel encapsulation action is used to encapsulate the packet
       to be tunneled across the network to enable a secure
       connection.";
  }

  identity forwarding {
    base egress-action;
    description
      "Identity for forwarding action capability. The forwarding
       action is used to relay the packet from one network segment
       to another node in the network.";
  }

  identity transformation {
    base egress-action;
    description
      "Identity for transformation action capability. The
       transformation action is used to transform a packet by
       modifying it (e.g., HTTP-to-CoAP packet translation).
       Note that a subset of transformation (e.g., HTTP-to-CoAP) is
       handled in this YANG module, rather than all the existing
       transformations.  Specific algorithmic transformations can be
       executed by a middlebox (e.g., NSF) for a given transformation
       name.";
    reference
      "RFC 8075: Guidelines for Mapping Implementations: HTTP to the
       Constrained Application Protocol (CoAP) - Translation between
       HTTP and CoAP.";
  }

  identity resolution-strategy {
    description
      "Base identity for resolution strategy capability";
  }

  identity fmr {
    base resolution-strategy;
    description
      "Identity for First Matching Rule (FMR) resolution
       strategy capability";
  }

  identity lmr {
    base resolution-strategy;
    description
      "Identity for Last Matching Rule (LMR) resolution
       strategy capability";
  }

  identity pmre {
    base resolution-strategy;
    description
      "Identity for Prioritized Matching Rule with Errors (PMRE)
       resolution strategy capability";
  }

  identity pmrn {
    base resolution-strategy;
    description
      "Identity for Prioritized Matching Rule with No Errors (PMRN)
       resolution strategy capability";
  }

  identity advanced-nsf {
    description
      "Base identity for advanced Network Security Function (NSF)
       capability.";
  }

  identity content-security-control {
    base advanced-nsf;
    description
      "Base identity for content security control. Content security
       control is an NSF that evaluates a packet's payload such as
       Intrusion Prevention System (IPS), URL-Filtering, Antivirus,
       and VoIP/CN Filter.";
  }

  identity attack-mitigation-control {
    base advanced-nsf;
    description
      "Base identity for attack mitigation control. Attack mitigation
       control is an NSF that mitigates an attack such as anti-DDoS
       or DDoS-mitigator.";
  }

  identity ips {
    base content-security-control;
    description
      "Base identity for IPS (Intrusion Prevention System) capability
       that prevents malicious activity within a network";
  }

  identity url-filtering {
    base content-security-control;
    description
      "Base identity for url filtering capability that limits access
       by comparing the web traffic's URL with the URLs for web
       filtering in a database";
  }

  identity anti-virus {
    base content-security-control;
    description
      "Base identity for antivirus capability to protect the network
       by detecting and removing viruses.";
  }

  identity voip-vocn-filtering {
    base content-security-control;
    description
      "Base identity for an advanced NSF for VoIP (Voice over
       Internet Protocol) and VoCN (Voice over Cellular Network,
       such as Voice over LTE or 5G) Security Service capability
       to filter the VoIP/VoCN packets or flows.";
    reference
      "RFC 3261: SIP: Session Initiation Protocol";
  }

  identity anti-ddos {
    base attack-mitigation-control;
    description
      "Base identity for advanced NSF Anti-DDoS Attack or DDoS
       Mitigator capability.";
  }

  identity packet-rate {
    base anti-ddos;
    description
      "Identity for advanced NSF Anti-DDoS detecting Packet Rate
       Capability where a packet rate is defined as the arrival rate
       of Packets toward a victim destination node.  The NSF with
       this capability can detect the incoming packet rate and create
       an alert if the rate exceeds the threshold.";

  }

  identity flow-rate {
    base anti-ddos;
    description
      "Identity for advanced NSF Anti-DDoS detecting Flow Rate
       Capability where a flow rate is defined as the arrival rate of
       flows towards a victim destination node.  The NSF with this
       capability can detect the incoming flow rate and create an
       alert if the rate exceeds the threshold.";
  }

  identity byte-rate {
    base anti-ddos;
    description
      "Identity for advanced NSF Anti-DDoS detecting Byte Rate
       Capability where a byte rate is defined as the arrival rate of
       Bytes toward a victim destination node.  The NSF with this
       capability can detect the incoming byte rate and create an
       alert if the rate exceeds the threshold.";
  }

  identity signature-set {
    base ips;
    description
      "Identity for the capability of IPS to set the signature.
       Signature is a set of rules to detect an intrusive activity.";
    reference
      "RFC 4766: Intrusion Detection Message Exchange Requirements -
       Section 2.2.13";
  }

  identity exception-signature {
    base ips;
    description
      "Identity for the capability of IPS to exclude signatures from
       detecting the intrusion.";
    reference
      "RFC 4766: Intrusion Detection Message Exchange Requirements -
       Section 2.2.13";
  }

  identity detect {
    base anti-virus;
    description
      "Identity for advanced NSF Antivirus capability to detect
       viruses using a security profile. The security profile is used
       to scan threats, such as virus, malware, and spyware. The NSF
       should be able to update the security profile.";
  }

  identity exception-files {
    base anti-virus;
    description
      "Identity for advanced NSF Antivirus capability to exclude a
       certain file type or name from detection.";
  }

  identity pre-defined {
    base url-filtering;
    description
      "Identity for pre-defined URL Database condition capability
       where URL database is a public database for URL filtering.";
  }

  identity user-defined {
    base url-filtering;
    description
      "Identity for user-defined URL Database condition capability
       that allows a user's manual addition of URLs for URL
       filtering.";
  }

  identity call-id {
    base voip-vocn-filtering;
    description
      "Identity for advanced NSF VoIP/VoCN Call Identifier (ID)
       capability.";
  }

  identity user-agent {
    base voip-vocn-filtering;
    description
      "Identity for advanced NSF VoIP/VoCN User Agent capability.";
  }

  /*
   *  Grouping
   */

  grouping nsf-capabilities {
    description
      "Network Security Function (NSF) Capabilities";
    reference
      "RFC 8329: Framework for Interface to Network Security
       Functions - I2NSF Flow Security Policy Structure.";

    leaf-list directional-capabilities {
      type identityref {
        base directional;
      }
      description
        "The capability of an NSF for handling directional traffic
         flow (i.e., unidirectional or bidirectional traffic flow).";
    }

    container event-capabilities {
      description
        "Capabilities of events.
         If a network security function has the event capabilities,
         the network security function supports rule execution
         according to system event and system alarm.";

      reference
        "RFC 8329: Framework for Interface to Network Security
         Functions - Section 7.
         draft-ietf-i2nsf-nsf-monitoring-data-model-14: I2NSF
         NSF Monitoring Interface YANG Data Model - System Alarm and
         System Events.";

      leaf-list system-event-capability {
        type identityref {
          base system-event;
        }
        description
          "System event capabilities";
      }

      leaf-list system-alarm-capability {
        type identityref {
          base system-alarm;
        }
        description
          "System alarm capabilities";
      }
    }

    container condition-capabilities {
      description
        "Conditions capabilities.";
      container generic-nsf-capabilities {
        description
          "Conditions capabilities.
           If a network security function has the condition
           capabilities, the network security function
           supports rule execution according to conditions of
           IPv4, IPv6, TCP, UDP, SCTP, DCCP, ICMP, or ICMPv6.";
        reference
          "RFC 768: User Datagram Protocol - UDP.
           RFC 791: Internet Protocol - IPv4.
           RFC 792: Internet Control Message Protocol - ICMP.
           RFC 4443: Internet Control Message Protocol (ICMPv6)
           for the Internet Protocol Version 6 (IPv6) Specification
           - ICMPv6.
           draft-ietf-tsvwg-rfc4960-bis-18: Stream Control
           Transmission Protocol - SCTP.
           RFC 8200: Internet Protocol, Version 6 (IPv6)
           Specification - IPv6.
           RFC 8329: Framework for Interface to Network Security
           Functions - I2NSF Flow Security Policy Structure.
           draft-ietf-tcpm-rfc793bis-25: Transmission Control
           Protocol (TCP) Specification";

        leaf-list ethernet-capability {
          type identityref {
            base ethernet;
          }
          description
            "Media Access Control (MAC) capabilities";
          reference
            "IEEE 802.3: IEEE Standard for Ethernet";
        }

        leaf-list ipv4-capability {
          type identityref {
            base ipv4;
          }
          description
            "IPv4 packet capabilities";
          reference
            "RFC 791: Internet Protocol";
        }

        leaf-list ipv6-capability {
          type identityref {
            base ipv6;
          }
          description
            "IPv6 packet capabilities";
          reference
            "RFC 8200: Internet Protocol, Version 6 (IPv6)
             Specification - IPv6";
        }

        leaf-list icmpv4-capability {
          type identityref {
            base icmpv4;
          }
          description
            "ICMPv4 packet capabilities";
          reference
            "RFC 792: Internet Control Message Protocol - ICMP";
        }

        leaf-list icmpv6-capability {
          type identityref {
            base icmpv6;
          }
          description
            "ICMPv6 packet capabilities";
          reference
            "RFC 4443: Internet Control Message Protocol (ICMPv6)
             for the Internet Protocol Version 6 (IPv6) Specification
             - ICMPv6";
        }

        leaf-list tcp-capability {
          type identityref {
            base tcp;
          }
          description
            "TCP packet capabilities";
          reference
            "draft-ietf-tcpm-rfc793bis-25: Transmission Control
             Protocol (TCP) Specification";
        }

        leaf-list udp-capability {
          type identityref {
            base udp;
          }
          description
            "UDP packet capabilities";
          reference
            "RFC 768: User Datagram Protocol - UDP";
        }

        leaf-list sctp-capability {
          type identityref {
            base sctp;
          }
          description
            "SCTP packet capabilities";
          reference
            "draft-ietf-tsvwg-rfc4960-bis-18: Stream Control
             Transmission Protocol - SCTP";
        }

        leaf-list dccp-capability {
          type identityref {
            base dccp;
          }
          description
            "DCCP packet capabilities";
          reference
            "RFC 4340: Datagram Congestion Control Protocol - DCCP";
        }
      }

      container advanced-nsf-capabilities {
        description
          "Advanced Network Security Function (NSF) capabilities,
           such as Anti-DDoS, IPS, and VoIP/VoCN.
           This container contains the leaf-lists of advanced
           NSF capabilities";

        leaf-list anti-ddos-capability {
          type identityref {
            base anti-ddos;
          }
          description
            "Anti-DDoS Attack capabilities";
        }

        leaf-list ips-capability {
          type identityref {
            base ips;
          }
          description
            "IPS capabilities";
        }

        leaf-list anti-virus-capability {
          type identityref {
            base anti-virus;
          }
          description
            "Antivirus capabilities";
        }

        leaf-list url-filtering-capability {
          type identityref {
            base url-filtering;
          }
          description
            "URL Filtering capabilities";
        }

        leaf-list voip-vocn-filtering-capability {
          type identityref {
            base voip-vocn-filtering;
         }
          description
            "VoIP/VoCN capabilities";
        }
      }

      container context-capabilities {
        description
          "Security context capabilities";

        leaf-list time-capabilities {
          type identityref {
            base time;
          }
          description
            "The capabilities for activating the policy within a
             specific time.";
        }

        leaf-list application-filter-capabilities{
          type identityref {
            base application-protocol;
          }
          description
            "Context capabilities based on the application protocol";
        }

        leaf-list device-type-capabilities {
          type identityref {
            base device-type;
          }
          description
            "Context capabilities based on the device attribute that
             can identify a device type
             (i.e., router, switch, pc, ios, or android).";
        }

        leaf-list user-condition-capabilities {
          type identityref {
            base user-condition;
          }
          description
            "Context capabilities based on user condition, such as
             user-id and user-name. The users can be collected into a
             user group (i.e., a group of users) and identified with
             group-id or group-name. An NSF is aware of the IP
             address of the user provided by a unified user
             management system via network. Based on name-address
             association, an NSF is able to enforce the security
             functions over the given user (or user group)";
        }

        leaf-list geographic-capabilities {
          type identityref {
            base geographic-location;
          }
          description
            "Context condition capabilities based on the geographical
             location of the source or destination";
        }
      }
    }

    container action-capabilities {
      description
        "Action capabilities.
         If a network security function has the action capabilities,
         the network security function supports the attendant
         actions for policy rules.";

      leaf-list ingress-action-capability {
        type identityref {
          base ingress-action;
        }
        description
          "Ingress-action capabilities";
      }

      leaf-list egress-action-capability {
        type identityref {
          base egress-action;
        }
        description
          "Egress-action capabilities";
      }

      leaf-list log-action-capability {
        type identityref {
          base log-action;
        }
        description
          "Log-action capabilities";
      }
    }

    leaf-list resolution-strategy-capabilities {
      type identityref {
        base resolution-strategy;
      }
      description
        "Resolution strategy capabilities.
         The resolution strategies can be used to specify how
         to resolve conflicts that occur between the actions
         of the similar or different policy rules that are matched
         for the same packet and by particular NSF; note that a
         badly written policy rule may cause a conflict of actions
         with another similar policy rule.";
    }

    leaf-list default-action-capabilities {
      type identityref {
        base default-action;
      }
      description
        "Default action capabilities.
         A default action is used to execute I2NSF policy rules
         when no rule matches a packet. The default action is
         defined as pass, drop, reject, rate-limit, or mirror.";
    }
  }

  /*
   * Data nodes
   */

  list nsf {
    key "nsf-name";
    description
      "The list of Network Security Functions (NSFs)";
    leaf nsf-name {
      type string;
      mandatory true;
      description
        "The name of Network Security Function (NSF)";
    }
    uses nsf-capabilities;
  }
}
