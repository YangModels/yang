module ietf-self-describing-capabilities {
  yang-version 1.1;
  namespace urn:ietf:params:xml:ns:yang:ietf-self-description-capabilities;
  prefix sdc;
  import ietf-system-capabilities  { prefix sysc ; }
  import ietf-module-tags  { prefix tags; }
  organization
    "IETF NETMOD (Network Modeling) Working Group";
  contact
    "WG Web:   <https://tools.ietf.org/wg/netconf/>
     WG List:  <mailto:netconf@ietf.org>

     Editor:   Qin Wu
               <mailto:bill.wu@huawei.com>
               Qiufang Ma
               <mailto:maqiufang1@huawei.com>
               Peng Liu
               <liupengyjy@chinamobile.com>
               Hui Cai
               <caihui@chinamobile.com>";
  description
    "This module defines an extension to System Capabilities model
     and provides additional self explaination data node tag attributes
     associated with node selector for queries filtering.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";
    revision 2020-07-08 {
    description
      "Initial revision";
    reference
      "RFC XXXX";
  }
    augment "/sysc:system-capabilities/sysc:datastore-capabilities" +
         "/sysc:per-node-capabilities" +
          "/sysc:node-selection/sysc:node-selector" {
     description "Allows per-node capabilities have additional self-explanation attributes";
     container self-describing-attributes {
      description "self describing attributes for specific data node.";
         leaf-list opm-tag {
           type tags:tag;
           description
            "Object, Property and Metric(OPM) Tags associated with
             specific data object within YANG module.
            See the IANA 'YANG Data Node Tag Prefixes' registry
            for reserved prefixes and the IANA
            'IETF YANG Data Node Tags' registry for IETF tags.";
         }
         leaf metric-group {
           type tags:tag;
           description
           "The metric-group can be used to provide correlation between
           different performance metric information associated with YANG
           data node.";
         }
         leaf multi-source-tag {
          type tags:tag;
          description
           "The multiple source tag can be used to aggregate peformance
            metric from different sources.";
         }
     }
   }
}
