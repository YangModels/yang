module ietf-rpki-rtr {
  yang-version "1.1";
  namespace "urn:ietf:params:xml:ns:yang:ietf-rpki-rtr";
  prefix "rpki-rtr";
  import ietf-yang-types {
    prefix "yang";
    reference
      "RFC 6991: Common YANG Data Types.";
  }
  import ietf-inet-types {
    prefix "inet";
    reference
      "RFC 6991: Common YANG Data Types";
  }
  import ietf-routing {
    prefix rt;
    reference
      "RFC 8349: A YANG Data Model for Routing Management
       (NMDA Version).";
  }
  import iana-crypt-hash {
    prefix "ianach";
    reference
      "RFC 7317: A YANG Data Model for System Management";
  }
  import ietf-ssh-client {
    prefix "ssh";
    reference
      "RFC XXXX: YANG Groupings for SSH Clients and SSH Servers";
  }
  import ietf-interfaces {
    prefix "if";
       reference
         "RFC 8343, A YANG Data Model for Interface Management.";
  }
  import ietf-key-chain {
    prefix key-chain;
    reference
      "RFC 8177: YANG Key Chain.";
  }
  organization
    "IETF SIDROPS Working Group";
  contact
    "TBD";
  description
    "This module describes a YANG model for the Resource Public
     Key Infrastructure (RPKI) to Router Protocol configuration.
     This YANG model conforms to the Network Management
     Datastore Architecture (NMDA) as described in RFC 8342.
     Copyright (c) 2022 IETF Trust and the persons identified as
     authors of the code.  All rights reserved.
     Redistribution and use in source and binary forms, with or
     without modification, is permitted pursuant to, and subject to
     the license terms contained in, the Revised BSD License set
     forth in Section 4.c of the IETF Trust's Legal Provisions
     Relating to IETF Documents
     (https://trustee.ietf.org/license-info).
     This version of this YANG module is part of RFC XXXX;
     see the RFC itself for full legal notices.
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  reference "RFC 8210";
  revision 2022-10-18 {
    description
      "Initial Version";
    reference
      "RFC 8210, YANG Data Model for RPKI to Router Protocol";
  }
  typedef ipv4-pfx-len {
    type uint8 {
      range "0 .. 32";
    }
    description
      "IPv4 Prefix Length.";
  }
  typedef ipv6-pfx-len {
    type uint8 {
      range "0 .. 128";
    }
    description
      "IPv6 Prefix Length.";
  }
  typedef subject-key-id {
    type binary {
      length 20;
    }
    description
      "Subject Key Identifier.";
  }
  identity rpki-rtr {
    base rt:routing-protocol;
    description
      "RPKI to Router protocol.";
  }
  grouping records-limit {
    description
      "Limit of records that can be received from the RPKI
       cache server.";
    leaf max-number {
      type uint64;
      description
        "Configures the maximum number of records that can be
         received from the RPKI cache server.";
    }
    leaf threshold-percentage {
      type uint8 {
        range "0..100";
      }
      units "percent";
      description
        "Configures the threshold percentage for record maximum
         number.";
    }
    leaf over-threshold-action {
      type enumeration {
        enum alert-only {
          description
            "Generates alert messages.";
        }
        enum discard {
          description
            "Discards excess records.";
        }
        enum reconnect {
          description
            "Diconncets with the RPKI cache server,
             and tries to reconnect after reconnection
             timer expires.";
        }
        enum idle-forever {
          description
            "Diconncets with the RPKI cache server
             forever.";
        }
      }
      description
        "The action to taken when record number exceeds
         threshold.";
    }
    leaf reconnect-interval {
      type uint32 {
        range "1..30000";
      }
      units "minutes";
      description
        "Time interval for the reconnection timer.";
    }
  }
  augment "/rt:routing/rt:control-plane-protocols/"
        + "rt:control-plane-protocol" {
    when "derived-from-or-self(rt:type, 'rpki-rtr')" {
      description
        "This augmentation is valid for a routing protocol
         instance of RPKI to Router.";
    }
    description
      "RPKI to Router protocol augmentation of ietf-routing module
       control-plane-protocol.";
    container rpki-rtr {
      description
        "Configuration parameters for the RPKI to Router Protocol.";
      container sessions {
        description
          "Parameters of RPKI sessions to cache servers.";
        list session {
          key "server-address";
          description
            "Each entry contains parameters for a RPKI session
             identified by the 'server-address' key.";
          leaf server-address {
            type inet:ip-address;
            mandatory true;
            description
              "The IP address of the RPKI cache server resembling
               a session";
          }
          leaf server-port {
            type inet:port-number;
            description
              "The remote port for the connection
               to the RPKI cache server";
          }
          leaf local-address {
            type union {
              type inet:ip-address;
              type if:interface-ref;
            }
            description
              "The local IP (either IPv4 or IPv6) address to use for
               the connection to the RPKI cache server. This may be
               expressed as either an IP address or reference to the
               name of an interface.";
          }
          leaf local-port {
            type inet:port-number;
            description
              "The local port for the connection
               to the RPKI cache server";
          }
          leaf enabled {
            type boolean;
            default "true";
            description
              "Whether the RPKI cache server is enabled.";
          }
          leaf preference {
            type uint32;
            description
              "The router's preference to connect to that cache.
               The lower the value, the more preferred.";
          }
          leaf description {
            type string;
            description
              "Textual description of the RPKI cache server";
          }
          leaf session-state {
            type enumeration {
              enum idle {
                description
                  "The session is down.";
              }
              enum connect {
                description
                  "The session is waiting for the underlying
                   transport session to be established.";
              }
              enum establish {
                description
                  "The session is up.";
              }
              enum ex-incr {
                description
                  "Incremental update of records in progress.";
              }
              enum ex-full {
                description
                  "Full update of records in progress.";
              }
            }
            config false;
            description
              "The session state.";
          }
          leaf enable-authentication {
            type boolean;
            default "false";
            description
              "Whether the session is secured.";
          }
          container authentication {
            when "../enable-authentication = 'true'";
            description
              "Container for describing how a particular session
               is to be secured.";
            choice option {
              description
                "Choice for session secruring methods.";
              case md5 {
                leaf md5-password {
                  type ianach:crypt-hash;
                  description
                    "The password for md5 authentication.";
                }
                description
                  "Uses TCP-MD5 to secure the session.";
              }
              case ssh {
                 uses ssh:ssh-client-grouping {
                  reference
                    "RFC XXXX: YANG Groupings for SSH Clients and
                     SSH Servers";
                }
                description
                  "Uses SSH to secure the session.";
              }
              case tcp-ao-keychain {
                leaf keychain-name {
                  type key-chain:key-chain-ref;
                  description
                    "Name of key chain.";
                  reference
                    "RFC 8177: YANG Key Chain.";
                }
                description
                  "Uses key-chain to secure the session.";
              }
            }
          }
          container vrp-limit {
            description
              "Limit of Validated ROA Payload records that can be
               received from the RPKI cache server.";
            uses records-limit;
          }
          container aspa-limit {
            description
              "Limit of ASPA records that can be received from the
               RPKI cache server.";
            uses records-limit;
          }
          container statistics {
            config false;
            description
              "Statistics of the RPKI cache server.";
            leaf total-vrp-records {
              type yang:zero-based-counter64;
              description
                "The total number of Validated ROA Payloads
                 received from the RPKI cache server.";
            }
            leaf ipv4-vrp-records {
              type yang:zero-based-counter64;
              description
                "The number of Validated ROA Payloads for IPv4
                 prefixes received from the RPKI cache server.";
            }
            leaf ipv6-vrp-records {
              type yang:zero-based-counter64;
              description
                "The number of Validated ROA Payloads for IPv6
                 prefixes received from the RPKI cache server.";
            }
            leaf router-key-records {
              type yang:zero-based-counter64;
              description
                "The number of router keys received from the RPKI
                 cache server.";
            }
            leaf aspa-records {
              type yang:zero-based-counter64;
              description
                "The number of ASPAs received from the RPKI
                 cache server.";
            }
          }
          container connection-data {
            config false;
            description
              "State information relating to the connection
               with the RPKI cache server.";
            leaf flaps {
              type uint32;
              description
                "Count for number of flaps observed on the
                 session.";
            }
            leaf last-session-up-down {
              type yang:timestamp;
              description
                "This timestamp indicates the time that the
                 RPKI-RTR session last transitioned in or out
                 of the UP state. The value is the timestamp in
                 microseconds relative to the Unix Epoch (Jan 1,
                 1970 00:00:00 UTC). The RPKI-RTR session uptime
                 can be computed by clients as the difference
                 between this value and the current time
                 in UTC (assuming the session is in the UP
                 state, per the session-state leaf).";
              reference
                "RFC 6810: The Resource Public Key Infrastructure.";
            }
            leaf last-update-sync-timestamp {
              type yang:timestamp;
              description
                "Time of last serial sync with cache server.";
            }
            leaf last-full-sync-timestamp {
              type yang:timestamp;
              description
                "Time of last reset sync with cache server.";
            }
            leaf last-serial-query-timestamp {
              type yang:timestamp;
              description
                "Time of last serial query sent to cache server.";
            }
            leaf last-reset-query-timestamp {
              type yang:timestamp;
              description
                "Time of last reset query sent to cache server.";
            }
            leaf last-eod-received {
              type yang:timestamp;
              description
                "Time in microseconds at which last EOD was
                 received.";
            }
            leaf last-config-change-timestamp {
              type yang:timestamp;
              description
                "Time of last host, port, VRF or local interface
                 change.";
            }
            leaf last-error-timestamp {
              type yang:timestamp;
              description
                "Time of sending/receiving protocol error to/from
                 cache server.";
            }
            leaf last-connection-error-timestamp {
              type yang:timestamp;
              description
                "Time of last connection error to cache server.";
            }
            leaf last-connection-timestamp {
              type yang:timestamp;
              description
                "Time of last connection to cache server.";
            }
            leaf error-reason {
              type string;
              description
                "Reason for error in connection.";
            }
          }
          container protocol-data {
            config false;
            description
              "State parameters related to the RPKI to router
               protocol";
            leaf protocol-version {
              type uint32;
              description
                "The version number of the RPKI to Router
                Protocol.";
            }
            leaf refresh-time {
              type yang:timestamp;
              description
                "Configures the time a router waits in between
                 sending periodic serial queries to the RPKI
                 cache server.";
            }
            leaf response-time {
              type yang:timestamp;
              description
                "Configures the time a router waits for a response
                 after sending a serial or reset query to the RPKI
                 cache server.";
            }
            leaf purge-time {
              type yang:timestamp;
              description
                "Configures the time a router waits to keep data
                 from the RPKI cache server after the session
                 drops.";
            }
            leaf hold-time {
              type yang:timestamp;
              description
                "Hold-time for this session.";
            }
            leaf record-lifetime {
              type yang:timestamp;
              description
                "Record-lifetime this session.";
            }
            leaf retry-interval {
              type uint32;
              description
                "Number of seconds between poll error and cache
                 server poll";
            }
            leaf expire-interval {
              type uint32;
              description
                "Number of seconds to retain data synced from
                 cache server";
            }
            leaf session-id {
              type uint16;
              config false;
              description
                "When a cache server is started, it generates a
                 Session ID to identify the instance of the cache
                 and to bind it to the sequence of Serial Numbers
                 that cache instance will generate.";
              reference
                "RFC 6810, The Resource Public Key Infrastructure
                 (RPKI) to Router Protocol
                 RFC 8210, The Resource Public Key Infrastructure
                 (RPKI) to Router Protocol, Version 1";
            }
            leaf serial-full {
              type uint32;
              config false;
              description
                "A 32-bit strictly increasing unsigned integer which
                 wraps from 2^32-1 to 0. It denotes the logical
                 version of a cache. It resembles the latest full
                 query.";
              reference
                "RFC 6810, The Resource Public Key Infrastructure
                 (RPKI) to Router Protocol
                 RFC 8210, The Resource Public Key Infrastructure
                 (RPKI) to Router Protocol, Version 1";
            }
            leaf serial-incremental {
              type uint32;
              config false;
              description
                "A 32-bit strictly increasing unsigned integer which
                 wraps from 2^32-1 to 0. It denotes the logical
                 version of a cache. It resembles the latest
                 incremental query.";
              reference
                "RFC 6810, The Resource Public Key Infrastructure
                 (RPKI) to Router Protocol
                 RFC 8210, The Resource Public Key Infrastructure
                 (RPKI) to Router Protocol, Version 1";
            }
            leaf in-total-messages {
              type yang:zero-based-counter64;
              description
                "The total number of messages received from the
                 RPKI cache server.";
            }
            leaf out-total-messages {
              type yang:zero-based-counter64;
              description
                "The total number of messages transmitted to the
                 RPKI cache server.";
            }
          }
          container pdu-counters {
            config false;
            description
              "Counters of PDUs that are received from cache";
            leaf serial-notify {
              type yang:zero-based-counter64;
              description
                "Serial notify PDU count";
            }
            leaf cache-response {
              type yang:zero-based-counter64;
              description
                "Cache response PDU count";
            }
            leaf ipv4-prefix {
              type yang:zero-based-counter64;
              description
                "IPv4 prefix PDU count";
            }
            leaf ipv6-prefix {
              type yang:zero-based-counter64;
              description
                "Ipv6 prefix PDU count";
            }
            leaf end-of-data {
              type yang:zero-based-counter64;
              description
                "End of data PDU count";
            }
            leaf cache-reset {
              type yang:zero-based-counter64;
              description
                "Cache reset PDU count";
            }
            leaf reset-query {
              type yang:zero-based-counter64;
              description
                "Reset query PDU count";
            }
            leaf serial-query {
              type yang:zero-based-counter64;
              description
                "Serial query PDU count";
            }
          }
          container error-pdu-counters {
            config false;
            description
              "Counters of error PDUs that originate from router
       or cache server";
            leaf corrupt-data {
              type yang:zero-based-counter64;
              description
                "Corrupt data PDU count";
            }
            leaf internal-error {
              type yang:zero-based-counter64;
              description
                "Internal error PDU count";
            }
            leaf unsupported-protocol-version {
              type yang:zero-based-counter64;
              description
                "Unsupported protocol version PDU count";
            }
            leaf unsupported-pdu-type {
              type yang:zero-based-counter64;
              description
                "Unsupported PDU type count";
            }
            leaf unexpected-protocol-version {
              type yang:zero-based-counter64;
              description
                "Unexpected protocol version PDU count";
            }
            leaf no-data-available {
              type yang:zero-based-counter64;
              description
                "No data available PDU count";
            }
            leaf invalid-request {
              type yang:zero-based-counter64;
              description
                "Invalid request PDU count";
            }
            leaf withdrawal-unknown-record {
              type yang:zero-based-counter64;
              description
                "Withdrawal of unknown record PDU count";
            }
            leaf duplicate-announcement-received {
              type yang:zero-based-counter64;
              description
                "Duplicate announcement received PDU count";
            }
          }
        }
      }
    }
  }
}
