module openconfig-feature-bundle {

  // namespace
  namespace "http://openconfig.net/yang/feature-bundle";

  prefix "oc-featbundle";

  import openconfig-module-catalog { prefix oc-cat; }
  import openconfig-extensions { prefix oc-ext; }

  // meta
  organization "OpenConfig working group";

  contact
    "OpenConfig working group
    netopenconfig@googlegroups.com";

  description
    "This module can be used to build network features using
        published YANG Models.";

  oc-ext:openconfig-version "0.2.0";

  revision "2016-02-25" {
    description
      "OpenConfig revision to specify
      feature bundles";
    reference "0.2.0";
  }

  revision "2016-02-15" {
    description
      "Initial OpenConfig public release";
    reference "0.1.0";
  }

  revision "2015-10-18" {
    description
      "Initial revision";
    reference "TBD";
  }

  grouping feature-bundle-information {

        description
          "Template defining the bundle";

    leaf name {
        type string;
        description "Published name of bundle, for example:
              l3vpn, l2vpn, internet-access";
    }

    leaf version {
        type string;
        description "bundle version number";
    }

    leaf description {
        type string;
        description "User defined information about bundle";
    }

    leaf category {
          type string;
          description
       "Categorization of bundle such as:
        network, service, oam, experimental, other";
    }

    leaf subcategory {
          type string;
          description
             "Sub-Categorization of bundle such as:
          protocol, operational, other";
        }
  } //bundle-template

  grouping feature-bundle-ingredients {

        description "Module ingredients used in bundle";

    container modules {

          description
            "Modules that comprise the bundle";

      list module {

        key "module-type";

        description
          "List of modules from yang-module-catalog comprising
           the bundle";

            leaf module-type {
                    type string;
          description
            "A user-define type of the module";
        }

        leaf catalog-reference {
          type leafref {
            path "/oc-cat:organizations"
              + "/oc-cat:organization"
              + "/oc-cat:modules"
              + "/oc-cat:module"
              + "/oc-cat:name";
                }
              description
            "Link to the module metadata in the model catalog";
        }

        leaf application-sequence {
           type uint8;
           description
                 "Sequence number indicating order of application of
              module";
        }
      } //module-info
    } //bundle-modules
  } //bundle-ingredients

  grouping feature-bundle-top {
    description
      "Top-level grouping for OpenConfig feature bundles";

    container feature-bundles {
      description
        "List of feature bundles";

      list feature-bundle {
        key "name";

        description
          "List of feature bundles - sets of modules that combine to
          create a set of functionality.";

        uses feature-bundle-information;
        uses feature-bundle-ingredients;
      }
    }
  } //bundle

  uses feature-bundle-top;

}
