module ietf-netconf-with-system {
   namespace "urn:ietf:params:xml:ns:yang:ietf-netconf-with-system";
   prefix ncws;
   import ietf-netconf { prefix nc; }

   organization
    "IETF NETCONF (Network Configuration Protocol) Working Group";

   contact
    "WG Web:   <http://tools.ietf.org/wg/netconf/>
     WG List:  <mailto:netconf@ietf.org>
     WG Chair:
     Editor:
                                                ";
   description
    "This module defines an extension to the NETCONF protocol
     that allows the NETCONF client to control how system configuration
     data are handled by the server in particular NETCONF operations.

     Copyright (c) 2010 IETF Trust and the persons identified as
     the document authors.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
   // RFC Ed.: replace XXXX with actual RFC number and remove this note

   revision 2019-12-31 {
     description
       "Initial version.";
     reference
      "RFC XXXX: With-system capability for NETCONF";
   }

   typedef with-system-mode {
      description
        "Possible modes to report system configuration data.";
      reference
         "RFC XXXX; section 3.";
         // RFC Ed.: replace XXXX with actual
         // RFC number and remove this note

      type enumeration {
         enum report-all {
             description
               "All system configuration data is reported.";
             reference
               "RFC XXXX; section 3.1";
               // RFC Ed.: replace XXXX with actual
               // RFC number and remove this note

         }
         enum report-all-tagged {
             description
               "All system configuration data is reported.
                Any nodes considered to be system configuration
                data will contain a 'origin' XML attribute,
                set to 'system'.";
             reference
               "RFC XXXX; section 3.4";
               // RFC Ed.: replace XXXX with actual
               // RFC number and remove this note
         }
         enum trim {
             description
               "Values are not reported if they contain the system
               configuration data.";
             reference
               "RFC XXXX; section 3.2";
               // RFC Ed.: replace XXXX with actual
               // RFC number and remove this note

         }
         enum explicit {
             description
               "Report values that contain the definition of
                explicitly set data.";
             reference
               "RFC XXXX; section 3.3";
               // RFC Ed.: replace XXXX with actual
               // RFC number and remove this note
         }
     }
   }

   grouping with-system-parameters {
     description
       "Contains the <with-system> parameter for control
        of system configuration data in NETCONF retrieval
        operations.";

     leaf with-system {
       description
         "The explicit system configuration data processing
          mode requested.";
       reference
         "RFC XXXX; section 4.6.1";
         // RFC Ed.: replace XXXX with actual
         // RFC number and remove this note

       type with-system-mode;
     }
   }

   // extending the get-config operation
   augment /nc:get-config/nc:input {
       description
         "Adds the <with-system> parameter to the
          input of the NETCONF <get-config> operation.";
       reference
         "RFC XXXX; section 4.6.1";
         // RFC Ed.: replace XXXX with actual
         // RFC number and remove this note

       uses with-system-parameters;
   }

   // extending the get operation
   augment /nc:get/nc:input {
       description
         "Adds the <with-system> parameter to
          the input of the NETCONF <get> operation.";
       reference
         "RFC XXXX; section 4.6.1";
         // RFC Ed.: replace XXXX with actual
         // RFC number and remove this note

       uses with-system-parameters;
   }
}
