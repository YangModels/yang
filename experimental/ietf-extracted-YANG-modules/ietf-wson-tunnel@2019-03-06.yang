module ietf-wson-tunnel {
  yang-version 1.1;

  namespace "urn:ietf:params:xml:ns:yang:ietf-wson-tunnel";
  prefix "wson-tunnel";

  import ietf-te { prefix "te"; }
  import ietf-layer0-types{ prefix "layer0-types"; }
  import ietf-te-path-computation { prefix "tepc"; }
  import ietf-otn-types { prefix "otn-types";}

  organization
    "IETF CCAMP Working Group";

  contact
    "WG Web:   <http://tools.ietf.org/wg/ccamp/>
     WG List:  <mailto:ccamp@ietf.org>

     WG Chair: Daniele Ceccarelli
               <mailto:daniele.ceccarelli@ericsson.com>

     WG Chair: Fatai Zhang
               <mailto:zhangfatai@huawei.com>

     Editor: Young Lee <leeyoung@huawei.com>
     Editor: Aihua Guo <aihuaguo@huawei.com>
     Editor: Dhruv Dhody <dhruv.ietf@gmail.com>
     Editor: Ricard Vilalta <ricard.vilalta@cttc.es>";
     description
       "This module defines a model for WSON Tunnel Services.";

  revision "2019-03-06" {
    description
      "Updates to version 3";
    reference "version 3";
  }

  /* Groupings. */
  grouping wson-tunnel-attributes {
    description "Parameters for WSON tunnel.";

    leaf src-client-signal {
      type identityref {
        base otn-types:client-signal;
      }
      description
        "Client signal at the source endpoint of
         the tunnel.";
    }

    leaf dst-client-signal {
      type identityref {
        base otn-types:client-signal;
      }
      description
        "Client signal at the destination endpoint of
         the tunnel.";
    }

    leaf fec-type {
      type identityref {
        base layer0-types:fec-type;
      }
      description
        "FEC type.";
    }

    leaf termination-type {
      type identityref {
        base layer0-types:term-type;
      }
      description
        "Termination type.";
    }

    leaf bit-stuffing {
      type boolean;
      description
        "Bit stuffing enabled/disabled.";
    }
  }

  grouping wson-path-constraints {
    description
      "Global named path constraints configuration
       grouping for WSON tunnel";

    leaf wavelength-assignment {
      type identityref {
        base layer0-types:wavelength-assignment;
      }
      description "Wavelength Allocation Method";
    }
  }

 /*
  * Data nodes
  */

  augment "/te:te/te:tunnels/te:tunnel" {
    description
      "Augment with additional parameters required for WSON tunnel.";
    uses wson-tunnel-attributes;
  }
  /*
   * Augment TE bandwidth
   */

  /* Augment bandwidth of named-path-constraints */
  augment "/te:te/te:globals/te:named-path-constraints/"
        + "te:named-path-constraint/"
        + "te:te-bandwidth/te:technology" {
    description "WSON bandwidth.";
    case wson {
      uses layer0-types:wson-path-bandwidth;
    }
  }

  /* Augment bandwdith of tunnel */
  augment "/te:te/te:tunnels/te:tunnel/"
        + "te:te-bandwidth/te:technology" {
    description "WSON bandwidth.";
    case wson {
      uses layer0-types:wson-path-bandwidth;
    }
  }

  /* Augment bandwidth of primary path */
  augment "/te:te/te:tunnels/te:tunnel/"
        + "te:p2p-primary-paths/te:p2p-primary-path/"
        + "te:te-bandwidth/te:technology" {
    description "WSON bandwidth.";
    case wson {
      uses layer0-types:wson-path-bandwidth;
    }
  }

  /* Augment bandwidth of reverse primary path */
  augment "/te:te/te:tunnels/te:tunnel/"
        + "te:p2p-primary-paths/te:p2p-primary-path/"
        + "te:p2p-primary-reverse-path/"
        + "te:te-bandwidth/te:technology" {
    description "WSON bandwidth.";
    case wson {
      uses layer0-types:wson-path-bandwidth;
    }
  }

  /* Augment bandwidht of secondary path */
  augment "/te:te/te:tunnels/te:tunnel/"
        + "te:p2p-secondary-paths/te:p2p-secondary-path/"
        + "te:te-bandwidth/te:technology" {
    description "WSON bandwidth.";
    case wson {
      uses layer0-types:wson-path-bandwidth;
    }
  }

  /*
   * Augment TE label.
   */
  /* Augment label hop of route-object-exclude-always of named-path-
constraints */
  augment "/te:te/te:globals/te:named-path-constraints/"
        + "te:named-path-constraint/te:explicit-route-objects-always/"
        + "te:route-object-exclude-always/te:type/te:label/"
        + "te:label-hop/te:te-label/te:technology" {
    description "WSON label.";
    case wson {
      uses layer0-types:wson-path-label;
    }
  }

  /* Augment label hop of route-object-include-exclude of named-path-
constraints */
  augment "/te:te/te:globals/te:named-path-constraints/"
        + "te:named-path-constraint/te:explicit-route-objects-always/"
        + "te:route-object-include-exclude/te:type/te:label/"
        + "te:label-hop/te:te-label/te:technology" {
    description "WSON label.";
    case wson {
      uses layer0-types:wson-path-label;
    }
  }

  /* Augment label restrictions for the path-in-segment of
     named-path-constraints */
  augment "/te:te/te:globals/te:named-path-constraints/"
        + "te:named-path-constraint/te:path-in-segment/"
        + "te:label-restrictions/te:label-restriction" {
    description "WSON label.";
    uses layer0-types:layer0-label-restriction;
  }

  /* Augment label restrictions start for the path-in-segment
     of named-path-constraints */
  augment "/te:te/te:globals/te:named-path-constraints/"
        + "te:named-path-constraint/te:path-in-segment/"
        + "te:label-restrictions/"
        + "te:label-restriction/te:label-start/"
        + "te:te-label/te:technology" {
    description "WSON label.";
    case wson {
      uses layer0-types:wson-link-label;
    }
  }

  /* Augment label restrictions end for the path-in-segment of
     named-path-constraints */
  augment "/te:te/te:globals/te:named-path-constraints/"
        + "te:named-path-constraint/te:path-in-segment/"
        + "te:label-restrictions/"
        + "te:label-restriction/te:label-end/"
        + "te:te-label/te:technology" {
    description "WSON label.";
    case wson {
      uses layer0-types:wson-link-label;
    }
  }

  /* Augment label restrictions for the path-out-segment of
     named-path-constraints */
  augment "/te:te/te:globals/te:named-path-constraints/"
        + "te:named-path-constraint/te:path-out-segment/"
        + "te:label-restrictions/"
        + "te:label-restriction" {
    description "WSON label.";
    uses layer0-types:layer0-label-restriction;
  }
  /* Augment label restrictions start for the path-out-segment
     of named-path-constraints */
  augment "/te:te/te:globals/te:named-path-constraints/"
        + "te:named-path-constraint/te:path-out-segment/"
        + "te:label-restrictions/"
        + "te:label-restriction/te:label-start/"
        + "te:te-label/te:technology" {
    description "WSON label.";
    case wson {
      uses layer0-types:wson-link-label;
    }
  }

  /* Augment label restrictions end for the path-out-segment of
     named-path-constraints */
  augment "/te:te/te:globals/te:named-path-constraints/"
        + "te:named-path-constraint/te:path-out-segment/"
        + "te:label-restrictions/"
        + "te:label-restriction/te:label-end/"
        + "te:te-label/te:technology" {
    description "WSON label.";
    case wson {
      uses layer0-types:wson-link-label;
    }
  }

  /* Augment label hop of route-exclude of primary path */
  augment "/te:te/te:tunnels/te:tunnel/"
        + "te:p2p-primary-paths/te:p2p-primary-path/"
        + "te:optimizations/te:algorithm/te:metric/"
        + "te:optimization-metric/te:explicit-route-exclude-objects/"
        + "te:route-object-exclude-object/te:type/te:label/"
        + "te:label-hop/te:te-label/te:technology" {
    description "WSON label.";
    case wson {
      uses layer0-types:wson-path-label;
    }
  }

  /* Augment label hop of route-include of primary path */
  augment "/te:te/te:tunnels/te:tunnel/"
        + "te:p2p-primary-paths/te:p2p-primary-path/"
        + "te:optimizations/te:algorithm/te:metric/"
        + "te:optimization-metric/te:explicit-route-include-objects/"
        + "te:route-object-include-object/te:type/te:label/"
        + "te:label-hop/te:te-label/te:technology" {
    description "WSON label.";
    case wson {
      uses layer0-types:wson-path-label;
    }
  }

  /* Augment label hop of route-object-exclude-always of primary path */
  augment "/te:te/te:tunnels/te:tunnel/"
        + "te:p2p-primary-paths/te:p2p-primary-path/"
        + "te:explicit-route-objects-always/"
        + "te:route-object-exclude-always/te:type/te:label/"
        + "te:label-hop/te:te-label/te:technology" {
    description "WSON label.";
    case wson {
      uses layer0-types:wson-path-label;
    }
  }

  /* Augment label hop of route-object-include-exclude of primary path */
  augment "/te:te/te:tunnels/te:tunnel/"
        + "te:p2p-primary-paths/te:p2p-primary-path/"
        + "te:explicit-route-objects-always/"
        + "te:route-object-include-exclude/te:type/te:label/"
        + "te:label-hop/te:te-label/te:technology" {
    description "WSON label.";
    case wson {
      uses layer0-types:wson-path-label;
    }
  }

  /* Augment label restrictions for the path-in-segment of primary path */
  augment "/te:te/te:tunnels/te:tunnel/"
        + "te:p2p-primary-paths/te:p2p-primary-path/"
        + "te:path-in-segment/te:label-restrictions/"
        + "te:label-restriction" {
    description "WSON label.";
    uses layer0-types:layer0-label-restriction;
  }

  /* Augment label restrictions start for the path-in-segment of primary path
*/
  augment "/te:te/te:tunnels/te:tunnel/"
        + "te:p2p-primary-paths/te:p2p-primary-path/"
        + "te:path-in-segment/te:label-restrictions/"
        + "te:label-restriction/te:label-start/"
        + "te:te-label/te:technology" {
    description "WSON label.";
    case wson {
      uses layer0-types:wson-link-label;
    }
  }

  /* Augment label restrictions end for the path-in-segment of primary path */
  augment "/te:te/te:tunnels/te:tunnel/"
        + "te:p2p-primary-paths/te:p2p-primary-path/"
        + "te:path-in-segment/te:label-restrictions/"
        + "te:label-restriction/te:label-end/"
        + "te:te-label/te:technology" {
    description "WSON label.";
    case wson {
      uses layer0-types:wson-link-label;
    }
  }

  /* Augment label restrictions for the path-out-segment of primary path */
  augment "/te:te/te:tunnels/te:tunnel/"
        + "te:p2p-primary-paths/te:p2p-primary-path/"
        + "te:path-out-segment/te:label-restrictions/"
        + "te:label-restriction" {
    description "WSON label.";
    uses layer0-types:layer0-label-restriction;
  }

  /* Augment label restrictions start for the path-out-segment of primary path
*/
  augment "/te:te/te:tunnels/te:tunnel/"
        + "te:p2p-primary-paths/te:p2p-primary-path/"
        + "te:path-out-segment/te:label-restrictions/"
        + "te:label-restriction/te:label-start/"
        + "te:te-label/te:technology" {
    description "WSON label.";
    case wson {
      uses layer0-types:wson-link-label;
    }
  }

  /* Augment label restrictions end for the path-out-segment of primary path
*/
  augment "/te:te/te:tunnels/te:tunnel/"
        + "te:p2p-primary-paths/te:p2p-primary-path/"
        + "te:path-out-segment/te:label-restrictions/"
        + "te:label-restriction/te:label-end/"
        + "te:te-label/te:technology" {
    description "WSON label.";
    case wson {
      uses layer0-types:wson-link-label;
    }
  }

  /* Augment label hop of path-route of primary path */
  augment "/te:te/te:tunnels/te:tunnel/"
        + "te:p2p-primary-paths/te:p2p-primary-path/"
        + "te:computed-paths-properties/"
          + "te:computed-path-properties/te:path-properties/"
        + "te:path-route-objects/te:path-computed-route-object/"
        + "te:type/te:label/"
        + "te:label-hop/te:te-label/te:technology" {
    description "WSON label.";
    case wson {
      uses layer0-types:wson-path-label;
    }
  }

  /* Augment label hop of record-route of primary LSP */
  augment "/te:te/te:tunnels/te:tunnel/"
        + "te:p2p-primary-paths/te:p2p-primary-path/"
        + "te:lsps/te:lsp/te:lsp-record-route-information/"
        + "te:lsp-record-route-information/te:type/te:label/"
        + "te:label-hop/te:te-label/te:technology" {
    description "WSON label.";
    case wson {
      uses layer0-types:wson-path-label;
    }
  }

  /* Augment label hop of path-route of primary LSP */
  augment "/te:te/te:tunnels/te:tunnel/"
        + "te:p2p-primary-paths/te:p2p-primary-path/"
        + "te:lsps/te:lsp/te:path-properties/"
        + "te:path-route-objects/te:path-computed-route-object/"
        + "te:type/te:label/"
        + "te:label-hop/te:te-label/te:technology" {
    description "WSON label.";
    case wson {
      uses layer0-types:wson-path-label;
    }
  }

  /* Augment label hop of route-exclude of reverse primary path */
  augment "/te:te/te:tunnels/te:tunnel/"
        + "te:p2p-primary-paths/te:p2p-primary-path/"
        + "te:p2p-primary-reverse-path/"
        + "te:optimizations/te:algorithm/te:metric/"
        + "te:optimization-metric/te:explicit-route-exclude-objects/"
        + "te:route-object-exclude-object/te:type/te:label/"
        + "te:label-hop/te:te-label/te:technology" {
    description "WSON label.";
    case wson {
      uses layer0-types:wson-path-label;
    }
  }

  /* Augment label hop of route-include of reverse primary path */
  augment "/te:te/te:tunnels/te:tunnel/"
        + "te:p2p-primary-paths/te:p2p-primary-path/"
        + "te:p2p-primary-reverse-path/"
        + "te:optimizations/te:algorithm/te:metric/"
        + "te:optimization-metric/te:explicit-route-include-objects/"
        + "te:route-object-include-object/te:type/te:label/"
        + "te:label-hop/te:te-label/te:technology" {
    description "WSON label.";
    case wson {
      uses layer0-types:wson-path-label;
    }
  }

  /* Augment label hop of route-object-exclude-always of reverse primary path
*/
  augment "/te:te/te:tunnels/te:tunnel/"
        + "te:p2p-primary-paths/te:p2p-primary-path/"
        + "te:p2p-primary-reverse-path/"
        + "te:explicit-route-objects-always/"
        + "te:route-object-exclude-always/"
        + "te:type/te:label/"
        + "te:label-hop/te:te-label/te:technology" {
    description "WSON label.";
    case wson {
      uses layer0-types:wson-path-label;
    }
  }

  /* Augment label hop of route-object-include-exclude of reverse primary path
*/
  augment "/te:te/te:tunnels/te:tunnel/"
        + "te:p2p-primary-paths/te:p2p-primary-path/"
        + "te:p2p-primary-reverse-path/"
        + "te:explicit-route-objects-always/"
        + "te:route-object-include-exclude/"
        + "te:type/te:label/"
        + "te:label-hop/te:te-label/te:technology" {
    description "WSON label.";
    case wson {
      uses layer0-types:wson-path-label;
    }
  }

  /* Augment label restrictions for the path-in-segment of reverse primary
path */
  augment "/te:te/te:tunnels/te:tunnel/"
        + "te:p2p-primary-paths/te:p2p-primary-path/"
        + "te:p2p-primary-reverse-path/"
        + "te:path-in-segment/te:label-restrictions/"
        + "te:label-restriction" {
    description "WSON label.";
    uses layer0-types:layer0-label-restriction;
  }

  /* Augment label restrictions start for the path-in-segment of reverse
primary path */
  augment "/te:te/te:tunnels/te:tunnel/"
        + "te:p2p-primary-paths/te:p2p-primary-path/"
        + "te:p2p-primary-reverse-path/"
        + "te:path-in-segment/te:label-restrictions/"
        + "te:label-restriction/te:label-start/"
        + "te:te-label/te:technology" {
    description "WSON label.";
    case wson {
      uses layer0-types:wson-link-label;
    }
  }
  /* Augment label restrictions end for the path-in-segment of reverse primary
path */
  augment "/te:te/te:tunnels/te:tunnel/"
        + "te:p2p-primary-paths/te:p2p-primary-path/"
        + "te:p2p-primary-reverse-path/"
        + "te:path-in-segment/te:label-restrictions/"
        + "te:label-restriction/te:label-end/"
        + "te:te-label/te:technology" {
    description "WSON label.";
    case wson {
      uses layer0-types:wson-link-label;
    }
  }

  /* Augment label restrictions for the path-out-segment of reverse primary
path */
  augment "/te:te/te:tunnels/te:tunnel/"
        + "te:p2p-primary-paths/te:p2p-primary-path/"
        + "te:p2p-primary-reverse-path/"
        + "te:path-out-segment/te:label-restrictions/"
        + "te:label-restriction" {
    description "WSON label.";
    uses layer0-types:layer0-label-restriction;
  }
  /* Augment label restrictions start for the path-out-segment of reverse
primary path */
  augment "/te:te/te:tunnels/te:tunnel/"
        + "te:p2p-primary-paths/te:p2p-primary-path/"
        + "te:p2p-primary-reverse-path/"
        + "te:path-out-segment/te:label-restrictions/"
        + "te:label-restriction/te:label-start/"
        + "te:te-label/te:technology" {
    description "WSON label.";
    case wson {
      uses layer0-types:wson-link-label;
    }
  }

  /* Augment label restrictions end for the path-out-segment of reverse
primary path */
  augment "/te:te/te:tunnels/te:tunnel/"
        + "te:p2p-primary-paths/te:p2p-primary-path/"
        + "te:p2p-primary-reverse-path/"
        + "te:path-out-segment/te:label-restrictions/"
        + "te:label-restriction/te:label-end/"
        + "te:te-label/te:technology" {
    description "WSON label.";
    case wson {
      uses layer0-types:wson-link-label;
    }
  }

  /* Augment label hop of path-route of reverse primary path */
  augment "/te:te/te:tunnels/te:tunnel/"
        + "te:p2p-primary-paths/te:p2p-primary-path/"
        + "te:p2p-primary-reverse-path/"
        + "te:computed-paths-properties/"
          + "te:computed-path-properties/te:path-properties/"
        + "te:path-route-objects/te:path-computed-route-object/"
        + "te:type/te:label/"
        + "te:label-hop/te:te-label/te:technology" {
    description "WSON label.";
    case wson {
      uses layer0-types:wson-path-label;
    }
  }

  /* Augment label hop of record-route of reverse primary LSP */
  augment "/te:te/te:tunnels/te:tunnel/"
        + "te:p2p-primary-paths/te:p2p-primary-path/"
        + "te:p2p-primary-reverse-path/"
        + "te:lsps/te:lsp/te:lsp-record-route-information/"
        + "te:lsp-record-route-information/te:type/te:label/"
        + "te:label-hop/te:te-label/te:technology" {
    description "WSON label.";
    case wson {
      uses layer0-types:wson-path-label;
    }
  }

  /* Augment label hop of path-route of reverse primary LSP */
  augment "/te:te/te:tunnels/te:tunnel/"
        + "te:p2p-primary-paths/te:p2p-primary-path/"
        + "te:p2p-primary-reverse-path/"
        + "te:lsps/te:lsp/te:path-properties/"
        + "te:path-route-objects/te:path-computed-route-object/"
        + "te:type/te:label/"
        + "te:label-hop/te:te-label/te:technology" {
    description "WSON label.";
    case wson {
      uses layer0-types:wson-path-label;
    }
  }

  /* Augment label hop of route-exclude of secondary path */
  augment "/te:te/te:tunnels/te:tunnel/"
        + "te:p2p-secondary-paths/te:p2p-secondary-path/"
        + "te:optimizations/te:algorithm/te:metric/"
        + "te:optimization-metric/te:explicit-route-exclude-objects/"
        + "te:route-object-exclude-object/te:type/te:label/"
        + "te:label-hop/te:te-label/te:technology" {
    description "WSON label.";
    case wson {
      uses layer0-types:wson-path-label;
    }
  }

  /* Augment label hop of route-include of secondary path */
  augment "/te:te/te:tunnels/te:tunnel/"
        + "te:p2p-secondary-paths/te:p2p-secondary-path/"
        + "te:optimizations/te:algorithm/te:metric/"
        + "te:optimization-metric/te:explicit-route-include-objects/"
        + "te:route-object-include-object/te:type/te:label/"
        + "te:label-hop/te:te-label/te:technology" {
    description "WSON label.";
    case wson {
      uses layer0-types:wson-path-label;
    }
  }

  /* Augment label hop of route-object-exclude-always of secondary path */
  augment "/te:te/te:tunnels/te:tunnel/"
        + "te:p2p-secondary-paths/te:p2p-secondary-path/"
        + "te:explicit-route-objects-always/"
        + "te:route-object-exclude-always/te:type/te:label/"
        + "te:label-hop/te:te-label/te:technology" {
    description "WSON label.";
    case wson {
      uses layer0-types:wson-path-label;
    }
  }

  /* Augment label hop of route-object-include-exclude of secondary path */
  augment "/te:te/te:tunnels/te:tunnel/"
        + "te:p2p-secondary-paths/te:p2p-secondary-path/"
        + "te:explicit-route-objects-always/"
        + "te:route-object-include-exclude/te:type/te:label/"
        + "te:label-hop/te:te-label/te:technology" {
    description "WSON label.";
    case wson {
      uses layer0-types:wson-path-label;
    }
  }

  /* Augment label restrictions for the path-in-segment of secondary path */
  augment "/te:te/te:tunnels/te:tunnel/"
        + "te:p2p-secondary-paths/te:p2p-secondary-path/"
        + "te:path-in-segment/te:label-restrictions/"
        + "te:label-restriction" {
    description "WSON label.";
    uses layer0-types:layer0-label-restriction;
  }

  /* Augment label restrictions start for the path-in-segment of secondary
path */
  augment "/te:te/te:tunnels/te:tunnel/"
        + "te:p2p-secondary-paths/te:p2p-secondary-path/"
        + "te:path-in-segment/te:label-restrictions/"
        + "te:label-restriction/te:label-start/"
        + "te:te-label/te:technology" {
    description "WSON label.";
    case wson {
      uses layer0-types:wson-link-label;
    }
  }

  /* Augment label restrictions end for the path-in-segment of secondary path
*/
  augment "/te:te/te:tunnels/te:tunnel/"
        + "te:p2p-secondary-paths/te:p2p-secondary-path/"
        + "te:path-in-segment/te:label-restrictions/"
        + "te:label-restriction/te:label-end/"
        + "te:te-label/te:technology" {
    description "WSON label.";
    case wson {
      uses layer0-types:wson-link-label;
    }
  }

  /* Augment label restrictions for the path-out-segment of secondary path */
  augment "/te:te/te:tunnels/te:tunnel/"
        + "te:p2p-secondary-paths/te:p2p-secondary-path/"
        + "te:path-out-segment/te:label-restrictions/"
        + "te:label-restriction" {
    description "WSON label.";
    uses layer0-types:layer0-label-restriction;
  }

  /* Augment label restrictions start for the path-out-segment of secondary
path */
  augment "/te:te/te:tunnels/te:tunnel/"
        + "te:p2p-secondary-paths/te:p2p-secondary-path/"
        + "te:path-out-segment/te:label-restrictions/"
        + "te:label-restriction/te:label-start/"
        + "te:te-label/te:technology" {
    description "WSON label.";
    case wson {
      uses layer0-types:wson-link-label;
    }
  }

  /* Augment label restrictions end for the path-out-segment of secondary path
*/
  augment "/te:te/te:tunnels/te:tunnel/"
        + "te:p2p-secondary-paths/te:p2p-secondary-path/"
        + "te:path-out-segment/te:label-restrictions/"
        + "te:label-restriction/te:label-end/"
        + "te:te-label/te:technology" {
    description "WSON label.";
    case wson {
      uses layer0-types:wson-link-label;
    }
  }

  /* Augment label hop of path-route of secondary path */
  augment "/te:te/te:tunnels/te:tunnel/"
        + "te:p2p-secondary-paths/te:p2p-secondary-path/"
        + "te:computed-paths-properties/"
          + "te:computed-path-properties/te:path-properties/"
          + "te:path-route-objects/"
        + "te:path-computed-route-object/te:type/te:label/"
        + "te:label-hop/te:te-label/te:technology" {
    description "WSON label.";
    case wson {
      uses layer0-types:wson-path-label;
    }
  }

  /* Augment label hop of record-route of secondary LSP */
  augment "/te:te/te:tunnels/te:tunnel/"
        + "te:p2p-secondary-paths/te:p2p-secondary-path/"
        + "te:lsps/te:lsp/te:lsp-record-route-information/"
        + "te:lsp-record-route-information/te:type/te:label/"
        + "te:label-hop/te:te-label/te:technology" {
    description "WSON label.";
    case wson {
      uses layer0-types:wson-path-label;
    }
  }

  /* Augment label hop of path-route of secondary LSP */
  augment "/te:te/te:tunnels/te:tunnel/"
        + "te:p2p-secondary-paths/te:p2p-secondary-path/"
        + "te:lsps/te:lsp/te:path-properties/"
        + "te:path-route-objects/"
        + "te:path-computed-route-object/te:type/te:label/"
        + "te:label-hop/te:te-label/te:technology" {
    description "WSON label.";
    case wson {
      uses layer0-types:wson-path-label;
    }
  }

  /* Augment label hop of record-route of LSP */
  augment "/te:te/te:lsps-state/"
        + "te:lsp/te:lsp-record-route-information/"
        + "te:lsp-record-route-information/te:type/te:label/"
        + "te:label-hop/te:te-label/te:technology" {
    description "WSON label.";
    case wson {
      uses layer0-types:wson-path-label;
    }
  }

  augment "/te:tunnels-rpc/te:input/te:tunnel-info/"
        + "tepc:path-request" {
    description
       "Augment with additional constraints WSON
        tunnel.";
    uses wson-tunnel-attributes;
    uses wson-path-constraints;
  }
}
