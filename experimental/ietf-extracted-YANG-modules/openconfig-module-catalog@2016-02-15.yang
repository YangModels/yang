module openconfig-module-catalog {

  yang-version "1";

  // namespace
  namespace "http://openconfig.net/yang/module-catalog";

  prefix "oc-cat";

  // import some basic types
  import ietf-inet-types { prefix inet; }
  import openconfig-catalog-types { prefix oc-cat-types; }
  import openconfig-extensions { prefix oc-ext; }
  import openconfig-release-bundle { prefix oc-relbundle; }

  // meta
  organization "OpenConfig working group";

  contact
    "OpenConfig working group
    www.openconfig.net";

  description
    "This module provides a schema for cataloging and descrbing
    YANG models published across various organizations.";

  oc-ext:openconfig-version "0.1.0";

  revision "2016-02-15" {
    description
      "Initial OpenConfig public release";
    reference "0.1.0";
  }

  revision "2015-10-18" {
    description
      "Initial revision";
    reference "TBD";
  }

  // extension statements

  // feature statements

  // identity statements

  // typedef statements

  // grouping statements

  grouping module-implementation-information {
    description
      "Data describing any available implementations";

    container implementations {
      description
        "Container for module implementation information";

      list implementation {
        key "implementation-id";
        description
          "List of available implementations, keyed by an identifier
          provided by either the implementor or the module
          maintainer.  Such a key avoids needing a complex composite
          key to uniquely identify an implementation.";

        leaf implementation-id {
          type string;
          description
            "An identifier for the implementation, provided by the
            implementor or the module maintainer.  This id should
            uniquely identify a specific implementation of the
            module, e.g., based on the vendor, platform, and platform
            version.";
        }

        leaf description {
          type string;
          description
            "A text summary of important information about the
            implementation";
        }

        leaf reference {
          type union {
            type string;
            type inet:uri;
          }
          description
            "A URI or text reference to more detailed information
            about the implementation.";
        }

        leaf implementor-name {
          type string;
          description
            "Name of the vendor or entity providing the module
            implementation";
        }

        leaf platform {
          type string;
          description
            "Name of the server platform on which the implementation
            is available -- this could be the model name of a network
            device, a server OS, etc.";
        }

        leaf platform-version {
          type string;
          description
            "Implementor-defined version name or number for the
            module implementation, corresponding to the platform.
            This could be the firmware version of a network device
            such as a router, OS version, or other server platform
            version.";
        }

        leaf implementation-status {
          type identityref {
            base oc-cat-types:IMPLEMENTATION_STATUS_TYPE;
          }
          description
            "Indicates the status of the implementation, e.g.,
            complete, partial, in-progress, etc.  Implementors
            may define additional values for the base identity";
        }
      }
    }
  }

  grouping module-dependency-information {
    description
      "Information about module dependencies";

    container dependencies {
      description
        "Container for information about module dependencies";

      leaf-list required-module {
        type leafref {
            path "../../name";
        }
        description
          //TODO: should this list be complete, or only the first-
          //level dependencies?
          "A simple list of modules that are prerequisites for the
          current module.  It is expected that each of the required
          modules would in turn list their dependencies.  The list
          values should be references to other modules in the
          catalog.";
      }
    }
  }

  grouping module-classification-information {
    description
      "Data describing the module's classification(s)";

    container classification {
      description
        "Container for data describing the module's classification";

      leaf deployment-status {
        type identityref {
          base oc-cat-types:MODULE_STATUS_TYPE;
        }
        description
          "Deployment status of the module -- experimental,
          standards-track, production, etc.";
      }

      leaf category {
        type identityref {
          base oc-cat-types:MODULE_CATEGORY_BASE;
        }
        description
           "Categorization of the module based on identities defined
           or used by the publishing organizations.";
      }

      leaf subcategory {
        type identityref {
          base oc-cat-types:MODULE_SUBCATEGORY_BASE;
        }
        description
           "Sub-categorization of the module based on identities
            defined or used by the publishing organizations.";
      }
    }
  }

  grouping module-usage-information {
    description
      "Data pertaining to retrieval and usage of the module";

    container module-usage {
      description
        "Container for data pertaining to retrieval and usage of the
        module";

      leaf authentication {
        //TODO: requires more detailed model for different types
        //of authentication / validation schemes
        type string;
        description
          "Authentication information to allow
          users to verify that the model originates from
          stated organization, e.g., X.509 certificate";
      }

      leaf md5-hash {
        type string;
        description
          "MD5 hash of the module file, used by users to validate
          data integrity";
      }

      leaf access-uri {
        type inet:uri;
        description
          "URI where module can be downloaded.  Modules may be
          made available from the catalog maintainer, or directly
          from the publisher";
      }
    }
  }

  grouping module-base-information {
    description
      "Basic information describing the module, e.g., the
      YANG metadata in the module preface.";

    leaf name {
      type string;
      description
        "The module name, as defined in the YANG module file.";
    }

    leaf namespace {
      //type inet:uri;
      type string;
      description
        "Published namespace of module";
    }

    leaf prefix {
      type string;
      description "Published prefix of module";
    }

    leaf revision {
      type string;
      description
        "Date in the revision statement of the module";
    }

    leaf summary {
      type string;
      description
        "Brief summary of the module description";
    }

    leaf module-version {
      type string;
      description
        "Optional version number for the module, in addition to the
        YANG revision statement";
    }

    container module-hierarchy {

      description
      "YANG module hierarchy specification";

      leaf module-hierarchy-level {
        type uint8 {
          range 1..5;
        }
        default 1;
        description
          "Module hierarchy level. If this is a sub-module,
           it is set to > 1, depending
           on the hierarchy level of the sub-module";
      }

      leaf module-parent {
        when "../module-hierarchy-level > '1'" {
          description "Only applicable to sub-modules";
        }
        type leafref {
          path "../../name";
        }
        description
          "Parent module, if this is a sub-module";
      }
    }
  } //module-base-information

  grouping organization-information {
    description
      "Data describing the publisher of the module";

    leaf name {
      type string;
      description
        "Name of Organization defining YANG Module:
        Standards Body examples:
          ietf, ieee, opendaylight, etc.
        Commercial entity examples:
          AT&T, Facebook
        Name of industry forum examples:
          openconfig, other";
    }

    leaf type {
      type identityref {
        base oc-cat-types:ORGANIZATION_TYPE;
      }
      description
        "YANG modules publication authority";
    }

    leaf contact {
      type string;
      description
        "Contact information for the publishing organization";
    }
  }

  grouping module-catalog-top {
    description
      "Top level structure of the module catalog";

    container organizations {

      description
        "List of organizations owning modules";

      list organization {

        key "name";

        description
          "List of organizations defining the YANG Modules";

        uses organization-information;
        uses oc-relbundle:release-bundle-top;

        container modules {
          description
            "Modules published by this organization";

          list module {
            key "name";
            description
              "List of published modules from the organization";

            uses module-base-information;
            uses module-classification-information;
            uses module-dependency-information;
            uses module-usage-information;

          }
        }
      }
    }

    uses module-implementation-information;

  }

  // data definition statements

  uses module-catalog-top;

  // augment statements

}
