module ietf-supa-ddc {
  namespace "urn:ietf:params:xml:ns:yang:ietf-supa-ddc";
  // replace with IANA namespace when assigned
  prefix ddc;

  organization "IETF";
  contact
     "Editor: Ying Cheng
     chengying10@chinaunicom.cn";

  description
     "This YANG module defines a component that describing
   the ddc service model for creating and optimizing
   tenant's DC (data center) services that are deployed
   in multiple data centers.

     Terms and Acronyms
      DDC: Distributed Data Center
        L2VPN: Layer 2 Virtual Private Network
        L3VPN: Layer 3 Virtual Private Network";

  revision 2014-12-25 {
     description
        "Initial revision.";
     reference "RFC4364, RFC7277";
  }

  container createDdcServices {
    description
      "Management system/ application requires controller to
       create tenant's network that are deployed in multiple
     data centers. The controller(s) is/are told the following
     data: name of data centers that the tenant's service are
     deployed in, connected method between data centers for
     the tenant (e.g. L2VPN, l3VPN, Native IP, etc.), name
     of tenant, ID of networks that belong to the tenant";
    list ddcService {
      key "tenantName";
      description
        "Overall ddc operational data, including the names of data
     center,the connection method between data centers, name
     of tenant, ID of networks that belong to the tenants";
      leaf tenantName {
        type string;
        mandatory true;
        description
          "Indicates the name of the tenant that the ddc service
           is created for";
      }
      leaf-list dcName {
        type string;
        description
          "List of the names of data center that the tenant's
           service is deployed in.";
      }
      leaf-list tenantNetworkId {
        type string;
        description
          "list of the tenant networks in different data centers.
       These networks should be integrated into the tenant's
       vitual data center";
      }
      leaf connectionType {
        type enumeration {
          enum L2VPN {
            value 0;
            description "L2VPN";
          }
          enum L3VPN {
            value 1;
            description "L3VPN";
          }
          enum nativeIPv4 {
            value 2;
            description "L4VPN";
          }
          enum nativeIPv6 {
            value 3;
            description "nativeIPv6";
          }
        }
        description
          "Indicates the connection method between data centers
           that the tenant service is deployed in. The connection
           type may be VPN (L2VPN or L3VPN) or Native IP (IPv4 or
           IPv6)";
      }
    }
  }

  container createVpnInstancesforDdc {
    description
      "Management system/ application requires controller to
       create VPN for a tenant between data centers. VPN name,
       tennant VLAN ID, VPN sites and interfaces, VPN type,
       bandwidth requirement and latency requirement should be
       told to controller";
    list vpnInstance {
      key "vpnName";
      description
        "Overall VPN operational data, including the name of VPN,
         the VLAN ID of tenant, the sites information of the VPN,
         the interface names of VPN endpoints, the type of VPN,
         the bandwidth and latency requirements of VPN";
      leaf vpnName {
        type string;
        mandatory true;
        description
          "Indicates the name of the VPN instance";
      }
      leaf vlanId {
        type uint16 {
          range "1 .. 4094";
        }
        description
          "Indicates the VLAN id of the tenant in data centers";
      }
      list dataCenterInformation {
        key "dcName";
        leaf dcName {
          type string;
          description
          "List of the names of data center that the tenant's
           service is deployed in.";
        }
        leaf interfaceName {
          type string;
          description
            "Indicates a set of access interface names of the
             network device that the data centers (deployment
             of tenant's service)are connected to.";
        }
        description
          "List of data center information including the names
           of data center and a set of access interface names of
           the network device";
      }
      leaf vpnType {
        type enumeration {
          enum L2VPN {
            value 0;
            description "L2VPN";
          }
          enum L3VPN {
            value 1;
            description "L3VPN";
          }
        }
        description
          "Indicates the type of VPN instance that is created for
           tenant.It can be L2VPN or L3VPN";
      }
      leaf bandWidth {
        type uint32;
        description
          "Indicates the bandwidth requirement of the VPN instance
           that is created for tenant.";
      }
      leaf latency {
        type uint32;
        description
          "Indicates the latency requirement of the VPN instance
           that is created for tenant.";
      }
    }
  }

  container optimizeTrafficServices {
    description
      "Management system/ application requires controller to
       adjust the bandwidth of VPN to optimize the traffic when
       the bandwidth utilization is below or over certain
       threshold. vpn name, vpn type and adjusted bandwidth
       should be told to controller.";
    list optimizeTrafficService {
      key "vpnName";
      description
        "The list of VPN that need to be adjusted for optimizing
         traffic for the VPN between data centers. The data
         includes the name of adjusted VPN instance, the type of
         VPN instance, the bandwidth and the latency requirement";
      leaf vpnName {
        type string;
        mandatory true;
        description
          "Indicates the name of VPN that needs to be adjusted. A
           VPN instance is identified by vpnName. It should be one
           of the created VPN instance names";
      }
      leaf vpnType {
        type enumeration {
          enum L2VPN {
            value 0;
            description "L2VPN";
          }
          enum L3VPN {
            value 1;
            description "L3VPN";
          }
        }
        description
          "Indicates the type of VPN instance that needs to be
           adjusted.L2VPN or L3VPN";
      }
      leaf bandWidth {
        type uint32;
        description
          "Indicates the bandwidth requirement of the VPN instance
           that is created for tenant.";
      }
      leaf latency {
        type uint32;
        description
          "Indicates the latency requirement of the VPN instance
           that is created for tenant.";
      }
    }
  }
}
