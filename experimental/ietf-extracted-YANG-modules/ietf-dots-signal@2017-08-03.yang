module ietf-dots-signal {
      namespace "urn:ietf:params:xml:ns:yang:ietf-dots-signal";
      prefix "signal";
      import ietf-inet-types {
          prefix "inet";
      }
     organization "McAfee, Inc.";
     contact "Konda, Tirumaleswar Reddy <TirumaleswarReddy_Konda@McAfee.com>";

     description
       "This module contains YANG definition for DOTS
       signal sent by the DOTS client to the DOTS server.";

     revision 2017-08-03 {
       reference
       "https://tools.ietf.org/html/draft-reddy-dots-signal-channel";
     }

     container mitigation-scope {
          description
             "Top level container for a mitigation request.";

          list scope {
             key mitigation-id;
             description "Identifier for the mitigation request.";
             leaf mitigation-id {
                type int32;
                description "Mitigation request identifier.";
              }
              leaf-list target-ip {
                  type inet:ip-address;
                  description
                     "IPv4 or IPv6 address identifyting the target.";
              }

              leaf-list target-prefix {
                  type inet:ip-prefix;
                  description
                     "IPv4 or IPv6 prefix identifyting the target.";
              }

              list target-port-range {
                  key "lower-port upper-port";
                  description "Port range. When only lower-port is present,
                               it represents a single port.";

                  leaf lower-port {
                     type inet:port-number;
                     mandatory true;
                     description "Lower port number.";
                  }

                  leaf upper-port {
                     type inet:port-number;
                         must ". >= ../lower-port" {
                           error-message
                           "The upper port number must be greater than or
                            equal to lower port number.";
                         }
                         description "Upper port number.";
                  }
              }

              leaf-list target-protocol {
                  type uint8;
                  description "Identifies the target protocol number.";
              }
              leaf-list fqdn {
                   type inet:domain-name;
                   description "FQDN";
              }

              leaf-list uri {
                  type inet:uri;
                  description "URI";
              }

              leaf-list alias {
                  type string;
                  description "alias name";
              }

              leaf lifetime {
                  type int32;
                  description
                    "Indicates the lifetime of the mitigation request.";
              }
          }
     }
  }
