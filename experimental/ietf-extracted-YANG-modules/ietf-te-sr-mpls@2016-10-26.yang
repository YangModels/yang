module ietf-te-sr-mpls {
  namespace "urn:ietf:params:xml:ns:yang:ietf-te-sr-mpls";

  /* Replace with IANA when assigned */
  prefix "te-sr-mpls";

  /* Import TE generic types */
  import ietf-te {
    prefix te;
  }

  /* Import TE generic types */
  import ietf-te-types {
    prefix te-types;
  }

  organization
    "IETF Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editor:   Tarek Saad
               <mailto:tsaad@cisco.com>

     Editor:   Rakesh Gandhi
               <mailto:rgandhi@cisco.com>

     Editor:   Vishnu Pavan Beeram
               <mailto:vbeeram@juniper.net>

     Editor:   Himanshu Shah
               <mailto:hshah@ciena.com>

     Editor:   Xufeng Liu
               <mailto:xufeng.liu@ericsson.com>

     Editor:   Xia Chen
               <mailto:jescia.chenxia@huawei.com>

     Editor:   Raqib Jones
               <mailto:raqib@Brocade.com>

     Editor:   Bin Wen
               <mailto:Bin_Wen@cable.comcast.com>";

  description
    "YANG data module for MPLS TE configurations,
    state, RPC and notifications.";

  revision "2016-10-26" {
    description "Latest update to MPLS TE YANG module.";
    reference "TBD";
  }

  identity sr-adjacency-protection-type {
    description
       "The Adj-SID base protection types";
  }

  identity sr-adjacency-protection-type-protected {
    base sr-adjacency-protection-type;
    description
       "The Adj-SID is eligible for protection (e.g.: using
        IPFRR or MPLS-FRR)";
  }

  identity sr-adjacency-protection-type-unprotected {
    base sr-adjacency-protection-type;
    description
       "The Adj-SID is not eligible for protection (e.g.: using
        IPFRR or MPLS-FRR)";
  }

  /* MPLS SR-TE tunnel properties*/
  grouping tunnel-sr-mpls-properties_config {
    description "MPLS TE SR tunnel properties";
    leaf path-signaling-type {
      type identityref {
        base te-types:path-signaling-type;
      }
      description "TE tunnel path signaling type";
    }
  }

  grouping named-sr-path-constraints_config {
    description "foo";
    leaf adjacency-protection {
      type identityref {
        base sr-adjacency-protection-type;
      }
      description "foo";
    }

  }

  /*** End of MPLS SR-TE tunnel configuration/state */

  /**
   * MPLS TE augmentations
   */

  /* MPLS TE global augmentations */
  augment "/te:te/te:globals/te:config/te:named-constraints" {
    description
        "Augmentations for MPLS SR-TE config named constraints";
    uses named-sr-path-constraints_config;
  }

  augment "/te:te/te:globals/te:state/te:named-constraints" {
    description
        "Augmentations for MPLS SR-TE state named constraints";
    uses named-sr-path-constraints_config;
  }

  /* MPLS TE tunnel augmentations */
  augment "/te:te/te:tunnels/te:tunnel/te:primary-paths" {
    description
        "Augmentations for MPLS SR-TE tunnel primary paths";
    uses tunnel-sr-mpls-properties_config;
  }
  augment "/te:te/te:tunnels/te:tunnel/te:primary-paths/" +
          "te:secondary-paths" {
    description
        "Augmentations for MPLS SR-TE tunnel secondary paths";
    uses tunnel-sr-mpls-properties_config;
  }

  /* MPLS TE LSPs augmentations */
}
