module ietf-i2nsf-capability {
  yang-version 1.1;
  namespace
    "urn:ietf:params:xml:ns:yang:ietf-i2nsf-capability";
  prefix
    iicapa;

  organization
    "IETF I2NSF (Interface to Network Security Functions)
     Working Group";

  contact
    "WG Web: <http://tools.ietf.org/wg/i2nsf>
     WG List: <mailto:i2nsf@ietf.org>

     WG Chair: Adrian Farrel
     <mailto:Adrain@olddog.co.uk>

     WG Chair: Linda Dunbar
     <mailto:Linda.duhbar@huawei.com>

     Editor: Susan Hares
     <mailto:shares@ndzh.com>

     Editor: Jaehoon Paul Jeong
     <mailto:pauljeong@skku.edu>

     Editor: Jinyong Tim Kim
     <mailto:timkim@skku.edu>";

  description
    "This module describes a capability model
    for I2NSF devices.

    Copyright (c) 2018 IETF Trust and the persons
    identified as authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC 8341; see
    the RFC itself for full legal notices.";

  revision "2019-03-11"{
    description "Initial revision.";
    reference
      "RFC XXXX: I2NSF Capability YANG Data Model";
  }

  /*
   * Identities
   */

  identity event {
    description
      "Base identity for event of policy.";
    reference
      "draft-hong-i2nsf-nsf-monitoring-data-model-06
       - Event";
  }

  identity system-event-capa {
    base event;
    description
      "Identity for system event";
    reference
      "draft-hong-i2nsf-nsf-monitoring-data-model-06
       - System alarm";
  }

  identity system-alarm-capa {
    base event;
    description
      "Identity for system alarm";
    reference
      "draft-hong-i2nsf-nsf-monitoring-data-model-06
       - System alarm";
  }

  identity access-violation {
    base system-event-capa;
    description
      "Identity for access violation
      among system events";
    reference
      "draft-hong-i2nsf-nsf-monitoring-data-model-06
       - System event";
  }

  identity configuration-change {
    base system-event-capa;
    description
      "Identity for configuration change
      among system events";
    reference
      "draft-hong-i2nsf-nsf-monitoring-data-model-06
       - System event";
  }

  identity memory-alarm {
    base system-alarm-capa;
    description
      "Identity for memory alarm
      among system alarms";
    reference
      "draft-hong-i2nsf-nsf-monitoring-data-model-06
       - System alarm";
  }

  identity cpu-alarm {
    base system-alarm-capa;
    description
      "Identity for cpu alarm
      among system alarms";
    reference
      "draft-hong-i2nsf-nsf-monitoring-data-model-06
       - System alarm";
  }

  identity disk-alarm {
    base system-alarm-capa;
    description
      "Identity for disk alarm
      among system alarms";
    reference
      "draft-hong-i2nsf-nsf-monitoring-data-model-06
       - System alarm";
  }

  identity hardware-alarm {
    base system-alarm-capa;
    description
      "Identity for hardware alarm
      among system alarms";
    reference
      "draft-hong-i2nsf-nsf-monitoring-data-model-06
       - System alarm";
  }

  identity interface-alarm {
    base system-alarm-capa;
    description
      "Identity for interface alarm
      among system alarms";
    reference
      "draft-hong-i2nsf-nsf-monitoring-data-model-06
       - System alarm";
  }

  identity condition {
    description
      "Base identity for conditions of policy";
  }

  identity ipv4-capa {
    base condition;
    description
      "Identity for capabilities of IPv4 condition";
    reference
      "RFC 791: Internet Protocol";
  }

  identity exact-ipv4-header-length {
    base ipv4-capa;
    description
      "Identity for exact header length capability
      of IPv4 condition";
    reference
      "RFC 791: Internet Protocol - Header Length";
  }

  identity range-ipv4-header-length {
    base ipv4-capa;
    description
      "Identity for range header length capability
      of IPv4 condition";
    reference
      "RFC 791: Internet Protocol - Header Length";
  }

  identity ipv4-tos {
    base ipv4-capa;
    description
      "Identity for type of service capability
      of IPv4 condition";
    reference
      "RFC 791: Internet Protocol - Type of Service";
  }

  identity exact-ipv4-total-length {
    base ipv4-capa;
    description
      "Identity for exact total length capability
      of IPv4 condition";
    reference
      "RFC 791: Internet Protocol - Total Length";
  }

  identity range-ipv4-total-length {
    base ipv4-capa;
    description
      "Identity for range total length capability
      of IPv4 condition";
    reference
      "RFC 791: Internet Protocol - Total Length";
  }

  identity ipv4-id {
    base ipv4-capa;
    description
      "Identity for identification capability
      of IPv4 condition";
    reference
      "RFC 791: Internet Protocol - Identification";
  }

  identity ipv4-fragment-flags {
    base ipv4-capa;
    description
      "Identity for fragment flags capability
      of IPv4 condition";
    reference
      "RFC 791: Internet Protocol - Fragmentation  Flags";
  }

  identity exact-ipv4-fragment-offset {
    base ipv4-capa;
    description
      "Identity for exact fragment offset capability
      of IPv4 condition";
    reference
      "RFC 791: Internet Protocol - Fragmentation  Offset";
  }

  identity range-ipv4-fragment-offset {
    base ipv4-capa;
    description
      "Identity for range fragment offset capability
      of IPv4 condition";
    reference
      "RFC 791: Internet Protocol - Fragmentation  Offset";
  }

  identity exact-ipv4-ttl {
    base ipv4-capa;
    description
      "Identity for exact time to live capability
      of IPv4 condition";
    reference
      "RFC 791: Internet Protocol - Time To Live (TTL)";
  }

  identity range-ipv4-ttl {
    base ipv4-capa;
    description
      "Identity for range time to live capability
      of IPv4 condition";
    reference
      "RFC 791: Internet Protocol - Time To Live (TTL)";
  }

  identity ipv4-protocol {
    base ipv4-capa;
    description
      "Identity for protocol capability
      of IPv4 condition";
    reference
      "RFC 790: Assigned numbers - Assigned Internet
       Protocol Number
       RFC 791: Internet Protocol - Protocol";
  }

  identity exact-ipv4-address {
    base ipv4-capa;
    description
      "Identity for exact address capability
      of IPv4 condition";
    reference
      "RFC 791: Internet Protocol - Address";
  }

  identity range-ipv4-address {
    base ipv4-capa;
    description
      "Identity for range-address capability
      of IPv4 condition";
    reference
      "RFC 791: Internet Protocol - Address";
  }

  identity ipv4-ipopts {
    base ipv4-capa;
    description
      "Identity for option capability
      of IPv4 condition";
    reference
      "RFC 791: Internet Protocol - Options";
  }

  identity ipv4-sameip {
    base ipv4-capa;
    description
      "Identity for sameIP capability
      of IPv4 condition";
  }

  identity ipv4-geoip {
    base ipv4-capa;
    description
      "Identity for geography capability
      of IPv4 condition";
  }

  identity ipv6-capa {
    base condition;
    description
      "Identity for capabilities of IPv6 condition";
    reference
      "RFC 2460: Internet Protocol, Version 6 (IPv6)
      Specification";
  }

  identity ipv6-traffic-class {
    base ipv6-capa;
    description
      "Identity for traffic class capability
      of IPv6 condition";
    reference
      "RFC 2460: Internet Protocol, Version 6 (IPv6)
      Specification - Traffic Class";
  }

  identity exact-ipv6-flow-label {
    base ipv6-capa;
    description
      "Identity for exact flow label capability
      of IPv6 condition";
    reference
      "RFC 2460: Internet Protocol, Version 6 (IPv6)
      Specification - Flow Label";
  }

  identity range-ipv6-flow-label {
    base ipv6-capa;
    description
      "Identity for range flow label capability
      of IPv6 condition";
    reference
      "RFC 2460: Internet Protocol, Version 6 (IPv6)
      Specification - Flow Label";
  }

  identity exact-ipv6-payload-length {
    base ipv6-capa;
    description
      "Identity for exact payload length capability
      of IPv6 condition";
    reference
      "RFC 2460: Internet Protocol, Version 6 (IPv6)
      Specification - Payload Length";
  }

  identity range-ipv6-payload-length {
    base ipv6-capa;
    description
      "Identity for range payload length capability
      of IPv6 condition";
    reference
      "RFC 2460: Internet Protocol, Version 6 (IPv6)
      Specification - Payload Length";
  }

  identity ipv6-next-header {
    base ipv6-capa;
    description
      "Identity for next header capability
      of IPv6 condition";
    reference
      "RFC 2460: Internet Protocol, Version 6 (IPv6)
      Specification - Next Header";
  }

  identity exact-ipv6-hop-limit {
    base ipv6-capa;
    description
      "Identity for exact hop limit capability
      of IPv6 condition";
    reference
      "RFC 2460: Internet Protocol, Version 6 (IPv6)
      Specification - Hop Limit";
  }

  identity range-ipv6-hop-limit {
    base ipv6-capa;
    description
      "Identity for range hop limit capability
      of IPv6 condition";
    reference
      "RFC 2460: Internet Protocol, Version 6 (IPv6)
      Specification - Hop Limit";
  }

  identity exact-ipv6-address {
    base ipv6-capa;
    description
      "Identity for exact address capability
      of IPv6 condition";
    reference
      "RFC 2460: Internet Protocol, Version 6 (IPv6)
      Specification - Address";
  }

  identity range-ipv6-address {
    base ipv6-capa;
    description
      "Identity for range address capability
      of IPv6 condition";
    reference
      "RFC 2460: Internet Protocol, Version 6 (IPv6)
      Specification - Address";
  }

  identity tcp-capa {
    base condition;
    description
      "Identity for capabilities of tcp condition";
    reference
      "RFC 793: Transmission Control Protocol";
  }

  identity exact-tcp-port-num {
    base tcp-capa;
    description
      "Identity for exact port number capability
      of tcp condition";
    reference
      "RFC 793: Transmission Control Protocol - Port Number";
  }

  identity range-tcp-port-num {
    base tcp-capa;
    description
      "Identity for range port number capability
      of tcp condition";
    reference
      "RFC 793: Transmission Control Protocol - Port Number";
  }

  identity exact-tcp-seq-num {
    base tcp-capa;
    description
      "Identity for exact sequence number capability
      of tcp condition";
    reference
      "RFC 793: Transmission Control Protocol - Sequence Number";
  }

  identity range-tcp-seq-num {
    base tcp-capa;
    description
      "Identity for range sequence number capability
      of tcp condition";
    reference
      "RFC 793: Transmission Control Protocol - Sequence Number";
  }

  identity exact-tcp-ack-num {
    base tcp-capa;
    description
      "Identity for exact acknowledgement number capability
      of tcp condition";
    reference
      "RFC 793: Transmission Control Protocol - Acknowledgement Number";
  }

  identity range-tcp-ack-num {
    base tcp-capa;
    description
      "Identity for range acknowledgement number capability
      of tcp condition";
    reference
      "RFC 793: Transmission Control Protocol - Acknowledgement Number";
  }

  identity exact-tcp-window-size {
    base tcp-capa;
    description
      "Identity for exact window size capability
      of tcp condition";
    reference
      "RFC 793: Transmission Control Protocol - Window Size";
  }

  identity range-tcp-window-size {
    base tcp-capa;
    description
      "Identity for range window size capability
      of tcp condition";
    reference
      "RFC 793: Transmission Control Protocol - Window Size";
  }

  identity tcp-flags {
    base tcp-capa;
    description
      "Identity for flags capability
      of tcp condition";
    reference
      "RFC 793: Transmission Control Protocol - Flags";
  }

  identity udp-capa {
    base condition;
    description
      "Identity for capabilities of udp condition";
    reference
      "RFC 768: User Datagram Protocol";
  }

  identity exact-udp-port-num {
    base udp-capa;
    description
      "Identity for exact port number capability
      of udp condition";
    reference
      "RFC 768: User Datagram Protocol - Port Number";
  }

  identity range-udp-port-num {
    base udp-capa;
    description
      "Identity for range port number capability
      of udp condition";
    reference
      "RFC 768: User Datagram Protocol - Port Number";
  }

  identity exact-udp-total-length {
    base udp-capa;
    description
      "Identity for exact total-length capability
      of udp condition";
    reference
      "RFC 768: User Datagram Protocol - Total Length";
  }

  identity range-udp-total-length {
    base udp-capa;
    description
      "Identity for range total-length capability
      of udp condition";
    reference
      "RFC 768: User Datagram Protocol - Total Length";
  }

  identity icmp-capa {
    base condition;
    description
      "Identity for capabilities of icmp condition";
    reference
      "RFC 792: Internet Control Message Protocol";
  }

  identity icmp-type {
    base icmp-capa;
    description
      "Identity for icmp type capability
      of icmp condition";
    reference
      "RFC 792: Internet Control Message Protocol";
  }

  identity http-capa {
    base condition;
    description
      "Identity for capabilities of http condition";
  }

  identity uri {
    base http-capa;
    description
      "Identity for uri capabilities of
       http condition";
  }

  identity url {
    base http-capa;
    description
      "Identity for url capabilities of
       http condition";
  }

  identity log-action-capa {
    description
      "Identity for capabilities of log action";
  }

  identity rule-log {
    base log-action-capa;
    description
      "Identity for rule log capability
      of log action";
  }

  identity session-log {
    base log-action-capa;
    description
      "Identity for session log capability
      of log action";
  }

  identity ingress-action-capa {
    description
      "Identity for capabilities of ingress action";
    reference
      "draft-ietf-i2nsf-capability-04: Information Model
       of NSFs Capabilities - Action";
  }

  identity egress-action-capa {
    description
      "Base identity for egress action";
  }

  identity default-action-capa {
    description
      "Identity for capabilities of default action";
    reference
      "draft-ietf-i2nsf-capability-04: Information Model
       of NSFs Capabilities - Default action";
  }

  identity pass {
    base ingress-action-capa;
    base egress-action-capa;
    base default-action-capa;
    description
      "Identity for pass";
    reference
      "draft-ietf-i2nsf-capability-04: Information Model
       of NSFs Capabilities - Actions and
       default action";
  }

  identity drop {
    base ingress-action-capa;
    base egress-action-capa;
    base default-action-capa;
    description
      "Identity for drop";
    reference
      "draft-ietf-i2nsf-capability-04: Information Model
       of NSFs Capabilities - Actions and
       default action";
  }

  identity reject {
    base ingress-action-capa;
    base egress-action-capa;
    base default-action-capa;
    description
      "Identity for reject";
    reference
      "draft-ietf-i2nsf-capability-04: Information Model
       of NSFs Capabilities - Actions and
       default action";
  }

  identity alert {
    base ingress-action-capa;
    base egress-action-capa;
    base default-action-capa;
    description
      "Identity for alert";
    reference
      "draft-ietf-i2nsf-capability-04: Information Model
       of NSFs Capabilities - Actions and
       default action";
  }

  identity mirror {
    base ingress-action-capa;
    base egress-action-capa;
    base default-action-capa;
    description
      "Identity for mirror";
    reference
      "draft-ietf-i2nsf-capability-04: Information Model
       of NSFs Capabilities - Actions and
       default action";
  }

  identity invoke-signaling {
    base egress-action-capa;
    description
      "Identity for invoke signaling";
  }

  identity tunnel-encapsulation {
    base egress-action-capa;
    description
      "Identity for tunnel encapsulation";
  }

  identity forwarding {
    base egress-action-capa;
    description
      "Identity for forwarding";
  }

  identity redirection {
    base egress-action-capa;
    description
      "Identity for redirection";
  }

  identity resolution-strategy-capa {
    description
      "Base identity for resolution strategy";
    reference
      "draft-ietf-i2nsf-capability-04: Information Model
       of NSFs Capabilities - Resolution Strategy";
  }

  identity fmr {
    base resolution-strategy-capa;
    description
      "Identity for First Matching Rule (FMR)";
    reference
      "draft-ietf-i2nsf-capability-04: Information Model
       of NSFs Capabilities - Resolution Strategy";
  }

  identity lmr {
    base resolution-strategy-capa;
    description
      "Identity for Last Matching Rule (LMR)";
    reference
      "draft-ietf-i2nsf-capability-04: Information Model
       of NSFs Capabilities - Resolution Strategy";
  }

  identity pmr {
    base resolution-strategy-capa;
    description
      "Identity for Prioritized Matching Rule (PMR)";
    reference
      "draft-ietf-i2nsf-capability-04: Information Model
       of NSFs Capabilities - Resolution Strategy";
  }

  identity pmre {
    base resolution-strategy-capa;
    description
      "Identity for Prioritized Matching Rule
      with Errors (PMRE)";
    reference
      "draft-ietf-i2nsf-capability-04: Information Model
       of NSFs Capabilities - Resolution Strategy";
  }

  identity pmrn {
    base resolution-strategy-capa;
    description
      "Identity for Prioritized Matching Rule
      with No Errors (PMRN)";
    reference
      "draft-ietf-i2nsf-capability-04: Information Model
       of NSFs Capabilities - Resolution Strategy";
  }

  identity advanced-nsf-capa {
    description
      "Base identity for advanced
      network security function capabilities";
    reference
      "RFC 8329: Framework for Interface to Network Security
       Functions - Differences from ACL Data Models
       draft-dong-i2nsf-asf-config-01: Configuration of
       Advanced Security Functions with I2NSF Security
       Controller";
  }

  identity antivirus-capa {
    base advanced-nsf-capa;
    description
      "Identity for antivirus capabilities";
    reference
      "RFC 8329: Framework for Interface to Network Security
       Functions - Differences from ACL Data Models
       draft-dong-i2nsf-asf-config-01: Configuration of
       Advanced Security Functions with I2NSF Security
       Controller - Antivirus";
  }

  identity antiddos-capa {
    base advanced-nsf-capa;
    description
      "Identity for antiddos capabilities";
    reference
      "RFC 8329: Framework for Interface to Network Security
       Functions - Differences from ACL Data Models
       draft-dong-i2nsf-asf-config-01: Configuration of
       Advanced Security Functions with I2NSF Security
       Controller - Antiddos";
  }

  identity ips-capa {
    base advanced-nsf-capa;
    description
      "Identity for IPS capabilities";
    reference
      "RFC 8329: Framework for Interface to Network Security
       Functions - Differences from ACL Data Models
       draft-dong-i2nsf-asf-config-01: Configuration of
       Advanced Security Functions with I2NSF Security
       Controller - Intrusion Prevention System";
  }

  identity voip-volte-capa {
    base advanced-nsf-capa;
    description
      "Identity for VoIP/VoLTE capabilities";
    reference
      "RFC 3261: SIP: Session Initiation Protocol
       RFC 8329: Framework for Interface to Network Security
       Functions - Differences from ACL Data Models
       draft-dong-i2nsf-asf-config-01: Configuration of
       Advanced Security Functions with I2NSF Security
       Controller";
  }

  identity detect {
    base antivirus-capa;
    description
      "Identity for detect capabilities
      of antivirus";
    reference
      "draft-dong-i2nsf-asf-config-01: Configuration of
       Advanced Security Functions with I2NSF Security
       Controller - Antivirus";
  }

  identity exception-application {
    base antivirus-capa;
    description
      "Identity for exception application capabilities
      of antivirus";
    reference
      "draft-dong-i2nsf-asf-config-01: Configuration of
       Advanced Security Functions with I2NSF Security
       Controller - Antivirus";
  }

  identity exception-signature {
    base antivirus-capa;
    description
      "Identity for exception signature capabilities
      of antivirus";
    reference
      "draft-dong-i2nsf-asf-config-01: Configuration of
       Advanced Security Functions with I2NSF Security
       Controller - Antivirus";
  }

  identity whitelists {
    base antivirus-capa;
    description
      "Identity for whitelists capabilities
      of antivirus";
    reference
      "draft-dong-i2nsf-asf-config-01: Configuration of
       Advanced Security Functions with I2NSF Security
       Controller - Antivirus";
  }

  identity syn-flood-action {
    base antiddos-capa;
    description
      "Identity for syn flood action capabilities
      of antiddos";
    reference
      "draft-dong-i2nsf-asf-config-01: Configuration of
       Advanced Security Functions with I2NSF Security
       Controller - Antiddos";
  }

  identity udp-flood-action {
    base antiddos-capa;
    description
      "Identity for udp flood action capabilities
      of antiddos";
    reference
      "draft-dong-i2nsf-asf-config-01: Configuration of
       Advanced Security Functions with I2NSF Security
       Controller - Antiddos";
  }

  identity http-flood-action {
    base antiddos-capa;
    description
      "Identity for http flood action capabilities
      of antiddos";
    reference
      "draft-dong-i2nsf-asf-config-01: Configuration of
       Advanced Security Functions with I2NSF Security
       Controller - Antiddos";
  }

  identity https-flood-action {
    base antiddos-capa;
    description
      "Identity for https flood action capabilities
      of antiddos";
    reference
      "draft-dong-i2nsf-asf-config-01: Configuration of
       Advanced Security Functions with I2NSF Security
       Controller - Antiddos";
  }

  identity dns-request-flood-action {
    base antiddos-capa;
    description
      "Identity for dns request flood action capabilities
      of antiddos";
    reference
      "draft-dong-i2nsf-asf-config-01: Configuration of
       Advanced Security Functions with I2NSF Security
       Controller - Antiddos";
  }

  identity dns-reply-flood-action {
    base antiddos-capa;
    description
      "Identity for dns reply flood action capabilities
      of antiddos";
    reference
      "draft-dong-i2nsf-asf-config-01: Configuration of
       Advanced Security Functions with I2NSF Security
       Controller - Antiddos";
  }

  identity icmp-flood-action {
    base antiddos-capa;
    description
      "Identity for icmp flood action capabilities
      of antiddos";
    reference
      "draft-dong-i2nsf-asf-config-01: Configuration of
       Advanced Security Functions with I2NSF Security
       Controller - Antiddos";
  }

  identity sip-flood-action {
    base antiddos-capa;
    description
      "Identity for sip flood action capabilities
      of antiddos";
    reference
      "draft-dong-i2nsf-asf-config-01: Configuration of
       Advanced Security Functions with I2NSF Security
       Controller - Antiddos";
  }

  identity detect-mode {
    base antiddos-capa;
    description
      "Identity for detect mode capabilities
      of antiddos";
    reference
      "draft-dong-i2nsf-asf-config-01: Configuration of
       Advanced Security Functions with I2NSF Security
       Controller - Antiddos";
  }

  identity baseline-learn {
    base antiddos-capa;
    description
      "Identity for baseline learn capabilities
      of antiddos";
    reference
      "draft-dong-i2nsf-asf-config-01: Configuration of
       Advanced Security Functions with I2NSF Security
       Controller - Antiddos";
  }

  identity signature-set {
    base ips-capa;
    description
      "Identity for signature set capabilities
      of IPS";
    reference
      "draft-dong-i2nsf-asf-config-01: Configuration of
       Advanced Security Functions with I2NSF Security
       Controller - Intrusion Prevention System";
  }
  identity ips-exception-signature {
    base ips-capa;
    description
      "Identity for ips exception signature capabilities
      of IPS";
    reference
      "draft-dong-i2nsf-asf-config-01: Configuration of
       Advanced Security Functions with I2NSF Security
       Controller - Intrusion Prevention System";
  }

  identity voice-id {
    base voip-volte-capa;
    description
      "Identity for voice-id capabilities
      of VoIP/VoLTE";
    reference
      "RFC 3261: SIP: Session Initiation Protocol";
  }

  identity user-agent {
    base voip-volte-capa;
    description
      "Identity for user agent capabilities
      of VoIP/VoLTE";
    reference
      "RFC 3261: SIP: Session Initiation Protocol";
  }

  /*
   *  Grouping
   */

  grouping nsf-capabilities {
    description
      "Capabilities of network security funtion";
    reference
      "RFC 8329: Framework for Interface to Network Security
       Functions - I2NSF Flow Security Policy Structure
       draft-ietf-i2nsf-capability-04: Information Model
       of NSFs Capabilities - Capability Information Model Design";

    leaf-list time-capabilities {
      type enumeration {
        enum absolute-time {
          description
            "Capabilities of absolute time.
             If network security function has the absolute time
             capability, the network security function
             supports rule execution according to absolute time.";
        }
        enum periodic-time {
          description
            "Capabilities of periodic time.
             If network security function has the periodic time
             capability, the network security function
             supports rule execution according to periodic time.";
        }
      }
      description
        "This is capabilities for time";
    }

    container event-capabilities {
      description
        "Capabilities of events.
         If network security function has
         the event capabilities, the network security functions
         supports rule execution according to system event
         and system alarm.";

      reference
        "RFC 8329: Framework for Interface to Network Security
         Functions - I2NSF Flow Security Policy Structure
         draft-ietf-i2nsf-capability-04: Information Model
         of NSFs Capabilities - Design Principles and ECA
         Policy Model Overview
         draft-hong-i2nsf-nsf-monitoring-data-model-06: A YANG
         Data Model for Monitoring I2NSF Network Security
         Functions - System Alarm and System Events";

      leaf-list system-event-capa {
        type identityref {
          base system-event-capa;
        }
        description
          "Capabilities for a system event";
      }

      leaf-list system-alarm-capa {
        type identityref {
          base system-alarm-capa;
        }
        description
          "Capabilities for a system alarm";
      }
    }

    container condition-capabilities {
      description
        "Capabilities of conditions.";

      container generic-nsf-capabilities {
        description
          "Capabilities of conditions.
           If a network security function has
           the condition capabilities, the network security function
           supports rule execution according to conditions of IPv4,
           IPv6, foruth layer, ICMP, and payload.";
        reference
          "RFC  791: Internet Protocol
           RFC  792: Internet Control Message Protocol
           RFC  793: Transmission Control Protocol
           RFC 2460: Internet Protocol, Version 6 (IPv6)
           Specification - Next Header
           RFC 8329: Framework for Interface to Network Security
           Functions - I2NSF Flow Security Policy Structure
           draft-ietf-i2nsf-capability-04: Information Model
           of NSFs Capabilities - Design Principles and ECA Policy
           Model Overview";

        leaf-list ipv4-capa {
          type identityref {
            base ipv4-capa;
          }
          description
            "Capabilities for an IPv4 packet";
          reference
            "RFC 791: Internet Protocol";
        }

        leaf-list ipv6-capa {
          type identityref {
            base ipv6-capa;
          }
          description
            "Capabilities for an IPv6 packet";
          reference
            "RFC 2460: Internet Protocol, Version 6 (IPv6)
             Specification - Next Header";
        }

        leaf-list tcp-capa {
          type identityref {
            base tcp-capa;
          }
          description
            "Capabilities for a tcp packet";
          reference
            "RFC 793: Transmission Control Protocol";
        }

        leaf-list udp-capa {
          type identityref {
            base udp-capa;
          }
          description
            "Capabilities for an udp packet";
          reference
            "RFC 768: User Datagram Protocol";
        }

        leaf-list icmp-capa {
          type identityref {
            base icmp-capa;
          }
          description
            "Capabilities for an ICMP packet";
          reference
            "RFC 2460: Internet Protocol, Version 6 (IPv6) ";
        }
      }

      container advanced-nsf-capabilities {
        description
          "Capabilities of advanced network security functions,
           such as anti virus, anti DDoS, IPS, and VoIP/VoLTE.";
        reference
          "RFC 8329: Framework for Interface to Network Security
           Functions - Differences from ACL Data Models
           draft-dong-i2nsf-asf-config-01: Configuration of
           Advanced Security Functions with I2NSF Security
           Controller";

        leaf-list antivirus-capa {
          type identityref {
            base antivirus-capa;
          }
          description
            "Capabilities for an antivirus";
          reference
            "draft-dong-i2nsf-asf-config-01: Configuration of
             Advanced Security Functions with I2NSF Security
             Controller";
        }

        leaf-list antiddos-capa {
          type identityref {
            base antiddos-capa;
          }
          description
            "Capabilities for an antiddos";
          reference
            "draft-dong-i2nsf-asf-config-01: Configuration of
             Advanced Security Functions with I2NSF Security
             Controller";
        }

        leaf-list ips-capa {
          type identityref {
            base ips-capa;
          }
          description
            "Capabilities for an ips";
          reference
            "draft-dong-i2nsf-asf-config-01: Configuration of
             Advanced Security Functions with I2NSF Security
             Controller";
        }

        leaf-list http-capa {
          type identityref {
            base http-capa;
          }
          description
            "Capabilities for a http";
          reference
            "draft-dong-i2nsf-asf-config-01: Configuration of
             Advanced Security Functions with I2NSF Security
             Controller";
        }

        leaf-list voip-volte-capa {
          type identityref {
            base voip-volte-capa;
         }
          description
            "Capabilities for a voip and volte";
          reference
            "draft-dong-i2nsf-asf-config-01: Configuration of
             Advanced Security Functions with I2NSF Security
             Controller";
        }
      }
    }
    container action-capabilities {
      description
        "Capabilities of actions.
         If network security function has
         the action capabilities, the network security function
         supports rule execution according to actions.";

      leaf-list ingress-action-capa {
        type identityref {
          base ingress-action-capa;
        }
        description
          "Capabilities for an action";
      }

      leaf-list egress-action-capa {
        type identityref {
          base egress-action-capa;
        }
        description
          "Capabilities for an egress action";
      }

      leaf-list log-action-capa {
        type identityref {
          base log-action-capa;
        }
        description
          "Capabilities for a log action";
      }
    }

    leaf-list resolution-strategy-capabilities {
      type identityref {
        base resolution-strategy-capa;
      }
      description
        "Capabilities for a resolution strategy.
        The resolution strategies can be used to
        specify how to resolve conflicts that occur between
        the actions of the same or different policy rules that
        are matched and contained in this particular NSF";
      reference
        "draft-ietf-i2nsf-capability-04: Information Model
         of NSFs Capabilities - Resolution strategy";
    }

    leaf-list default-action-capabilities {
      type identityref {
        base default-action-capa;
      }
      description
        "Capabilities for a default action.
         A default action is used to execute I2NSF policy rule
         when no rule matches a packet. The default action is
         defined as pass, drop, reject, alert, and mirror.";
      reference
        "draft-ietf-i2nsf-capability-04: Information Model
         of NSFs Capabilities - Default action";
    }
  }

  /*
   * Data nodes
   */

  container nsf {
    description
      "The list of capabilities of
       network security function";
    uses nsf-capabilities;
  }
}
