module ietf-slice-policy {
  yang-version 1.1;
  namespace "urn:ietf:params:xml:ns:yang:ietf-slice-policy";
  prefix "sl-pol";

  import ietf-inet-types {
    prefix "inet";
    reference
      "RFC 6991: Common YANG Data Types";
  }

  import ietf-routing-types {
    prefix "rt-types";
    reference
      "RFC 8294: Common YANG Data Types for the Routing Area";
  }

  import ietf-access-control-list {
    prefix "acl";
    reference
      "RFC 8519: YANG Data Model for Network Access Control Lists
       (ACLs)";
  }

  import ietf-te-types {
    prefix te-types;
    reference
      "RFC 8776: Common YANG Data Types for Traffic Engineering";
  }

  organization
    "IETF Traffic Engineering Architecture and Signaling (TEAS)
     Working Group.";

  contact
    "WG Web:   <http://tools.ietf.org/wg/teas/>
     WG List:  <mailto:teas@ietf.org>

     Editor:   Vishnu Pavan Beeram
               <mailto:vbeeram@juniper.net>

     Editor:   Tarek Saad
               <mailto:tsaad@juniper.net>

     Editor:   Bin Wen
               <mailto:Bin_Wen@cable.comcast.com>

     Editor:   Daniele Ceccarelli
               <mailto:daniele.ceccarelli@ericsson.com>

     Editor:   Shaofu Peng
               <mailto:peng.shaofu@zte.com.cn>

     Editor:   Ran Chen
               <mailto:chen.ran@zte.com.cn>

     Editor:   Luis M. Contreras
               <mailto:luismiguel.contrerasmurillo@telefonica.com>

     Editor:   Xufeng Liu
               <mailto:xufeng.liu.ietf@gmail.com>";

  description
    "This YANG module defines a data model for managing slice
     policies on slice policy capable nodes and controllers.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX; see the
     RFC itself for full legal notices.";

  revision "2021-02-22" {
    description "Initial revision.";
    reference
      "RFC XXXX: YANG Data Model for Slice Policies.";
  }

  /*
   * I D E N T I T I E S
   */

  /*
   * Identity - MPLS Slice Selector Label Position Type
   */

  identity ss-mpls-label-position-type {
    description
      "Base identity for the position of the MPLS label that is used
       for slice selection.";
  }

  identity ss-mpls-label-position-top {
    base ss-mpls-label-position-type;
    description
      "MPLS label that is used for slice selection is at the top of
       the label stack.";
  }

  identity ss-mpls-label-position-bottom {
    base ss-mpls-label-position-type;
    description
      "MPLS label that is used for slice selection is either at the
       bottom or at a specific offset from the bottom of the label
       stack.";
  }

  identity ss-mpls-label-position-indicator {
    base ss-mpls-label-position-type;
    description
      "MPLS label that is used for slice selection is preceded by
       a special purpose indicator label in the label stack.";
  }

  /*
   * Identity - S-PHB Class Direction
   */

  identity s-phb-class-direction {
    description
      "Base identity for the direction of traffic to which the Slice
       PHB class profile is applied.";
  }

  identity s-phb-class-direction-in {
    base s-phb-class-direction;
    description
      "Slice PHB class profile is applied to incoming traffic.";
  }

  identity s-phb-class-direction-out {
    base s-phb-class-direction;
    description
      "Slice PHB class profile is applied to outgoing traffic.";
  }

  identity s-phb-class-direction-in-out {
    base s-phb-class-direction;
    description
      "Slice PHB class profile is applied to both incoming and
       outgoing directions of traffic.";
  }

  /*
   * Identity - S-PHB Class Priority
   */

  identity s-phb-class-priority {
    description
      "Base identity for the priority of the child class scheduler.";
  }

  identity s-phb-class-priority-low {
    base s-phb-class-priority;
    description
      "Priority of the child class scheduler is low.";
  }

  identity s-phb-class-priority-strict-high {
    base s-phb-class-priority;
    description
      "Priority of the child class scheduler is strict-high.";
  }

  /*
   * Identity - S-PHB Class Drop Probability
   */

  identity s-phb-class-drop-probability {
    description
      "Base identity for the drop probability applied to packets
       exceeding the CIR of the class queue.";
  }

  identity s-phb-class-drop-probability-low {
    base s-phb-class-drop-probability;
    description
      "Low drop probability applied to packets exceeding the CIR of
       the class queue.";
  }

  identity s-phb-class-drop-probability-medium {
    base s-phb-class-drop-probability;
    description
      "Medium drop probability applied to packets exceeding the CIR
       of the class queue.";
  }

  identity s-phb-class-drop-probability-high {
    base s-phb-class-drop-probability;
    description
      "High drop probability applied to packets exceeding the CIR of
       the class queue.";
  }

  /*
   * T Y P E D E F S
   */

  typedef slice-policy-acl-ref {
    type leafref {
      path "/acl:acls/acl:acl/acl:name";
    }
    description
      "This type is used to reference an ACL.";
  }

  typedef slice-policy-ss-ref {
    type leafref {
      path "/network-slicing/slice-policies/slice-policy/"
        + "slice-selectors/slice-selector/index";
    }
    description
      "This type is used to reference a Slice Selector (SS).";
  }

  typedef slice-policy-phb-ref {
    type leafref {
      path "/network-slicing/phbs/phb/"
        + "id";
    }
    description
      "This type is used to reference a Slice Policy Per-Hop
       Behavior (S-PHB).";
  }

  typedef slice-policy-topo-filter-ref {
    type leafref {
      path "/network-slicing/topology-filters/topology-filter/"
        + "name";
    }
    description
      "This type is used to reference a Slice Policy Topology.";
  }

  /*
   * G R O U P I N G S
   */

  /*
   * Grouping - Slice Selector MPLS: Label location specific fields
   */
  grouping sl-pol-ss-mpls-label-location {
    description
      "Grouping for MPLS (SS) label location specific fields.";
    leaf label-position {
      type identityref {
        base ss-mpls-label-position-type;
      }
      description
        "MPLS label position - top, bottom with offset, Slice label
         indicator.";
    }
    leaf label-position-offset {
      when "derived-from-or-self(../label-position,"
        + "'sl-pol:ss-mpls-label-position-bottom')" {
        description
          "MPLS label position offset is relevant only when the
           label-position is set to 'bottom'.";
      }
      type uint8;
      description
        "MPLS label position offset.";
    }
  }
  /*
   * Grouping - Slice Selector (SS)
   */
  grouping sl-pol-slice-selector {
    description
      "Grouping for Slice Selectors.";
    container slice-selectors {
      description
        "Container for Slice Selectors.";
      list slice-selector {
        key "index";
        description
          "List of Slice Selectors - this includes the default
           selector and others that are used for overriding the
           default.";
        leaf index {
          type uint16;
          description
            "An index to identify an entry in the slice-selector
             list. The entry with the lowest index is the
             default slice-selector.";
        }
        container mpls {
          description
            "Container for MPLS Slice Selector.";
          choice ss-mpls-type {
            description
              "Choices for MPLS Slice Selector.";
            case label-value {
              leaf label {
                type rt-types:mpls-label;
                description
                  "MPLS Slice Selector Label is explicitly
                   specified.";
              }
              uses sl-pol-ss-mpls-label-location;
            }
            case label-ranges {
              list label-range {
                key "index";
                unique "start-label end-label";
                description
                  "MPLS Slice Selector Label is picked from a
                   specified set of label ranges.";
                leaf index {
                  type string;
                  description
                    "A string that uniquely identifies a label
                     range.";
                }
                leaf start-label {
                  type rt-types:mpls-label;
                  must '. <= ../end-label' {
                    error-message
                      "The start-label must be less than or equal "
                    + "to end-label";
                  }
                  description
                    "Label-range start.";
                }
                leaf end-label {
                  type rt-types:mpls-label;
                  must '. >= ../start-label' {
                    error-message
                      "The end-label must be greater than or equal "
                    + "to start-label";
                  }
                  description
                    "Label-range end.";
                }
                uses sl-pol-ss-mpls-label-location;
              }
            }
          }
        }
        container ipv4 {
          description
            "Container for IPv4 Slice Selector.";
          leaf-list destination-prefix {
            type inet:ipv4-prefix;
            description
              "IPv4 Slice Selector is picked from a specified set of
               IPv4 destination prefixes.";
          }
        }
        container ipv6 {
          description
            "Container for IPv6 Slice Selector.";
          choice ss-ipv6-type {
            description
              "Choices for IPv6 Slice Selector.";
            case ipv6-destination {
              leaf-list destination-prefix {
                type inet:ipv6-prefix;
                description
                  "IPv6 Slice Selector is picked from a specified
                   set of IPv6 destination prefixes.";
              }
            }
            case ipv6-flow-label {
              container slid-flow-labels {
                description
                  "Container for a set of Slice IDs that are
                   encoded within the flow label.";
                list slid-flow-label {
                  key "slid";
                  description
                    "IPv6 Slice Selector is picked from a set of
                     Slice IDs that are encoded within the flow
                     label.";
                  leaf slid {
                    type inet:ipv6-flow-label;
                    description
                      "Slice ID encoded inside the IPv6 flow label.";
                  }
                  leaf bitmask {
                    type uint32;
                    description
                      "Bitmask to extract the encoded Slice ID from
                       the IPv6 flow label.";
                  }
                }
              }
            }
          }
        }
        leaf-list acl-ref {
          type slice-policy-acl-ref;
          description
            "Slice Selection is done based on the specified list of
             ACLs.";
        }
      }
    }
  }

  /*
   * Grouping - Slice Policy Resource Reservation
   */
  grouping sl-pol-resource-reservation {
    description
      "Grouping for slice policy resource reservation.";
    container resource-reservation {
      description
        "Container for slice policy resource reservation.";
      leaf preference {
        type uint16;
        description
          "Control plane preference for the corresponding
           slice aggregate. A higher preference
           indicates a more favorable resource
           reservation than a lower preference.";
      }
      choice max-bw-type {
        description
          "Choice of maximum bandwidth specification.";
        case bw-value {
          leaf maximum-bandwidth {
            type uint64;
            description
              "The maximum bandwidth allocated to a slice aggregate
               on the network resources - specified as absolute
               value.";
          }
        }
        case bw-percentage {
          leaf maximum-bandwidth-percent {
            type rt-types:percentage;
            description
              "The maximum bandwidth allocated to a slice aggregate
               on the network resources - specified as percentage
               of link capacity.";
          }
        }
      }
      leaf-list shared-resource-groups {
        type uint32;
        description
          "List of shared resource groups that a slice aggregate
           shares its allocated resources with.";
      }
      container protection {
        description
          "Container for slice aggregate protection reservation.";
        leaf backup-sa-id {
          type uint32;
          description
            "The ID that identifies the slice aggregate used
             for backup paths that protect primary paths in a
             specific slice aggregate.";
        }
        choice backup-bw-type {
          description
            "Choice of backup bandwidth specification.";
          case backup-bw-value {
            leaf backup-bandwidth {
              type uint64;
              description
                "The maximum bandwidth on a network resource that
                 is allocated for backup traffic - specified as
                 absolute value.";
            }
          }
          case backup-bw-percentage {
            leaf backup-bandwidth-percent {
              type rt-types:percentage;
              description
                "The maximum bandwidth on a network resource that
                 is allocated for backup traffic - specified as
                 percentage of the link capacity.";
            }
          }
        }
      }
    }
  }

  /*
   * Grouping - Slice policy PHB (S-PHB)
   */
  grouping sl-pol-phb {
    description
      "Grouping for S-PHB.";
    leaf phb {
      type slice-policy-phb-ref;
      description
        "Reference to a specific PHB from the list of global
         PHBs.";
    }
  }

  /*
   * Grouping - Slice policy default profile override
   */
  grouping sl-pol-override-options {
    description
      "Grouping of fields that are used to override the default
       profile of the slice policy.";
    leaf slice-selector-override {
      type slice-policy-ss-ref;
      description
        "Reference to a specific Slice Selector (different from
         default).";
    }
    leaf phb-override {
      type slice-policy-phb-ref;
      description
        "Reference to a specific PHB (different from default).";
    }
  }

  /*
   * Grouping - Standard Topology Filter
   */
  grouping sl-pol-topo-filter-standard {
    description
      "Grouping for standard topology filter.";
    choice standard-topo-type {
      description
        "Choice of standard topology filter.";
      case flex-algo {
        leaf algo-id {
          type uint8;
          description
            "Algorithm ID.";
        }
        leaf mt-id {
          type uint16;
          description
            "Multi Topology ID.";
        }
      }
      case te-topo {
        uses te-types:te-topology-identifier;
      }
    }
  }

  /*
   * Grouping - Custom Topology Filters
   */
  grouping sl-pol-topo-filter-custom {
    description
      "Grouping for custom topology filters.";
    leaf-list link-affinity {
      type string;
      description
        "Match-filter is a list of link affinities.";
    }
    leaf-list link-name {
      type string;
      description
        "Match-filter is a list of link names.";
    }
    leaf-list node-prefix {
      type inet:ip-prefix;
      description
        "Match-filter is a list of node IDs.";
    }
    leaf-list as {
      type inet:as-number;
      description
        "Match-filter is a list of AS numbers.";
    }
  }

  /*
   * Grouping - Member Topologies
   */
  grouping sl-pol-member-topologies {
    description
      "Grouping for member topologies.";
    container member-topologies {
      description
        "Container for member topologies.";
      list member-topology {
        key "topology-filter";
        description
          "List of member topologies.";
        leaf topology-filter {
          type slice-policy-topo-filter-ref;
          description
            "Reference to a specific topology filter from the list
             of global topology filters.";
        }
        uses sl-pol-override-options;
      }
    }
  }

  /*
   * Grouping - Per-Hop Behaviors (PHBs)
   */
  grouping sl-pol-phbs {
    description
      "Grouping for PHBs.";
    container phbs {
      description
        "Container for PHBs.";
      list phb {
        key "id";
        description
          "List of PHBs.";
        leaf id {
          type uint16;
          description
            "A 16-bit ID that uniquely identifies the PHB.";
        }
        choice profile-type {
          description
            "Choice of PHB profile type.";
          case profile {
            description
              "Generic PHB profile available on the network
               element.";
            leaf profile {
              type string;
              description
                "Generic PHB profile identifier.";
            }
          }
          case custom-profile {
            description
              "Custom PHB profile.";
            choice guaranteed-rate-type {
              description
                "Guaranteed rate is the committed information rate
                 (CIR) of the slice aggregate. The guaranteed rate
                 also determines the amount of excess (extra)
                 bandwidth that a group of slice aggregates can
                 share. Extra bandwidth is allocated among the
                 group in proportion to the guaranteed rate of
                 each slice aggregate.";
              case rate {
                leaf guaranteed-rate {
                  type uint64;
                  description
                    "Guaranteed rate specified as absolute value.";
                }
              }
              case percentage {
                leaf guaranteed-rate-percent {
                  type rt-types:percentage;
                  description
                    "Guaranteed rate specified in percentage.";
                }
              }
            }
            choice shaping-rate-type {
              description
                "Shaping rate is the maximum bandwidth of the slice
                 aggregate; the peak information rate (PIR) of a
                 slice aggregate.";
              case rate {
                leaf shaping-rate {
                  type uint64;
                  description
                    "Shaping rate specified as absolute value.";
                }
              }
              case percentage {
                leaf shaping-rate-percent {
                  type rt-types:percentage;
                  description
                    "Shaping rate specified in percentage.";
                }
              }
            }
            container classes {
              description
                "Container for classes.";
              list class {
                key class-id;
                description
                  "List of classes.";
                leaf class-id {
                  type string;
                  description
                    "A string to uniquely identify a class.";
                }
                leaf direction {
                  type identityref {
                    base s-phb-class-direction;
                  }
                  description
                    "Class direction.";
                }
                leaf priority {
                  type identityref {
                    base s-phb-class-priority;
                  }
                  description
                    "Priority of the class scheduler. Only one slice
                     aggregate class queue can be set as a
                     strict-high priority queue. Strict-high
                     priority allocates the scheduled bandwidth to
                     the queue before any other queue receives
                     bandwidth. Other queues receive the bandwidth
                     that remains after the strict-high queue has
                     been serviced.";
                }
                choice guaranteed-rate-type {
                  description
                    "Guaranteed Rate is the Committed information
                     rate (CIR) of slice aggregate class - specified
                     as absolute value or percentage.";
                  case rate {
                    leaf guaranteed-rate {
                      type uint64;
                      description
                        "Guaranteed rate specified as absolute
                         value.";
                    }
                  }
                  case percentage {
                    leaf guaranteed-rate-percent {
                      type rt-types:percentage;
                      description
                        "Guaranteed rate specified in percentage.";
                    }
                  }
                }
                leaf drop-probability {
                  type identityref {
                    base s-phb-class-drop-probability;
                  }
                  description
                    "Drop probability applied to packets exceeding
                     the CIR of the class queue.";
                }
                choice maximum-bandwidth-type {
                  description
                    "Maximum bandwidth is the Peak information
                     rate (PIR) of slice aggregate class - specified
                     as absolute value or percentage.";
                  case rate {
                    leaf maximum-bandwidth {
                      type uint64;
                      description
                        "Maximum bandwidth specified as absolute
                         value.";
                    }
                  }
                  case percentage {
                    leaf maximum-bandwidth-percent {
                      type rt-types:percentage;
                      description
                        "Maximum bandwidth specified as percentage.";
                    }
                  }
                }
                choice delay-buffer-size-type {
                  description
                    "Size of the queue buffer as a percentage of the
                     dedicated buffer space - specified as value or
                     percentage.";
                  case value {
                    leaf delay-buffer-size {
                      type uint64;
                      description
                        "Delay buffer size.";
                    }
                  }
                  case percentage {
                    leaf delay-buffer-size-percent {
                      type rt-types:percentage;
                      description
                        "Delay buffer size specified as percentage.";
                    }
                  }
                }
              }
            }
          }
        }
      }
    }
  }

  /*
   * Grouping - Topology Filters
   */
  grouping sl-pol-topology-filters {
    description
      "Grouping for topology filters.";
    container topology-filters {
      description
        "Container for topology filters.";
      list topology-filter {
        key "name";
        description
          "List of topology filters.";
        leaf name {
          type string;
          description
            "A string that uniquely identifies the topology filter.";
        }
        choice topology-filter-type {
          description
            "Choice of topology filter type.";
          case standard-topology {
            uses sl-pol-topo-filter-standard;
          }
          case custom-topology {
            container include-any {
              description
                "Include-any filters.";
              uses sl-pol-topo-filter-custom;
            }
            container include-all {
              description
                "Include-all filters.";
              uses sl-pol-topo-filter-custom;
            }
            container exclude {
              description
                "Exclude filters.";
             uses sl-pol-topo-filter-custom;
            }
          }
        }
      }
    }
  }

  /*
   * Grouping - Slice Policies
   */
  grouping sl-policies {
    description
      "Grouping for slice policies.";
    container slice-policies {
      description
        "Container for slice policies.";
      list slice-policy {
        key "name";
        unique "sa-id";
        description
          "List of slice policies.";
        leaf name {
          type string;
          description
            "A string that uniquely identifies the slice policy.";
        }
        leaf sa-id {
          type uint32;
          description
            "A 32-bit ID that uniquely identifies the slice
             aggregate created by the enforcement of this slice
             policy.";
        }
        uses sl-pol-resource-reservation;
        uses sl-pol-slice-selector;
        uses sl-pol-phb;
        uses sl-pol-member-topologies;
      }
    }
  }

  /*
   * Top-level container - Network Slicing
   */
  container network-slicing {
    presence "Enable network slicing.";
    description
      "Top-level container for network slicing specific constructs
       on a slice policy capable network entity.";
    uses sl-pol-phbs;
    uses sl-pol-topology-filters;
    uses sl-policies;
  }
}
