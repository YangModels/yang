module ietf-l3-te-topology {
  yang-version 1.1;
  namespace "urn:ietf:params:xml:ns:yang:ietf-l3-te-topology";
  prefix "l3tet";

  import ietf-network {
    prefix "nw";
    reference "RFC 8345: A YANG Data Model for Network Topologies";
  }
  import ietf-network-topology {
    prefix "nt";
    reference "RFC 8345: A YANG Data Model for Network Topologies";
  }
  import ietf-l3-unicast-topology {
    prefix "l3t";
    reference "RFC 8346: A YANG Data Model for Layer 3 Topologies";
  }
  import ietf-te-topology {
    prefix "tet";
    reference
      "I-D.ietf-teas-yang-te-topo: YANG Data Model for Traffic
       Engineering (TE) Topologies";
  }

  organization
    "IETF Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Igor Bryskin
               <mailto:Igor.Bryskin@huawei.com>

     Editor:   Vishnu Pavan Beeram
               <mailto:vbeeram@juniper.net>

     Editor:   Tarek Saad
               <mailto:tsaad@cisco.com>

     Editor:   Himanshu Shah
               <mailto:hshah@ciena.com>

     Editor:   Oscar Gonzalez De Dios
               <mailto:oscar.gonzalezdedios@telefonica.com>";

  description
    "YANG data model for representing and manipulating Layer 3 TE
     Topologies.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2019-06-28 {

    description
      "Initial revision";
    reference "RFC XXXX: YANG Data Model for Layer 3 TE Topologies";
  }

  grouping l3-te-topology-type {
    description
      "Identifies the L3 TE topology type.";
    container l3-te {
      presence "Indiates L3 TE Topology";
      description
        "Its presence identifies the L3 TE topology type.";
    }
  }

  augment "/nw:networks/nw:network/nw:network-types/"
    + "l3t:l3-unicast-topology" {
    description
      "Defines the L3 TE topology type.";
    uses l3-te-topology-type;
  }

  augment "/nw:networks/nw:network/l3t:l3-topology-attributes" {
    when "../nw:network-types/l3t:l3-unicast-topology/l3tet:l3-te" {
      description
        "Augment only for L3 TE topology";
    }
    description
      "Augment topology configuration";
    uses l3-te-topology-attributes;
  }

  augment "/nw:networks/nw:network/nw:node/l3t:l3-node-attributes" {
    when "../../nw:network-types/l3t:l3-unicast-topology/"
      + "l3tet:l3-te" {
      description
        "Augment only for L3 TE topology";
    }
    description
      "Augment node configuration";
    uses l3-te-node-attributes;
  }

  augment "/nw:networks/nw:network/nw:node/nt:termination-point/"
    + "l3t:l3-termination-point-attributes" {
    when "../../../nw:network-types/l3t:l3-unicast-topology/"
      + "l3tet:l3-te" {
      description
        "Augment only for L3 TE topology";
    }
    description
      "Augment termination point configuration";
    uses l3-te-tp-attributes;
  }

  augment "/nw:networks/nw:network/nt:link/l3t:l3-link-attributes" {
    when "../../nw:network-types/l3t:l3-unicast-topology/"
      + "l3tet:l3-te" {
      description
        "Augment only for L3 TE topology";
    }
    description
      "Augment link configuration";
    uses l3-te-link-attributes;
  }

  grouping l3-te-topology-attributes {
    description
      "L3 TE topology scope attributes";
    container l3-te-topology-attributes {
      must "/nw:networks/nw:network"
        + "[nw:network-id = current()/network-ref]/nw:network-types/"
        + "tet:te-topology" {
        error-message
          "The referenced network must be a TE topology.";
        description
          "The referenced network must be a TE topology.";
      }
      description
        "Containing TE topology references";
      uses nw:network-ref;
    } // l3-te-topology-attributes
  } // l3-te-topology-attributes

  grouping l3-te-node-attributes {
    description
      "L3 TE node scope attributes";
    container l3-te-node-attributes {
      must "/nw:networks/nw:network"
        + "[nw:network-id = current()/network-ref]/nw:network-types/"
        + "tet:te-topology" {
        error-message
          "The referenced network must be a TE topology.";
        description
          "The referenced network must be a TE topology.";
      }
      description
        "Containing TE node references";
      uses nw:node-ref;
    } // l3-te
  } // l3-te-node-attributes

  grouping l3-te-tp-attributes {
    description
      "L3 TE termination point scope attributes";
    container l3-te-tp-attributes {
      must "/nw:networks/nw:network"
        + "[nw:network-id = current()/network-ref]/nw:network-types/"
        + "tet:te-topology" {
        error-message
          "The referenced network must be a TE topology.";
        description
          "The referenced network must be a TE topology.";
      }
      description
        "Containing TE termination point references";
      uses nt:tp-ref;
    } // l3-te
  } // l3-te-tp-attributes

  grouping l3-te-link-attributes {
    description
      "L3 TE link scope attributes";
    container l3-te-link-attributes {
      must "/nw:networks/nw:network"
        + "[nw:network-id = current()/network-ref]/nw:network-types/"
        + "tet:te-topology" {
        error-message
          "The referenced network must be a TE topology.";
        description
          "The referenced network must be a TE topology.";
      }
      description
        "Containing TE link references";
      uses nt:link-ref;
    }
  } // l3-te-link-attributes
}
