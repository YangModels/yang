module ietf-detnet-qos {
     yang-version 1;
     namespace "urn:ietf:params:xml:ns:yang:ietf-detnet-qos";
     prefix detnet-qos;
         import ietf-inet-types{
       prefix "inet";
     }

     organization "IETF DetNet Working Group";
         contact
       "WG Web:   <http://tools.ietf.org/wg/detnet/>
        WG List:  <mailto: detnet@ietf.org>
        WG Chair: Lou Berger
                  <mailto:lberger@labn.net>
                  Janos Farkas
                  <janos.farkas@ericsson.com>
        Editor:   Quan Xiong
                  <mailto:xiong.quan@zte.com.cn>
        Editor:   Yufang Han
                  <mailto:han.yufang1@zte.com.cn>";

     description
       "This YANG module describes the Deterministic Networking (DetNet)
           Quality of Service (QoS) based on the Differentiated Services (DiffServ)
           model.";

     revision "2018-10-13" {
       description "initial revision";
       reference "RFC XXXX: draft-xiong-detnet-qos-yang-01";
     }

    typedef qos-phb-class {
     type enumeration {
      enum df {
        value 1 ;
        description "Default Forwarding for Best effort";
      }
      enum af1 {
        value 2 ;
        description "Assured forwarding class 1";
      }
      enum af2 {
        value 3 ;
        description "Assured forwarding class 2";
      }
      enum af3 {
        value 4 ;
        description "Assured forwarding class 3";
      }
      enum af4 {
        value 5 ;
        description "Assured forwarding class 4";
      }
      enum ef {
        value 6 ;
        description "Expedited forward";
      }
          enum cs6 {
        value 7 ;
        description "Internetwork control service class";
      }
      enum cs7 {
        value 8 ;
        description "Network control service class";
      }
      enum dn {
        value 9 ;
        description "DetNet forward";
      }
     }
         description
         "The PHB class including AF,EF,CS,DF,DN";
    }

    typedef detnet-policy-type {
          type enumeration {
            enum diffserv {
              value 1 ;
                  description "DiffServ Policy";
            }
          }
          description
         "The DetNet policy type.";
    }

    typedef detnet-classifier-type {
          type enumeration {
            enum ba {
              value 1 ;
                  description "DiffServ BA Classifier";
            }
                enum mf {
              value 2 ;
                  description "DiffServ MF Classifier";
            }
          }
          description
         "The DetNet classifier type including BA and MF.";
    }

        typedef detnet-action-type {
          type enumeration {
            enum meter {
              value 1 ;
                  description "DiffServ meter Action";
            }
            enum shaper {
              value 2 ;
                  description "DiffServ shaper Action";
            }
                enum dropper {
              value 3 ;
                  description "DiffServ dropper Action";
            }
                enum marker {
              value 4 ;
                  description "DiffServ marker Action";
            }
                enum order {
              value 5 ;
                  description "DiffServ order Action";
            }
                enum scheduler {
              value 6 ;
                  description "DiffServ scheduler Action";
            }
          }
          description
         "The DetNet classifier type including BA and MF.";
        }

        grouping mpls-tc {
        description "MPLS TC Information";
        leaf phb-class {
                    type qos-phb-class;
            description "Specify phb class of PHB info, support [a"
            + "f1,af2,af3,af4,be,ef,cs6,cs7,dn]";
        }
        leaf tc-value {
            type uint8 {
                range 0..7 {
                description "MPLS-TC value, support [0-7]";
                }
            }
            mandatory true ;
                        description "MPLS-TC value, support [0-7]";
            }
    }
        grouping ip-dscp {
        description "IP DSCP Information";
        leaf phb-class {
                    type qos-phb-class ;
            description "Specify server class of PHB info, support [a"
            + "f1,af2,af3,af4,be,ef,cs6,cs7,dn]";
        }
        leaf dscp-value {
            type uint8 {
                range 0..63 {
                description "IPv4/IPv6 DSCP value, support [0-63]";
                }
            }
            mandatory true ;
                        description "IPv4/IPv6 DSCP value, support [0-63]";
            }
    }

    grouping mpls-header-info {
        description "MPLS TC Information";
        leaf phb-class {
                    type qos-phb-class ;
            description "Specify phb class of PHB info, support [a"
            + "f1,af2,af3,af4,be,ef,cs6,cs7,dn]";
        }
        leaf tc-value {
            type uint8 {
                range 0..7 {
                description "MPLS-TC value, support [0-7]";
                }
            }
            mandatory true ;
                        description "MPLS-TC value, support [0-7]";
            }
                leaf s-label {
                    type uint32;
                    description "DetNet Flow ID value, support classifier MF";
                }
                list f-labels {
            key "f-label-id";
                        description "DetNet forwarding label id, support classifier MF";
                        leaf f-label-id {
                            type uint32;
                                description "DetNet forwarding label value, support classifier MF";
                        }
                }
    }

        grouping ipv4-header-info {
        description "IP DSCP Information";
        leaf phb-class {
                    type qos-phb-class ;
            description "Specify server class of PHB info, support [a"
            + "f1,af2,af3,af4,be,ef,cs6,cs7,dn]";
        }
        leaf dscp-value {
            type uint8 {
                range 0..63 {
                description "IPv4/IPv6 DSCP value, support [0-63]";
                }
            }
            mandatory true ;
                        description "IPv4/IPv6 DSCP value, support [0-63]";
            }
                leaf ipv4-source-address {
                        type inet:ipv4-address;
                    description "source address value, support classifier MF";
                }
                leaf ipv4-destination-address {
                        type inet:ipv4-address;
                    description "destination address value, support classifier MF";
                }
                leaf protocol-ID {
                    type uint8;
                    description "protocol ID, support classifier MF";
                }
                leaf source-port-numbers {
                    type inet:port-number;
                    description "source port numbers, support classifier MF";
                }
                leaf destination-port-numbers {
                    type inet:port-number;
                    description "destination port numbers, support classifier MF";
                }
    }

        grouping ipv6-header-info {
        description "IPv6 DSCP Information";
        leaf phb-class {
                    type qos-phb-class ;
            description "Specify server class of PHB info, support [a"
            + "f1,af2,af3,af4,be,ef,cs6,cs7,dn]";
        }
        leaf dscp-value {
            type uint8 {
                range 0..63 {
                description "IPv4/IPv6 DSCP value, support [0-63]";
                }
            }
            mandatory true ;
                        description "IPv4/IPv6 DSCP value, support [0-63]";
            }
                leaf ipv6-source-address {
                        type inet:ipv6-address;
                    description "source address value, support classifier MF";
                }
                leaf ipv6-destination-address {
                        type inet:ipv6-address;
                    description "destination address value, support classifier MF";
                }
                leaf protocol-ID {
                    type uint8;
                    description "protocol ID, support classifier MF";
                }
                leaf source-port-numbers {
                    type inet:port-number;
                    description "source port numbers, support classifier MF";
                }
                leaf destination-port-numbers {
                    type inet:port-number;
                    description "destination port numbers, support classifier MF";
                }
                leaf flow-label {
             type inet:ipv6-flow-label;
             description
               "The flow label of the header.";
        }
    }

    grouping detnet-classifiers {
        description "Configure the DetNet classifiers";
        choice classifier-type {
            description "Choice of classifiers types";
                        case ba {
                            description "BA classifier";
                                choice encapsulation-type {
                  description "Tunnel type includes: IP, MPLS.";
                  case MPLS {
                                    list mpls-ba {
                        key "tc-value";
                                            description "MPLS-TC be mapped to PHB";
                        uses mpls-tc;
                    }
                  }
                  case IP {
                    list ip-ba {
                        key "dscp-value";
                                            description "IPv4/IPv6 DSCP be mapped to PHB";
                        uses ip-dscp;
                                    }
                  }
                }
                        }
                        case mf {
                            description "MF classifier";
                                choice tunnel-type {
                  description
                     "Tunnel type includes: IPv4, IPv6, MPLS.";
                  case MPLS {
                                    list mpls-mf {
                        key "tc-value";
                                            description "MPLS-TC be mapped to PHB";
                        uses mpls-header-info;
                    }
                  }
                  case IPv4 {
                    list ipv4-mf {
                        key "dscp-value";
                                            description "IPv4 DSCP be mapped to PHB";
                        uses ipv4-header-info;
                                        }
                                  }
                  case IPv6 {
                    list ipv6-mf {
                        key "dscp-value";
                                            description "IPv6 DSCP be mapped to PHB";
                        uses ipv6-header-info;
                                        }
                                  }
                }
                        }
        }
    }

        grouping detnet-actions {
        description
          "DetNet Configuration about the actions";
        list detnet-action {
            key "detnet-action-type";
                        description "DetNet actions, to be defined.";
            leaf detnet-action-type {
              type detnet-action-type;
                          description "DetNet action types";
            }
            choice actions {
              description "Choice of action types";
                          case meter {
                            description "meter action";
              }
                          case marker {
                            description "marker action";
              }
                          case shaper {
                            description "shaper action";
              }
                          case dropper {
                            description "dropper action";
              }
                          case order {
                            description "order action";
              }
                          case scheduler {
                            description "scheduler action";
              }
            }
        }
    }

        container detnet-qos-policies {
        description "Configuration about DetNet QoS Policy";
        list detnet-policy-template {
                        key detnet-policy-name;
                        description "DetNet policy template";
                    leaf detnet-policy-name {
                           type string;
                           description "DetNet policy name";
            }
            leaf detnet-policy-type {
              type detnet-policy-type;
                          description "DetNet policy type";
            }
            list detnet-classifier-template {
                key detnet-classifier-name;
                                description "DetNet classifier template";
                leaf detnet-classifier-name {
                    type string;
                                        description "DetNet classifier name";
                }
                                leaf detnet-classifier-type {
                                        type detnet-classifier-type;
                                        description "DetNet classifier type";
                }
                        uses detnet-classifiers;
                                uses detnet-actions;
            }
            }
        }
}
