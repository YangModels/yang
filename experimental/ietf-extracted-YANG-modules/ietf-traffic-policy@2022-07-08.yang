module ietf-traffic-policy {
  yang-version 1.1;
  namespace "urn:ietf:params:xml:ns:yang:ietf-traffic-policy";
  prefix policy;

  import ietf-interfaces {
    prefix if;
  }
  import ietf-qos-action {
    prefix action;
  }

  organization
    "IETF Routing Area Working Group";

  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     configuring qos specification implementations.

     Copyright (c) 2021 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2022-07-08 {
    description
      "Initial version";
    reference
      "RFC XXXX: YANG Models for Quality of Service (QoS).";
  }
  feature policy-inline-classifier-config {
    description
      " This feature allows classifier configuration
        directly under policy.";
  }
  feature classifier-template-feature {
    description
       " This feature allows classifier as template configuration
         in a policy.";
  }
  identity policy-type {
    description
      "This base identity type defines policy-types";
  }
  identity diffserv {
    base policy-type;
    description
      "This defines ip policy-type";
  }
  identity ipv4-diffserv {
    base policy-type;
    description
      "This defines ipv4 policy-type";
  }
  identity ipv6-diffserv {
    base policy-type;
    description
      "This defines ipv6 policy-type";
  }

  identity filter-type {
    description
      "This is identity of base filter-type";
  }
  identity dscp {
    base filter-type;
    description
      "Differentiated services code point filter-type";
  }
  identity source-ipv4-prefix {
    base filter-type;
    description
      "source ipv4 prefix filter-type";
  }
  identity destination-ipv4-prefix {
    base filter-type;
    description
      "destination ipv4 prefix filter-type";
  }
  identity source-ipv6-prefix {
    base filter-type;
    description
      "source ipv6 prefix filter-type";
  }
  identity destination-ipv6-prefix {
    base filter-type;
    description
      "destination ipv6 prefix filter-type";
  }
  identity source-port {
    base filter-type;
    description
      "source port filter-type";
  }
  identity destination-port {
    base filter-type;
    description
      "destination port filter-type";
  }
  identity protocol {
    base filter-type;
    description
      "protocol type filter-type";
  }
  identity traffic-group-name {
    base filter-type;
    description
      "traffic-group filter type";
  }

  identity match-filter-operation {
    description
      "filter match logical operation type";
  }
  identity match-all-filter {
    base match-filter-operation;
    description
      "Classifier entry filter logical AND operation";
  }
  identity match-any-filter {
    base match-filter-operation;
    description
      "Classifier entry filter logical OR operation";
  }
  identity direction {
    description
      "This is identity of traffic direction";
  }
  identity inbound {
    base direction;
    description
      "Direction of traffic coming into the network entry";
  }
  identity outbound {
    base direction;
    description
      "Direction of traffic going out of the network entry";
  }
  grouping filters {
    description
      "Filters types in a Classifier entry";
    leaf type {
      type identityref {
        base filter-type;
      }
      description
        "This leaf defines type of the filter";
    }
    leaf logical-not {
      type boolean;
      description
        "This is logical-not operator for a filter. When true, it
         indicates filter looks for absence of a pattern defined
         by the filter.";
    }
  }
  grouping generic-classifier-attr {
    description
      "
       Classifier generic attributes like name,
       description, operation type
      ";
    leaf name {
      type string;
      description
        "classifier entry name";
    }
    leaf description {
      type string;
      description
        "classifier entry description statement";
    }
    leaf filter-operation {
      type identityref {
        base match-filter-operation;
      }
      default "match-all-filter";
      description
        "Filters are applicable as match-any or match-all filters";
    }
  }
  grouping inline-attr {
    description
      "attributes of inline classifier in a policy";
    leaf inline {
      type boolean;
      default "false";
      description
        "Indication of inline classifier entry";
    }
    leaf filter-operation {
      type identityref {
        base match-filter-operation;
      }
      default "match-all-filter";
      description
        "Filters are applicable as match-any or match-all filters";
    }
    list filter{
      if-feature policy-inline-classifier-config;
      must " ../inline = 'true' " {
        description
          "For inline filter configuration, inline attribute" +
          "must be true";
      }
      key "type logical-not";
      uses filters;
      description
        "Filters configured inline in a policy";
    }
  }
  grouping generic-policy-attr {
    description
      "Policy Attributes";
    leaf name {
      type string;
      description
        "policy name";
    }
    leaf type {
      type identityref {
        base policy-type;
      }
      description
        "policy type";
    }
    leaf description {
      type string;
      description
        "policy description";
    }
  }
  identity action-type {
    description
      "This base identity type defines action-types";
  }
  identity dscp-marking {
    base action-type;
    description
      "dscp marking action type";
  }
  identity meter-inline {
    base action-type;
    description
      "meter-inline action type";
  }
  identity meter-reference {
    base action-type;
    description
      "meter reference action type";
  }
  identity queue {
    base action-type;
    description
      "queue action type";
  }
  identity scheduler {
    base action-type;
    description
      "scheduler action type";
  }
  identity discard {
    base action-type;
    description
      "discard action type";
  }
  identity child-policy {
    if-feature action:child-policy-feature;
    base action-type;
    description
      "child-policy action type";
  }
  identity count {
    if-feature action:count-feature;
    base action-type;
    description
      "count action type";
  }
  identity named-counter {
    if-feature action:named-counter-feature;
    base action-type;
    description
      "name counter action type";
  }

  grouping classifier-action-entry {
    description
      "List of Configuration of classifier & associated actions";
    list action {
      key "type";
      ordered-by user;
      description
        "Configuration of classifier & associated actions";
      leaf type {
        type identityref {
          base action-type;
        }
        description
          "This defines action type ";
      }
      choice action-params {
        description
          "Choice of action types";
      }
    }
  }
  container classifiers {
    if-feature classifier-template-feature;
    description
      "list of classifier entry";
    list classifier{
      key "name";
      description
        "each classifier entry contains a list of filters";
      uses generic-classifier-attr;
      list filter {
        key "type logical-not";
        uses filters;
        description
          "Filter entry configuration";
      }
    }
  }
  container policies{
    description
      "list of policy templates";
    list policy{
      key "name type";
      description
        "policy template";
      uses generic-policy-attr;
      list classifier{
        key "name";
        ordered-by user;
        description
          "Classifier entry configuration in a policy";
        leaf name {
          type string;
          description
            "classifier entry name";
        }
        uses inline-attr;
        uses classifier-action-entry;
      }
    }
  }
  augment "/if:interfaces/if:interface" {
    description
      "Augments Diffserv Target Entry to Interface module";
    list qos-target-policy {
      key "direction type";
      description
        "policy target for inbound or outbound direction";
      leaf direction {
        type identityref {
          base direction;
        }
        description
          "Direction of the traffic flow either inbound or outbound";
      }
      leaf type {
        type identityref {
          base policy-type;
        }
        description
          "Policy entry type";
      }
      leaf name {
        type string;
        mandatory true;
        description
          "Policy name";
      }
    }
  }
}
