module acl {
    namespace "urn:cisco:params:xml:ns:yang:acl";
    // replace with IANA namespace when assigned
    prefix acl;

    import ietf-inet-types {
        prefix "inet";
    }

    import ietf-yang-types {
        prefix "yang";
    }

    organization
       "IETF NETMOD (NETCONF Data Modeling Language) Working Group";

    contact
    "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com";

    description
        "This YANG module defines a component that describing the
        configuration of Access Control Lists (ACLs).

        An ACL is an ordered set of rules and actions used to filter
        traffic.  Each set of rules and actions is represented
        as an Access Control Entries (ACE). Each ACE is evaluated
        sequentially. When the rule matches then action for that
        rule is applied to the packet.

        There are three types of ACL.

        IP ACLs - IP ACLs are ordered sets of rules that can use to
            filter traffic based on IP information in the Layer 3
            header of packets.
            The device applies IP ACLs only to IP traffic. IP ACL
            can be IPv4 or IPv6.
        MAC ACLs - MAC ACLs are used to filter traffic using the
            information in the Layer 2 header of each packet.
            MAC ACLs are by default only applied to non-IP
            traffic; however, Layer 2 interfaces can be configured
            to apply MAC ACLs to all traffic.
        ARP ACLs - The device applies ARP ACLs to IP traffic.

        This module should be used with acl-ip, acl-arp, or acl-mac
        depends on what feature the device supports.

        This YANG module also includes auxiliary definitions that
        are needed in conjunction with configuration of ACLs, such as
        reusable containers and references for ports and IP.

        Terms and Acronyms
         ACE (ace): Access Control Entry

         ACL (acl): Access Control List

         AFI (afi): Authority and Format Identifier (Address
             Field Identifier)

         ARP (arp): Address Resolution Protocol

         IP (ip): Internet Protocol

         IPv4 (ipv4):Internet Protocol Version 4

         IPv6 (ipv6): Internet Protocol Version 6

         MAC: Media Access Control

         TCP (tcp): Transmission Control Protocol

         TTL (ttl): Time to Live

         VLAN (vlan): Virtual Local Area Network
       ";

    revision 2012-08-31 {
        description "Initial revision. ";
    }

    feature host-by-name {
        description
            "The capability to reference a host by name.";
    }

    feature log-input {
        description
            "The ability to log messages upon the matching of ACLs.";
    }

    feature time-to-live {
        description "The ability to filter packets based on their
        time-to-live (TTL) value (0 to 255)";
        reference "ACL Support for Filtering on TTL Value";
    }

    feature ethertype-mask {
        description
            "The ability to fiter packets based on ether-type mask
            in hex 0x0-0xFFFF.";
    }

    feature flow-label {
        description
            "The ability to filter packets based on flow lable.
            The 20-bit Flow Label field in the IPv6 header
            is used by a source to label packets
            of a flow. This is an IPv6 ACEs option.";
        reference "RFC 3697 IPv6 Flow Label Specification";
    }

    feature match-counter {
        description
            "The ability to maintain global or local match statistics
            for each ACL ruels.";
    }

    feature port-group {
        description
            "The ability to define named groups for lists of ports. ";
    }
    feature ip-group-address {
        description
            "The ability to define named groups for lists of
            ip addresses. ";
    }
    feature arp-acl {
        description "The ability to support ARP ACLs.";

    }
    feature capture-session-id {
        description
            "The ability to configure ACL capture in order to
            selectively monitor traffic on an interface or VLAN.
            When the capture option for an ACL rule
            is enabled, packets that match this rule are
            either forwarded or dropped based on the specified permit
            or deny action and may also be copied to an alternate
            destination port for further analysis.
            An ACL rule with the capture option can be applied
            as follows:
                On a VLAN
                In the ingress direction on all interfaces
                In the egress direction on all Layer 3 interfaces
            The statistics data for the capture-session are capture
            in the device where the ACL rule applied to.";
    }

    feature packet-length {
        description "The ability to filter packets by packet length";
    }

    identity acl-type {
        description "Base acl type for all ACL";
    }

    identity mac-acl {
        base acl-type;
        description "layer 2 ACL type";
    }

    identity ip-acl {
        base "acl-type";
        description "layer 3 ACL type";
    }
    identity arp-acl {
        base "acl-type";
        description "ARP ACL type";
    }

    /* Types */

    typedef Comparator {
        description "A data type used to express comparator string";
        type enumeration {
            enum "eq" {
                value 0;
                description "match only equal to any giving number.";
            }
            enum "gt" {
                value 1;
                description
                    "match only greater than any giving number.";
            }
            enum "lt" {
                value 2;
                description
                    "match only lower than any giving number.";
            }
            enum "neq" {
                value 3;
                description
                    "match only not equal to any giving number";
            }
        }
    }

    typedef ACL-Action {
        description "An enumeration data type to express acl
            action when match.";
        type enumeration {
            enum permit {
                description "Apply permit action to the traffic";
            }
            enum deny {
                description "Apply deny action to the traffic";
            }
        }

    }

    typedef IP-Network-Kind {
        description "A enumeration to indicate the network to be
            expressed as an IP address and mask
            or simply identify a system as a host,
            or as a member of a pre-defined address group,
            or as any system.";
        type enumeration {
            enum ip {
                description "Used with address and mask couple
                    to express network.
                    ";
            }
            enum any {
                description "To express Any network or address.
                    Use the any keyword as an abbreviation
                    for an address and a mask of 0.0.0.0
                    255.255.255.255. For example:
                    0.0.0.0/255.255.255.255 means 'any'";
            }
            enum host {
                description "Used with host address to express a
                    single host
                    Use the host address(or name)
                    combination is the same as an address
                    and mask of address 0.0.0.0.
                    For example: '10.1.1.2/0.0.0.0' is the same
                    as 'host 10.1.1.2'";
            }
            enum group {
                description "Use the group keyword and group name
                    to refer to a pre-defined address object group
                    which is a list of address and mask.";
            }
        }
    }

    typedef MAC-Network-Kind {
        description
            "A enumeration data type to express the different ways
            to express network or address ";
        type enumeration {
            enum mac {
                description "Used with address and mask couple
                    to express network.";
            }
            enum any {
                description "To express Any network or address";
            }
            enum host {
                description " Use the host address
                    combination as an abbreviation for an address
                    and wildcard of address 0.0.0.0";
            }
        }
    }

    typedef Sequence-Number {
        description
            "An data type based on uint32 to determine the order
            in which the statements within the access list will
            be evaluated.";
        type uint32 {
            range "1..2147483646";
        }

    }

    typedef Remark {
        type string {
            length "0..100";
        }
    }

    typedef Acl-Type-Ref {
        description
            "This type is used to refer to an Access Control List
            (ACL) type";
        type identityref {
            base "acl-type";
        }
    }

    typedef Acl-Ref {
        description "This type refers to an ACL.";
        type leafref {
            path  "/acl:acls/acl:acl/acl:name";
        }
    }

    typedef Port-Group-Ref {
        description
            "This type is used to refer to a Portgroup object.";
        type leafref {
            path "/acls/port-obj-grp/port-group/name";
        }

    }

    typedef IP-Address-Group-Ref {
        description
            "This type is used to refer to a time range object.";
        type leafref {
            path "/acls/ip-address-obj-grp/ip-address-group/name";
        }
    }

    typedef Time-Range-Ref {
        description
            "This type is used to refer to a time range object.";
        type leafref {
            path "/acls/timerange-obj-grp/timerange-group/name";
        }

    }

    grouping PORT-GROUP {
        description
            "Using comparator and port, or port-upper and port-lower
            to specify a port range. ";
        choice port-number-or-range {
            case port-number-range {
                description
                    "Port group includes all ports between port-lower
                    and port-upper (including those)";
                leaf port-lower {
                    type inet:port-number;
                    description "Lower Port number.";
                    mandatory true;
                }
                leaf port-upper {
                    type inet:port-number;
                    description "Upper Port number.";
                    mandatory true;
                    must "../port-lower <= ../port-upper";
                }
            }
            case port-number {
                description
                    "Port group includes all ports that are greater
                    than, greater or equal, less than, less or equal,
                    or not equal the port, per the indicated
                    comparator.
                    It is possible for the port group to be empty
                    (for example, in case a port group that
                    is less than the minimum port number is
                    specified).";
                leaf comparator {
                    type Comparator;
                    mandatory true;
                }
                leaf port {
                    type inet:port-number;
                    description "Port number.";
                    mandatory true;
                }
            }
        }
    }

    /*
     * MAC-SOURCE-ADDRESS and MAC-DESTINATION-ADDRESS
     */
    grouping MAC-SOURCE-NETWORK {
        description "MAC address and mask pair for source.";
        leaf mac-source-kind {
            type MAC-Network-Kind ;
        }
        choice source-network {
            when "mac-source-kind != 'any'" ;
            case address {
                    when "mac-source-kind = 'mac'" ;
                leaf source-address {
                    type yang:mac-address;
                    mandatory true;
                    description "A source MAC address.";
                }
                leaf source-address-mask {
                    type yang:mac-address;
                    mandatory true;
                }
            }
           case host {
                when "mac-source-kind = 'host'" ;
                leaf source-host-name {
                    type inet:host;
                    mandatory true;
                }
            }
        }
    }

    grouping MAC-DESTINATION-NETWORK {
        description "MAC address and mask pair for destination.";
        leaf mac-dest-kind {
            type MAC-Network-Kind ;
        }
        choice dest-network {
            when "mac-dest-kind != 'any'" ;
            case address {
                    when "mac-dest-kind = 'mac'" ;
                leaf dest-address {
                    type yang:mac-address;
                    mandatory true;
                    description "A destination MAC address";
                }
                leaf dest-address-mask {
                    type yang:mac-address;
                    mandatory true;
                }
            }
           case host {
                when "mac-dest-kind = 'host'" ;
                leaf dest-host-name {
                    type inet:host;
                    mandatory true;
                }
            }
        }
    }

    grouping IP-ADDRESS-AND-MASK {
        description "Reusable IP address and mask pair.";
        leaf ip-address-kind {
            type IP-Network-Kind ;
        }
        choice mask-or-host {
            when "ip-address-kind != 'any'";
            case mask {
                when "ip-address-kind = 'ip'" ;
                leaf ip-address {
                    type inet:ip-address;
                }
                leaf ip-mask {
                    type inet:ip-prefix;
                    mandatory true;
                }
            }
            case host {
                when "ip-address-kind = 'host'";
                leaf ip-host-address {
                    type inet:host;
                    mandatory true;
                }
            }
        }

    }

    grouping IP-SOURCE-NETWORK {
        description "Reusable IP address and mask pair.";

        leaf ip-source-kind {
            type IP-Network-Kind ;
            mandatory true;
        }
        choice source-address-host-group {
            when "ip-source-kind != 'any'";
            case mask {
                when "ip-source-kind = 'ip'" ;
                leaf ip-source-address {
                    type inet:ip-address;
                }
                leaf ip-source-mask {
                    type inet:ip-prefix;
                    mandatory true;
                }
            }
            case host {
                when "ip-source-kind = 'host'";
                leaf ip-source-host-address {
                    type inet:host;
                    mandatory true;
                }
            }
            case group {
                when "ip-source-kind = 'group'";
                leaf ip-source-group  {
                    type IP-Address-Group-Ref;
                    mandatory true;
                }
                if-feature ip-group-address;
            }

        }
    }

    grouping IP-DESTINATION-NETWORK {
        description
            "Reusable IP address and mask pair for destination.";
        leaf ip-dest-kind {
            type IP-Network-Kind ;
            mandatory true;
        }
        choice dest-address-host-group {
            when "ip-dest-kind != 'any'";
            case mask {
                when "ip-dest-kind = 'ip'" ;
                leaf ip-dest-address {
                    type inet:ip-address;
                }
                leaf ip-dest-mask {
                    type inet:ip-prefix;
                }
            }
            case host-address {
                when "ip-dest-address = 'host'";
                leaf ip-dest-host-address {
                    type inet:host;
                }
            }
            case group {
                when "ip-dest-address = 'group'";
                leaf ip-dest-group {
                    type IP-Address-Group-Ref;
                }
            }
        }
    }

    container acls {
        description
            "This is the top container that contains a list of
            named ACL and reusable acl object groups.";
        list acl {
            key name;
            leaf name {
                description "ACL/access group name.";
                type string;
            }

            leaf acl-type {
                type Acl-Type-Ref;
                description "Type of ACL";
                mandatory true;
            }
            leaf enable-capture-global{
                type boolean;
                description "Enable packet capture on this filter
                    for this session. Session ID range is 1 to 48";
                default "false";
            }
            leaf capture-session-id-global {
                when "../enable-capture-global = 'true'";
                type uint32 {
                    range "1..48";
                }
                if-feature capture-session-id;
                description "Enable packet capture on this filter
                    for this session. Session ID range is 1 to 48";
            }
            choice enable-match-counter-choices {
                if-feature match-counter;
                case match {
                    leaf enable-match-counter {
                        type boolean;
                        description
                            "Eanble to collect statistics for the ACL";
                        default false;
                    }
                }
                case per-entry-match {
                    leaf enable-per-entry-match-counter {
                        type boolean;
                        description "Enable to collect match
                            statistics for each ACL entry(ACE).";
                        default false;
                    }
                }
            }

            leaf match {
                if-feature match-counter;
                config false;
                type uint64;
                description
                    "The total packet that have matched for the
                    particular access list";
            }
        }

        container port-obj-grp {
            list port-group { //CLI: object-group ip port foogroup
                key "name";
                leaf name {
                    type string;
                }
                container groups {
                    list groups {
                        key "sequence-num";
                        leaf sequence-num {
                            type Sequence-Number;
                        }
                        //unique "comparator port-number
                        //port-lower port-upper";
                        uses PORT-GROUP;
                    }
                }
            }

        }

        container timerange-obj-grp {
            description "Define time range entries to restrict
                the access. The time range is identified by a name
                and then referenced by a function, so that those
                time restrictions are imposed on the function itself.";
            list timerange-group {
                key "name";
                leaf name {
                    type string;
                    mandatory true;
                }
                container time-ranges {
                    list time-range {
                        key "sequence-num";
                        leaf sequence-num {
                            type Sequence-Number;
                            mandatory true;
                            description
                                "Sequence number. This number
                                determines the order of the statements
                                in the timerange list.
                                Range is 1 to 2147483646. ";
                        }

                        choice range-type {
                            case remark {
                                leaf remark {
                                    type string;
                                    description "The remark is the
                                        comments about each time range
                                        which is to make
                                        the time range entry easier for
                                        the network administrator to
                                        understand";
                                }
                            }
                            case absolute {
                                container absolute {
                                    description
                                        "Absolute time and date that
                                        the associated function starts
                                        going into effect.";
                                    leaf start {
                                        type yang:date-and-time;
                                        description "Absolute start
                                            time and date";
                                    }
                                    leaf end {
                                        type yang:date-and-time;
                                        description
                                            "Absolute end time and
                                            date";
                                    }

                                }
                            }
                            case periodic {
                                container periodic {
                                    description "To specify a periodic
                                        time and date.";
                                    leaf weekdays {
                                        type bits {
                                            bit Sunday {
                                                position 0;
                                            }
                                            bit Monday {
                                                position 1;
                                            }
                                            bit Tuesday {
                                                position 2;
                                            }
                                            bit Wednesday {
                                                position 3;
                                            }
                                            bit Thursday {
                                                position 4;
                                            }
                                            bit Friday {
                                                position 5;
                                            }
                                            bit Saturday {
                                                position 6;
                                            }
                                        }
                                    }
                                    leaf start {
                                        type yang:timestamp;
                                        description "Start time";
                                    }
                                    leaf end {
                                        type yang:timestamp;
                                        description "End time";
                                    }
                                }
                            }
                        }
                    }
                }
            }

        }
        container ip-address-obj-grp {
            description
                "This contains a list of named ip address group. Each
                group defines a range of address and mask pair.";
            list ip-address-group {
                key "name";
                leaf name {
                    type string;
                }
                leaf afi {
                    default "ipv4";
                    type inet:ip-version;
                    description "Address Field Identifier (AFI).";
                }
                container ip-addresses {
                    list ip-address {
                        key "sequence-num";
                        leaf sequence-num {
                            type Sequence-Number;
                            mandatory true;
                            description
                                "Sequence number. This number
                                determines the order of the statements
                                 in the timerange list. Range is 1 to
                                 2147483646. ";

                        }

                        uses IP-ADDRESS-AND-MASK ;
                        //unique "ip-address ip-mask";
                        //unique "ip-host-address";
                    }
                }
            }
        }
    }
    rpc reset-match-counter {
        description "This RPC is to reset the statistics for the
            ACL matches.
            When name is the only input, it
            clears ACL match statistics and individual
            ACE match statistics.
            When name and sequence-numer are both inputs, it clears
            the ACE match statistics.";
        input {
            leaf name {
                type string;
                mandatory true;
                description "This name is the acl name.";
            }
            leaf sequence-num {
                type Sequence-Number;
                description
                    "This number is the ACE sequence-num.";
            }
        }
    }

}
