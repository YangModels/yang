module bfd {
   namespace "urn:ietf:params:xml:ns:yang:bfd";
  prefix bfd;

  import ietf-management-oam {
    prefix goam;
  }
  import ietf-inet-types {
    prefix inet;
  }
  import ietf-interfaces {
    prefix if;
  }
  import ietf-yang-types {
    prefix yang;
  }

  revision 2014-08-30 {
    description
      "Initial revision.";
  }

  identity bfd {
    base bfd:technology-types;
    description
      "bfd type";
  }

  identity bfd {
    base moam:command-sub-type;
  }

  identity bfd-contiuity-check {
    base moam:command-sub-type;
  }

  identity bfd-connectity-verification {
    base moam:command-sub-type;
  }

  identity technology-sub-type {
    description
" In BFD, different encapsulation types such as IP/UDP, PW-ACH can be employed.
"technology-sub-type" further identifies the encapsulation type within the BFD.
Technology sub-type is defined as an identity type. This allows different
encapsulation types to augment BFD OAM YANG model to include encapsulation
type specific extensions without redefining common BFD definitions.
Instead of defining seperate models for each such encapsulation
we define technology sub type. Technology subtype is associated at MEG level"     }

augment "/gen-oam:domains/gen-oam:domain/gen-oam:MAs/gen-oam:MA " {
       leaf technology-sub-type {
         type identityref {
           base technology-sub-type;
         }
       }
     }

augment
"/gen-oam:domains/gen-oam:domain/gen-oam:MAs/gen-oam:MA/gen-oam:MEP/ gen-oam:session "{
list session-status {
         key " bfdsess-status ";
         leaf bfdsess-admin-status {
         type enumeration{
enum enabled(1);
enum disabled(2);
enum adminDown(3);
enum down(4);
};
       description
         " Denotes the desired operational status of the BFD session.

          A transition to enabled(1) will start the BFD state machine
          for the session.  The state machine will have an initial
          state of down(2).

          A transition to disabled(2) will stop the BFD state machine
          for the session.  The state machine may first transition to
          adminDown(1) prior to stopping.

          A transition to adminDown(3) will cause the BFD state
          machine to transition to adminDown(1) and will cause the
          session to remain in this state.

          A transition to down(4) will cause the BFD state machine
          to transition to down(2) and will cause the session to
          remain in this state";
         }
         leaf bfdsess-oper-status {
           type enumeration{
enum up(1);
enum down(2);
enum adminDown(3);
};
        description
         " Denotes the actual operational status of the BFD session.
          If the value of bfdOperStatus is down(2), this value MUST
          eventually be down(2) as well.  If the value of
          bfdOperStatus is adminDown(3), this value MUST eventually
          be adminDown(3) as well ";
         }
        leaf bfdsess-status {
           type uint32;
        description
         " Configured BFD session state ";
         }
        leaf bfdsess-remote-heard {
           type boolean;
        description
         " This leaf specifies the status of BFD packet reception from
          the remote system.  Specifically, it is set to true(1) if
          the local system is actively receiving BFD packets from the
          remote system and is set to false(2) if the local system
          has not received BFD packets recently (within the detection
          time) or if the local system is attempting to tear down
          the BFD session ";
         }
       }
     }
augment
"/gen-oam:domains/gen-oam:domain/gen-oam:MAs/gen-oam:MA/gen-oam:MEP / gen-oam:session " {
       list session-type {
         key " bfdsess-type ";
         leaf bfdsess-version-num {
           type uint32;
        description
         " The version number of the BFD protocol that this session
          is running in.  Write access is available for this object
          to provide the ability to set the desired version for this
          BFD session ";
         }
         leaf bfdsess-type {
           type uint32;
        description
         " This leaf specifies the type of this BFD session ";
         }
leaf bfdsess-oper-mode {
           type uint32;
        description
         " This object specifies the operational mode of this
          BFD session ";
         }
leaf bfdsess-demandmode-desired {
          type boolean;
        description
         " This leaf indicates the local system's
          desire to use Demand mode.  Specifically, it is set
          to true(1) if the local system wishes to use
          Demand mode or false(2) if not ";
         }
leaf bfdsess-controlplanel-indep {
          type boolean;
        description
         " This leaf indicates the local system's
          ability to continue to function through a disruption of
          the control plane.  Specifically, it is set
          to true(1) if the local system BFD implementation is
          independent of the control plane.  Otherwise, the
          value is set to false(2) ";
         }
leaf bfdsess-multi-point {
          type boolean;
        description
         " This leaf indicates the Multipoint (M) bit for this
          session.  It is set to true(1) if the Multipoint (M) bit is
          set to 1.  Otherwise, the value is set to false(2) ";
         }
leaf bfdsess-detect-mult {
          type uint32;
        description
         " This leaf specifies the Detect time multiplier ";
         }
leaf bfdsess-authpres {
          type boolean;
        description
         " This leaf indicates the local system's
          desire to use authentication.  Specifically, it is set
          to true(1) if the local system wishes the session
          to be authenticated or false(2) if not";
         }
leaf bfdsess-authentication-type {
          type uint32;
        description
         " The authentication type used for this BFD session.
          This field is valid only when the Authentication
          Present bit is set ";
         }
       }
     }

augment
"/gen-oam:domains/gen-oam:domain/gen-oam:MAs/gen-oam:MA/ gen-oam:context-id " {
       case context-id-bfdsess {
         leaf bfdsess-discriminator {
          type uint32;
        description
         " This leaf specifies the local discriminator for this BFD
          session, which is used to uniquely identify it ";
         }
leaf bfdsess-remotediscr {
          type uint32;
        description
         " This leaf specifies the session discriminator chosen
          by the remote system for this BFD session.  The value may
          be zero(0) if the remote discriminator is not yet known
          or if the session is in the down or adminDown(1) state ";
         }
leaf bfdsess-dismap-index{
          type uint32;
        description
         " This leaf specifies a mapping between a
local discriminator and a BFD session ";
}
       }
     }

augment
"/gen-oam:domains/gen-oam:domain/gen-oam:MAs/gen-oam:MA/gen-oam:MEP / gen-oam:session " {
       list bfdsess-authentication {
           key " bfdsess-authentication-keyid,bfdsess-authentication-key ";
           leaf bfdsess-authentication-keyid {
          type uint32;
        description
         " This leaf specifies the authentication key ID in use for this session.
          This object permits multiple keys to be active simultaneously.
          The value -1 indicates that no authentication key ID will
          be present in the optional BFD Authentication Section ";
         }
leaf bfdsess-authentication-key {
          type uint32;
        description
         " This leaf specifies the authentication key.  When the
          bfdSess-Authentication-Type is simplePassword(1), the value
          of this object is the password present in the BFD packets.
          When the bfdSess-Authentication-Type is one of the keyed
          authentication types, this value is used in the
          computation of the key present in the BFD authentication
          packet ";
         }
         }
}
augment
"/gen-oam:domains/gen-oam:domain/gen-oam:MAs/gen-oam:MA/gen-oam:MEP / gen-oam:session " {
       list bfd-addr-type {
           key " bfdSess-SrcAddr-Type,bfdSess-DstAddr-Type ";
           leaf bfdSess-SrcAddr-Type {
          description
         " This leaf specifies the IP address type of the source IP
          address of this BFD session.  The value of unknown(0) is
          allowed only when the session is singleHop(1) and the
          source IP address of this BFD session is derived from
          the outgoing interface, or when the BFD session is not
          associated with a specific interface.  If any other
          unsupported values are attempted in a set operation, the
          agent MUST return an inconsistentValue error ";
             type uint32;
           }
leaf bfdSess-DstAddr-Type {
          description
         " This leaf specifies the IP address type of the neighboring
          IP address that is being monitored with this BFD session.
          The value of unknown(0) is allowed only when the session is
          singleHop(1) and the outgoing interface is of type
          point to point, or when the BFD session is not associated
          with a specific interface.  If any other unsupported values
          are attempted in a set operation, the agent MUST return an
          inconsistentValue error ";
             type uint32;
           }

         }
}

augment
"/gen-oam:domains/gen-oam:domain/gen-oam:MAs/gen-oam:MA/gen-oam:MEP"{

           leaf bfdSess-Source-UdpPort {
          description
         " This leaf specifies the source UDP port number used
          for this BFD session's Control packets.  The value may be
          zero(0) if the session is in adminDown(1) state.  Upon
          creation of a new BFD session via this, the value of
          zero(0) specified would permit the implementation to
          choose its own source port number ";
             type uint32;
           }
leaf bfdSess-echoSrc-Udp{
          description
         " This leaf specifies the source UDP port number used for
          this BFD session's Echo packets.  The value may be zero(0)
          if the session is not running in the Echo mode, or the
          session is in adminDown(1) state.  Upon creation of a new
          BFD session via this, the value of zero(0) would
          permit the implementation to choose its own source port
          number ";
             type uint32;
           }
}

augment
"/gen-oam:domains/gen-oam:domain/gen-oam:MAs/gen-oam:MA/gen-oam:MEP/moam:session "{

           leaf bfdSess-Destination-UdpPort {
          description
         " This leaf specifies the destination UDP port number
          used for this BFD session's Control packets.  The value
          may be zero(0) if the session is in adminDown(1) state";
             type uint32;
           }
         }

augment
"/gen-oam:domains/gen-oam:domain/gen-oam:MAs/gen-oam:MA/gen-oam:MEP
/gen-oam:session/gen-oam:interval "  {
choice bfdSess-DesiredMinTx-Interval {
          description
         " This leaf specifies the minimum interval, in
          microseconds, that the local system would like to use
          when transmitting BFD Control packets.  The value of
          zero(0) is reserved in this case and should not be
          used ";
             type uint32;
           }
choice bfdSess-ReqMinRx-Interval {
          description
         " This leaf specifies the minimum interval, in
          microseconds, between received BFD Control packets the
          local system is capable of supporting.  The value of
          zero(0) can be specified when the transmitting system
          does not want the remote system to send any periodic BFD
          Control packets ";
             type uint32;
           }
choice bfdSess-ReqMinEchoRx-Interval {
          description
         " This leaf specifies the minimum interval, in
          microseconds, between received BFD Echo packets that this
          system is capable of supporting.  The value must be zero(0) if
          this is a multihop BFD session ";
             type uint32;
           }
choice bfdSess-Negotiated-Interval {
          description
         " This leaf specifies the negotiated interval, in
          microseconds, that the local system is transmitting
          BFD Control packets ";
             type uint32;
           }
choice bfdSess-NegotiatedEcho-Interval {
          description
         " This leaf specifies the negotiated interval, in
          microseconds, that the local system is transmitting
          BFD Echo packets.  The value is expected to be zero if
          the sessions are not running in Echo mode ";
             type uint32;
           }
     }

 augment "/gen-oam:cc/gen-oam:input " {
       leaf technology-sub-type {
         type identityref {
           base technology-sub-type;
         }
       }
     }

augment "/gen-oam:cc/gen-oam:input " {
list session-type{
       key " bfdsess-type ";
         leaf bfdsess-version-num {
           type uint32;
         }
         leaf bfdsess-type {
           type uint32;
         }
leaf bfdsess-oper-mode {
           type uint32;
         }
leaf bfdsess-demandmode-desired {
          type boolean;
         }
leaf bfdsess-controlplanel-indep {
          type boolean;
         }
leaf bfdsess-multi-point {
          type boolean;
         }
leaf bfdsess-detect-mult {
          type uint32;
         }
leaf bfdsess-authpres {
          type boolean;
         }
leaf bfdsess-authentication-type {
          type uint32;
         }
       }
     }

augment
"/gen-oam:cc/gen-oam:input " {
       list session-status {
       key " bfdsess-status "
         leaf bfdsess-admin-status {
           type enumeration{
enum enabled(1);
enum disabled(2);
enum adminDown(3);
enum down(4);
};
         }
         leaf bfdsess-oper-status {
           type enumeration{
enum up(1);
enum down(2);
enum adminDown(3);
};
         }
        leaf bfdsess-status {
           type uint32;
         }
        leaf bfdsess-remote-heard {
           type boolean;
         }
       }
     }

augment
"/gen-oam:cc/gen-oam:input "  {
choice context-id{
       case context-id-bfdsess {
         leaf bfdsess-discriminator {
          type uint32;
         }
leaf bfdsess-remotediscr {
          type uint32;
         }
leaf bfdsess-dismap-index {
          type uint32;
         }
       }
     }
}

augment
"/gen-oam:cc/gen-oam:input " {
       list bfdsess-authentication {
 key"bfdsess-authentication-keyid,bfdsess-authentication-key ";
           leaf bfdsess-authentication-keyid {
          type uint32;
         }
leaf bfdsess-authentication-key {
          type uint32;
         }
         }
}

augment
"/gen-oam:cc/gen-oam:input "  {

leaf bfdSess-SrcAddr-Type {
             type uint32;
           }
leaf bfdSess-DstAddr-Type {
             type uint32;
           }
         }
}

augment
"/gen-oam:cc/gen-oam:input " {
leaf bfdSess-Source-UdpPort{
             type uint32;
}
leaf bfdSess-echoSrc-Udp{
             type uint32;
           }
}
augment
"/gen-oam:cc/gen-oam:input " {
           leaf bfdSess-Destination-UdpPort {
             type uint32;
           }
}

augment
"/gen-oam:cc/gen-oam:input "{
       list session-interval {
           key " bfdSess-DesiredMinTx-Interval ";
 leaf bfdSess-DesiredMinTx-Interval {
             type uint32;
           }
leaf bfdSess-ReqMinRx-Interval {
             type uint32;
           }
leaf bfdSess-ReqMinEchoRx-Interval {
             type uint32;
           }
leaf bfdSess-Negotiated-Interval {
             type uint32;
           }
leaf bfdSess-NegotiatedEcho-Interval {
             type uint32;
           }
         }
     }

augment
"/gen-oam:cc/gen-oam:output " {

           leaf bfdSess-Source-UdpPort {
             type uint32;
           }
leaf bfdSess-echoSrc-Udp{
             type uint32;
           }
}
augment
"/gen-oam:cc/gen-oam:output " {
           leaf bfdSess-Destination-UdpPort {
             type uint32;
           }
}

augment
"/gen-oam:cc/gen-oam:output /gen-oam: maintenance-stats " {
case session-perform-bfd {
         leaf bfdSess-PerfCtrlPkt-In {
          type uint32;
        description
         " The total number of BFD control messages received for this
          BFD session";
         }
leaf bfdSess-PerfCtrlPkt-Out {
          type uint32;
        description
         " The total number of BFD control messages sent for this BFD
          session";
         }
leaf bfdSess-PerfCtrlPkt-Drop {
          type uint32;
        description
         " The total number of BFD control messages received for this
          session yet dropped for being invalid ";
         }
leaf bfdSess-PerfCtrlPktDrop-LastTime {
          type uint32;
        description
         " The value of sysUpTime on the most recent occasion at
          which received the BFD control message for this session was
          dropped.  If no such up event exists, this object contains
          a zero value ";
         }
leaf bfdSess-PerfEchoPkt-In {
          type uint32;
        description
         " The total number of BFD Echo messages received for this
          BFD session ";
         }
leaf bfdSess-PerfEchoPkt-Out {
          type uint32;
        description
         " The total number of BFD Echo messages sent for this BFD
          session ";
         }
leaf bfdSess-PerfEchoPkt-Drop {
          type uint32;
        description
         " The total number of BFD Echo messages received for this
          session yet dropped for being invalid ";
         }
leaf bfdSess-PerfEchoPktDrop-LastTime {
          type uint32;
        description
         " The value of sysUpTime on the most recent occasion at
          which received the BFD Echo message for this session was
          dropped.  If no such up event has been issued, this
          object contains a zero value ";
         }
leaf bfdSess-UpTime {
          type uint32;
        description
         "The value of sysUpTime on the most recent occasion at which
          the session came up.  If no such event has been issued,
          this object contains a zero value";
         }
leaf bfdSess-PerfLastSessDownTime {
          type uint32;
        description
         " The value of sysUpTime on the most recent occasion at
          which the last time communication was lost with the
          neighbor.  If no down event has been issued, this object
          contains a zero value ";
         }
leaf bfdSess-PerfLastCommLostDiag {
          type uint32;
        description
         " The BFD diag code for the last time communication was lost
          with the neighbor.  If such an event has not been issued,
          this object contains a zero value";
         }
leaf bfdSess-PerfSess-UpCount {
          type uint32;
        description
         " The number of times this session has gone into the Up
          state since the system last rebooted ";
         }
leaf bfdSess-Perf-DiscTime {
          type uint32;
        description
         " The value of sysUpTime on the most recent occasion at
          which any one or more of the session counters suffered
          a discontinuity ";
         }
       }
     }

     augment "/gen-oam:cv/gen-oam:input " {
       leaf technology-sub-type {
         type identityref {
           base technology-sub-type;
         }
       }
     }

augment "/gen-oam:cv/gen-oam:input " {
list session-type{
       key " bfdsess-type ";
         leaf bfdsess-version-num {
           type uint32;
         }
         leaf bfdsess-type {
           type uint32;
         }
leaf bfdsess-oper-mode {
           type uint32;
         }
leaf bfdsess-demandmode-desired {
          type boolean;
         }
leaf bfdsess-controlplanel-indep {
          type boolean;
         }
leaf bfdsess-multi-point {
          type boolean;
         }
leaf bfdsess-detect-mult {
          type uint32;
         }
leaf bfdsess-authpres {
          type boolean;
         }
leaf bfdsess-authentication-type {
          type uint32;
         }
       }
     }

augment
"/gen-oam:cv/gen-oam:input " {
       list session-status {
       key " bfdsess-status "
         leaf bfdsess-admin-status {
           type enumeration{
enum enabled(1);
enum disabled(2);
enum adminDown(3);
enum down(4);
};
         }
         leaf bfdsess-oper-status {
           type enumeration{
enum up(1);
enum down(2);
enum adminDown(3);
};
         }
        leaf bfdsess-status {
           type uint32;
         }
        leaf bfdsess-remote-heard {
           type boolean;
         }
       }
     }

augment
"/gen-oam:cv/gen-oam:input "  {
choice context-id{
       case context-id-bfdsess {
         leaf bfdsess-discriminator {
          type uint32;
         }
leaf bfdsess-remotediscr {
          type uint32;
         }
leaf bfdsess-dismap-index {
          type uint32;
         }
       }
     }
}

augment
"/gen-oam:cv/gen-oam:input " {
       list bfdsess-authentication {
 key"bfdsess-authentication-keyid,bfdsess-authentication-key ";
           leaf bfdsess-authentication-keyid {
          type uint32;
         }
leaf bfdsess-authentication-key {
          type uint32;
         }
         }
}

augment
"/gen-oam:cv/gen-oam:input "  {

leaf bfdSess-SrcAddr-Type {
             type uint32;
           }
leaf bfdSess-DstAddr-Type {
             type uint32;
           }
         }
}
