module ietf-commonaugment {
    yang-version 1.1;
    namespace "urn:ietf:params:xml:ns:yang:commonaugment";
    prefix commonaug;

    organization
       "IETF NETMOD (NETCONF Data Modeling Language) Working Group";

    contact
       "WG Web:   <http://tools.ietf.org/wg/netmod/>
        WG List:  <mailto:netmod@ietf.org>

        WG Chair: Lou Berger
                  <mailto:lberger@labn.net>

        WG Chair: Kent Watsen
                  <mailto:kwatsen@juniper.net>

        Editor:   Lyle Bertz
                  <mailto:lyleb551144@gmail.com>";

    description
    "This module contains YANG definition for
     common augments.

     Copyright (c) 2016 IETF Trust and the persons identified as the
     document authors. All rights reserved.

     This document is subject to BCP 78 and the IETF Trust's Legal
     Provisions Relating to IETF Documents
     (http://trustee.ietf.org/license-info) in effect on the date of
     publication of this document. Please review these documents
     carefully, as they describe your rights and restrictions with
     respect to this document. Code Components extracted from this
     document must include Simplified BSD License text as described
     in Section 4.e of the Trust Legal Provisions and are provided
     without warranty as described in the Simplified BSD License.";

    revision 2017-03-04 {
        description "Initial Revision.";
        reference "draft-bertz-netmod-commonaugment-00";
    }

    extension also-augments {
      argument "target-node";
      description
        "The argument is a string that identifies a node in the
        schema tree and is the same argument that is defined for
        the YANG argument statement";
    }
}
