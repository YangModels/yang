module ietf-network-slice-mapping {
  yang-version 1.1;
  namespace
    "urn:ietf:params:xml:ns:yang:ietf-network-slice-mapping";
  prefix ietf-nsm;

  import ietf-network {
    prefix nw;
    reference
      "RFC 8345: A YANG Data Model for Network Topologies";
  }
  import ietf-network-slice {
    prefix ietf-ns;
    reference
      "I-D.ietf-teas-ietf-network-slice-nbi-yang: IETF Network Slice
       Service YANG Model";
  }
  import ietf-te-service-mapping-types {
    prefix tsmt;
    reference
      "I-D.ietf-teas-te-service-mapping-yang: Traffic Engineering
       (TE) and Service Mapping YANG Data Model";
  }
  import ietf-l3vpn-ntw {
    prefix l3vpn-ntw;
    reference
      "RFC 9182: A YANG Network Data Model for Layer 3 VPNs";
  }
  import ietf-l2vpn-ntw {
    prefix l2vpn-ntw;
    reference
      "RFC 9291: A Layer 2 VPN Network YANG Model";
  }
  import ietf-nrp {
    prefix nrp;
    reference
      "I-D.wd-teas-nrp-yang: A YANG Data Model for Network
       Resource Partition (NRP)";
  }

  organization
    "IETF Traffic Engineering Architecture and Signaling (TEAS)
     Working Group";
  contact
    "WG Web:  <https://datatracker.ietf.org/wg/teas/>
     WG List:  <mailto:teas@ietf.org>
     Editor: Dhruv Dhody <dhruv.ietf@gmail.com>
             Bo Wu <lana.wubo@huawei.com>";
  description
    "This module contains a YANG module to map the IETF Network
     Slice with Traffic Engineering (TE) or VPN Network models.

     Copyright (c) 2023 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2023-03-12 {
    description
      "initial version.";
    reference
      "RFC XXXX: IETF Network Slice Service Mapping YANG Model";
  }

  identity map-to {
    description
      "Base identity from which specific map-to are derived.";
  }

  identity map-to-nrp {
    base map-to;
    description
      "Map to Network Resource Partition (NRP)";
  }

  identity map-to-vpn {
    base map-to;
    description
      "Map to VPN";
  }

  identity map-to-l3vpn {
    base map-to-vpn;
    description
      "Map to L3VPN";
  }

  identity map-to-l2vpn {
    base map-to-vpn;
    description
      "Map to L2VPN";
  }

  identity map-to-l1vpn {
    base map-to-vpn;
    description
      "Map to L1VPN";
  }

  identity map-to-te {
    base map-to;
    description
      "Map to TE directly";
  }

  grouping ns-mapping {
    description
      "Mapping between IETF network slice and Network
       Resource Partition (NRP)/VPN/TE";
    container ns-mapping {
      description
        "The container for the mapping";
      leaf map-to {
        type identityref {
          base map-to;
        }
        description
          "Mapping to NRP/VPN/TE";
      }
      choice map {
        description
          "Mapping to NRP/VPN/TE";
        case nrp {
          leaf nrp-id {
            type leafref {
              path "/nw:networks/nw:network"
                 + "/nrp:nrp/nrp:nrp-id";
            }
            description
              "A reference to NRP ID";
            reference
              "I-D.ietf-teas-ietf-network-slices: Framework
               for IETF Network Slices";
          }
        }
        case l3vpn {
          leaf l3vpn-id {
            type leafref {
              path "/l3vpn-ntw:l3vpn-ntw"
                 + "/l3vpn-ntw:vpn-services"
                 + "/l3vpn-ntw:vpn-service"
                 + "/l3vpn-ntw:vpn-id";
            }
            description
              "A reference to VPN ID";
          }
          leaf l3vpn-nrp-id {
            type leafref {
              path "/nw:networks/nw:network"
                 + "/nrp:nrp/nrp:nrp-id";
            }
            description
              "An optional reference to NRP ID";
            reference
              "I-D.ietf-teas-ietf-network-slices: Framework
               for IETF Network Slices";
          }
          description
            "Mapping to L3NM";
          reference
            "RFC9182: A YANG Network Data Model for
             Layer 3 VPNs";
        }
        case l2vpn {
          leaf l2vpn-id {
            type leafref {
              path "/l2vpn-ntw:l2vpn-ntw"
                 + "/l2vpn-ntw:vpn-services"
                 + "/l2vpn-ntw:vpn-service"
                 + "/l2vpn-ntw:vpn-id";
            }
            description
              "A reference to VPN ID";
          }
          leaf l2vpn-nrp-id {
            type leafref {
              path "/nw:networks/nw:network"
                 + "/nrp:nrp/nrp:nrp-id";
            }
            description
              "An optional reference to NRP ID";
            reference
              "I-D.ietf-teas-ietf-network-slices: Framework
               for IETF Network Slices";
          }
          description
            "Mapping to L2NM";
          reference
            "RFC 9291: A Layer 2 VPN Network YANG Model";
        }
        case te {
          uses tsmt:te-mapping;
          description
            "Mapping to TE directly";
          reference
            "I-D.ietf-teas-te-service-mapping-yang:
             Traffic Engineering (TE) and Service
             Mapping YANG Model";
        }
      }
    }
  }

  augment "/ietf-ns:network-slices/ietf-ns:network-slice" {
    description
      "IETF Network Slice augmented to include the mapping
       information to the network slice realization";
    container mapping {
      presence "Indicates Mapping information";
      description
        "Container to augment IETF network slice to
         include NRP / VPN / TE mappings";
      uses ns-mapping;
    }
  }
}
