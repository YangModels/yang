module ietf-ipfix {
  yang-version 1.1;

  namespace "urn:ietf:params:xml:ns:yang:ietf-ipfix";

  prefix ietf-ipfix;

  import ietf-inet-types {
    prefix inet;
    reference
      "RFC 6991: Common YANG Data Types";
  }

  import ietf-yang-types {
    prefix yang;
    reference
      "RFC 6991: Common YANG Data Types";
  }
  import ietf-interfaces {
    prefix if;
    reference
      "RFC 8343: A YANG Model for Interface Management";
  }

  organization
    "IETF";

  contact
    "Web:      TBD
     List:     TBD

     Editor:   Joey Boyd
               <mailto:joey.boyd@adtran.com>

     Editor:   Marta Seda
               <mailto:marta.seda@calix.com>";

  // RFC Ed.: replace XXXX with actual RFC numbers and
  // remove this note.

  description
    "This module contains a collection of YANG definitions for the
     management of IP Flow Information Export (IPFIX).

     This data model is designed for the Network Management Datastore
     Architecture defined in RFC 8342.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2019 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  revision 2020-03-05 {
    description
      "Initial revision.";
    reference
      "RFC XXXX: YANG Data Models for the IP Flow Information Export
                 (IPFIX) Protocol, Packet Sampling (PSAMP) Protocol,
                 and Bulk Data Export";
  }

  feature exporter {
    description
      "If supported, the Monitoring Device can be used as
       an Exporter. Exporting Processes can be configured.";
  }

  feature collector {
    description
      "If supported, the Monitoring Device can be used as
       a Collector.  Collecting Processes can be configured.";
  }

  feature tcp-transport {
    description
      "If supported, the Monitoring Device supports TCP
       as the transport protocol.";
  }

  feature udp-transport {
    description
      "If supported, the Monitoring Device supports UDP
       as the transport protocol.";
  }

  feature sctp-transport {
    description
      "If supported, the Monitoring Device supports SCTP
       as the transport protocol.";
  }

  feature file-reader {
    description
      "If supported, the Monitoring Device supports the
       configuration of Collecting Processes as File Readers.";
  }

  feature file-writer {
    description
      "If supported, the Monitoring Device supports the
       configuration of Exporting Processes as File Writers.";
  }

  feature if-mib {
    description
      "This feature indicates that the device implements
       the IF-MIB.";
    reference
      "RFC 2863: The Interfaces Group MIB";
  }

  identity export-mode {
    description
      "Base identity for different usages of export
       destinations configured for an Exporting Process.";
    reference
      "RFC 6615, Section 8 (ipfixExportMemberType)";
  }

  identity parallel {
    base export-mode;
    description
      "Parallel export of Data Records to all destinations configured
       for the Exporting Process.";
    reference
      "RFC 6615, Section 8 (ipfixExportMemberType)";
  }

  identity load-balancing {
    base export-mode;
    description
      "Load-balancing between the different destinations
       configured for the Exporting Process.";
    reference
      "RFC 6615, Section 8 (ipfixExportMemberType)";
  }

  identity fallback {
    base export-mode;
    description
      "Export to the primary destination (i.e., the first
       destination configured for the Exporting Process). If the
       export to the primary destination fails, the Exporting Process
       tries to export to the secondary destination.  If the
       secondary destination fails as well, it continues with the
       tertiary, etc.";
    reference
      "RFC 6615, Section 8 (ipfixExportMemberType)";
  }

  identity options-type {
    description
      "Base identity for report types exported with
       options templates.";
  }

  identity metering-statistics {
    base options-type;
    description
      "Metering Process Statistics.";
    reference
      "RFC 7011, Section 4.1";
  }

  identity metering-reliability {
    base options-type;
    description
      "Metering Process Reliability Statistics.";
    reference
      "RFC 7011, Section 4.2";
  }

  identity exporting-reliability {
    base options-type;
    description
      "Exporting Process Reliability Statistics.";
    reference
      "RFC 7011, Section 4.3";
  }

  identity flow-keys {
    base options-type;
    description
      "Flow Keys.";
    reference
      "RFC 7011, Section 4.4";
  }

  identity selection-sequence {
    base options-type;
    description
      "Selection Sequence and Selector Reports.";
    reference
      "RFC 5476, Sections 6.5.1 and 6.5.2";
  }

  identity selection-statistics {
    base options-type;
    description
      "Selection Sequence Statistics Report.";
    reference
      "RFC 5476, Sections 6.5.3";
  }

  identity accuracy {
    base options-type;
    description
      "Accuracy Report.";
    reference
      "RFC 5476, Section 6.5.4";
  }

  identity reducing-redundancy {
    base options-type;
    description
      "Enables the utilization of Options Templates to reduce
       redundancy in the exported Data Records.";
    reference
      "RFC 5473";
  }

  identity extended-type-information {
    base options-type;
    description
      "Export of extended type information for enterprise-specific
       Information Elements used in the exported Templates.";
    reference
      "RFC 5610";
  }

  typedef ie-name-type {
    type string {
      length "1..max";
      pattern '\S+';
    }
    description
      "Type for Information Element names. Whitespaces are not
       allowed.";
  }

  typedef name-type {
    type string {
      length "1..max";
      pattern '\S(.*\S)?';
    }
    description
      "Type for 'name' leafs, which are used to identify specific
       instances within lists, etc.

       Leading and trailing whitespaces are not allowed.";
  }

  typedef ie-id-type {
    type uint16 {
      range "1..32767";
    }
    description
      "Type for Information Element identifiers.";
  }

  typedef transport-session-status {
    type enumeration {
      enum "inactive" {
        value 0;
        description
          "This value MUST be used for Transport Sessions that are
           specified in the system but currently not active.

           The value can be used for Transport Sessions that are
           backup (secondary) sessions.";
      }
      enum "active" {
        value 1;
        description
          "This value MUST be used for Transport Sessions that are
           currently active and transmitting or receiving data.";
      }
      enum "unknown" {
        value 2;
        description
          "This value MUST be used if the status of the Transport
           Sessions cannot be detected by the device.

           This value should be avoided as far as possible.";
      }
    }
    description
      "Status of a Transport Session.";
    reference
      "RFC 6615, Section 8 (ipfixTransportSessionStatus)";
  }

  grouping transport-layer-security-parameters {
    description
      "TLS or DTLS parameters.";

    container transport-layer-security {
      presence
        "The presence of this container indicates TLS is enabled.";
      description
        "TLS or DTLS configuration.";

      leaf-list local-certification-authority-dn {
        type string;
        description
          "Distinguished names of certification authorities whose
           certificates may be used to identify the local endpoint.";
        reference
          "RFC 5280";
      }

      leaf-list local-subject-dn {
        type string;
        description
          "Distinguished names that may be used in the certificates
           to identify the local endpoint.";
        reference
          "RFC 5280.";
      }

      leaf-list local-subject-fqdn {
        type inet:domain-name;
        description
          "Fully qualified domain names that may be used in the
           certificates to identify the local endpoint.";
        reference
          "RFC 5280";
      }

      leaf-list remote-certification-authority-dn {
        type string;
        description
          "Distinguished names of certification authorities whose
           certificates are accepted to authorize remote endpoints.";
        reference
          "RFC 5280";
      }

      leaf-list remote-subject-dn {
        type string;
        description
          "Distinguished names which are accepted in certificates to
           authorize remote endpoints.";
        reference
          "RFC 5280";
      }

      leaf-list remote-subject-fqdn {
        type inet:domain-name;
        description
          "Fully qualified domain names that are accepted in
           certificates to authorize remote endpoints.";
        reference
          "RFC 5280";
      }
    }
  }

  grouping transport-session-state-parameters {
    description
      "State parameters of a Transport Session originating from an
       Exporting Process or terminating at a Collecting Process.
       Parameter names and semantics correspond to the managed
       objects in IPFIX-MIB.";
    reference
      "RFC 7011; RFC 6615, Section 8 (ipfixTransportSessionEntry,
       ipfixTransportSessionStatsEntry)";

    leaf ipfix-version {
      type uint16;
      description
        "Used for Exporting Processes, this parameter contains the
         version number of the IPFIX protocol that the Exporter uses
         to export its data in this Transport Session.

         Used for Collecting Processes, this parameter contains the
         version number of the IPFIX protocol it receives for this
         Transport Session. If IPFIX Messages of different IPFIX
         protocol versions are received, this parameter contains the
         maximum version number.

         Note that this parameter corresponds to
         ipfixTransportSessionIpfixVersion in the IPFIX MIB module.";
      reference
        "RFC 6615, Section 8
         (ipfixTransportSessionIpfixVersion)";
    }

    leaf source-address {
      type inet:host;
      description
        "The source address of the Exporter of the IPFIX Transport
         Session.";
      reference
        "RFC 6615, Section 8
         (ipfixTransportSessionSourceAddressType,
         ipfixTransportSessionSourceAddress);
         RFC 4960, Section 6.4";
    }

    leaf destination-address {
      type inet:host;
      description
        "The destination address of the path that is selected by the
         Exporter to send IPFIX messages to the Collector.

         In the case of TCP, it is possible that if an FQDN address
         is configured it resolves into many addresses.

         Note that this parameter functionally corresponds to
         ipfixTransportSessionDestinationAddressType and
         ipfixTransportSessionDestinationAddress in the IPFIX MIB
         module.";
      reference
        "RFC 6615, Section 8
         (ipfixTransportSessionDestinationAddressType,
         ipfixTransportSessionDestinationAddress);
         RFC 4960, Section 6.4";
    }

    leaf source-port {
      type inet:port-number;
      description
        "The transport-protocol port number of the Exporter of the
         IPFIX Transport Session.

         Note that this parameter corresponds to
         ipfixTransportSessionSourcePort in the IPFIX MIB module.";
      reference
        "RFC 6615, Section 8
         (ipfixTransportSessionSourcePort).";
    }

    leaf destination-port {
      type inet:port-number;
      description
        "The transport-protocol port number of the Collector of the
         IPFIX Transport Session.

         Note that this parameter corresponds to
         ipfixTransportSessionDestinationPort in the IPFIX MIB
         module.";
      reference
        "RFC 6615, Section 8
         (ipfixTransportSessionDestinationPort)";
    }

    leaf status {
      type transport-session-status;
      description
        "Status of the Transport Session.

         Note that this parameter corresponds to
         ipfixTransportSessionStatus in the IPFIX MIB module.";
        reference
         "RFC 6615, Section 8 (ipfixTransportSessionStatus)";
    }

    leaf rate {
      type yang:gauge32;
      units "bytes per second";
      description
        "The number of bytes per second transmitted by the
         Exporting Process or received by the Collecting Process.
         This parameter is updated every second.

         Note that this parameter corresponds to
         ipfixTransportSessionRate in the IPFIX MIB module.";
      reference
        "RFC 6615, Section 8 (ipfixTransportSessionRate)";
    }

    leaf bytes {
      type yang:counter64;
      units "bytes";
      description
        "The number of bytes transmitted by the Exporting Process or
         received by the Collecting Process.

         Discontinuities in the value of this counter can occur at
         re-initialization of the management system, and at other
         times as indicated by the value of
         transport-session-discontinuity-time.

         Note that this parameter corresponds to
         ipfixTransportSessionBytes in the IPFIX MIB module.";
      reference
        "RFC 6615, Section 8 (ipfixTransportSessionBytes)";
    }

    leaf messages {
       type yang:counter64;
       units "IPFIX Messages";
       description
         "The number of messages transmitted by the Exporting Process
          or received by the Collecting Process.

          Discontinuities in the value of this counter can occur at
          re-initialization of the management system, and at other
          times as indicated by the value of
          transport-session-discontinuity-time.

          Note that this parameter corresponds to
          ipfixTransportSessionMessages in the IPFIX MIB module.";
       reference
         "RFC 6615, Section 8
          (ipfixTransportSessionMessages)";
    }

    leaf discarded-messages {
      type yang:counter64;
      units "IPFIX Messages";
      description
        "Used for Exporting Processes, this parameter indicates the
         number of messages that could not be sent due to internal
         buffer overflows, network congestion, routing issues, etc.
         Used for Collecting Process, this parameter indicates the
         number of received IPFIX Message that are malformed, cannot
         be decoded, are received in the wrong order or are missing
         according to the sequence number.

         Discontinuities in the value of this counter can occur at
         re-initialization of the management system, and at other
         times as indicated by the value of
         transport-session-discontinuity-time.

         Note that this parameter corresponds to
         ipfixTransportSessionDiscardedMessages in the IPFIX MIB
         module.";
      reference
        "RFC 6615, Section 8
         (ipfixTransportSessionDiscardedMessages)";
    }

    leaf records {
      type yang:counter64;
      units "Data Records";
      description
        "The number of Data Records transmitted by the Exporting
         Process or received by the Collecting Process.

         Discontinuities in the value of this counter can occur at
         re-initialization of the management system, and at other
         times as indicated by the value of
         transport-session-discontinuity-time.

         Note that this parameter corresponds to
         ipfixTransportSessionRecords in the IPFIX MIB module.";
      reference
        "RFC 6615, Section 8
         (ipfixTransportSessionRecords)";
    }

    leaf templates {
      type yang:counter32;
      units "Templates";
      description
        "The number of Templates transmitted by the Exporting Process
         or received by the Collecting Process.

         Discontinuities in the value of this counter can occur at
         re-initialization of the management system, and at other
         times as indicated by the value of
         transport-session-discontinuity-time.

         Note that this parameter corresponds to
         ipfixTransportSessionTemplates in the IPFIX MIB module.";
      reference
        "RFC 6615, Section 8
        (ipfixTransportSessionTemplates)";
    }

    leaf options-templates {
      type yang:counter32;
      units "Options Templates";
      description
        "The number of Option Templates transmitted by the Exporting
         Process or received by the Collecting Process.

         Discontinuities in the value of this counter can occur at
         re-initialization of the management system, and at other
         times as indicated by the value of
         transport-session-discontinuity-time.

         Note that this parameter corresponds to
         ipfixTransportSessionOptionsTemplates in the IPFIX MIB
         module.";
      reference
        "RFC 6615, Section 8
         (ipfixTransportSessionOptionsTemplates)";
    }

    leaf transport-session-start-time {
      type yang:date-and-time;
      description
        "Timestamp of the start of the given Transport Session.

         This state parameter does not correspond to any object in
         the IPFIX MIB module.";
    }

    leaf transport-session-discontinuity-time {
      type yang:date-and-time;
      description
        "Timestamp of the most recent occasion at which one or more
         of the Transport Session counters suffered a discontinuity.

         Note that this parameter functionally corresponds to
         ipfixTransportSessionDiscontinuityTime in the IPFIX MIB
         module. In contrast to
         ipfixTransportSessionDiscontinuityTime, the time is
         absolute and not relative to sysUpTime.";
      reference
        "RFC 6615, Section 8
         (ipfixTransportSessionDiscontinuityTime)";
    }
  }

  grouping collection-template-state-parameters {
    description
      "State parameters of a (Options) Template received by a
       Collecting Process in a specific Transport Session or read by
       the File Reader.

       Parameter names and semantics correspond to the
       managed objects in IPFIX-MIB";
    reference
      "RFC 7011; RFC 6615, Section 8 (ipfixTemplateEntry,
       ipfixTemplateDefinitionEntry, ipfixTemplateStatsEntry)";

    list template {
      key "name";
      description
        "This list contains the Templates and Options Templates that
         are transmitted by the Exporting Process or received by the
         Collecting Process.

         Withdrawn or invalidated (Options) Templates MUST be removed
         from this list.";

      leaf name {
        type name-type;
        description
          "An arbitrary string which uniquely identifies the
           template.";
      }

      leaf observation-domain-id {
        type uint32;
        description
          "The ID of the Observation Domain for which this Template
           is defined.

           Note that this parameter corresponds to
           ipfixTemplateObservationDomainId in the IPFIX MIB
           module.";
        reference
          "RFC 6615, Section 8
           (ipfixTemplateObservationDomainId)";
      }

      leaf template-id {
        type uint16 {
          range "256..65535";
        }
        description
          "This number indicates the Template ID in the IPFIX
           message.

           Note that this parameter corresponds to ipfixTemplateId in
           the IPFIX MIB module.";
        reference
          "RFC 6615, Section 8 (ipfixTemplateId)";
      }

      leaf set-id {
        type uint16 {
          range "2..3 | 256..65535";
        }
        description
          "This number indicates the Set ID of the Template.
           A value of 2 is reserved for Template Sets.  A value of 3
           is reserved for Options Template Sets.  Values from 4 to
           255 are reserved for future use.  Values 256 and above
           are used for Data Sets.  The Set ID values of 0 and 1 are
           not used for historical reasons.

           Note that this parameter corresponds to ipfixTemplateSetId
           in the IPFIX MIB module.";
        reference
          "RFC 7011, Section 3.3.2;
           RFC 6615, Section 8 (ipfixTemplateSetId)";
      }

      leaf access-time {
        type yang:date-and-time;
        description
          "This parameter contains the time when this (Options)
           Template was last received from the Exporter or read from
           the file.

           Note that this parameter corresponds to
           ipfixTemplateAccessTime in the IPFIX MIB module.";
        reference
          "RFC 6615, Section 8 (
           ipfixTemplateAccessTime)";
      }

      leaf template-data-records {
        type yang:counter64;
        description
          "The number of received Data Records defined by this
           (Options) Template.

           Discontinuities in the value of this counter can occur at
           re-initialization of the management system, and at other
           times as indicated by the value of
           template-discontinuity-time.

           Note that this parameter corresponds to
           ipfixTemplateDataRecords in the IPFIX MIB module.";
        reference
          "RFC 6615, Section 8 (ipfixTemplateDataRecords)";
      }
      leaf template-discontinuity-time {
        type yang:date-and-time;
        description
          "Timestamp of the most recent occasion at which the counter
           template-data-records suffered a discontinuity.

           Note that this parameter functionally corresponds to
           ipfixTemplateDiscontinuityTime in the IPFIX MIB module. In
           contrast to  ipfixTemplateDiscontinuityTime, the time is
           absolute and not relative to sysUpTime.";
        reference
          "RFC 6615, Section 8
           (ipfixTemplateDiscontinuityTime)";
      }

      list field {
        key "name";
        description
          "This list contains the (Options) Template fields of which
           the (Options) Template is defined.

           The order of the list corresponds to the order of the
           fields in the (Option) Template Record.";

        leaf name {
          type name-type;
          description
            "An arbitrary string which uniquely identifies the
             template field.";
        }

        leaf ie-id {
          type ie-id-type;
          description
            "This parameter indicates the Information Element
             identifier of the field.

             Note that this parameter corresponds to
             ipfixTemplateDefinitionIeId in the IPFIX MIB module.";
          reference
            "RFC 7011; RFC 6615, Section 8
             (ipfixTemplateDefinitionIeId).";
        }

        leaf ie-length {
          type uint16;
          units "octets";
          description
            "This parameter indicates the length of the Information
             Element of the field.

             Note that this parameter corresponds to
             ipfixTemplateDefinitionIeLength in the IPFIX MIB
             module.";
          reference
            "RFC 7011; RFC 6615, Section 8
             (ipfixTemplateDefinitionIeLength)";
        }

        leaf ie-enterprise-number {
          type uint32;
          description
            "This parameter indicates the IANA enterprise number of
             the authority defining the Information Element
             identifier.

             If the Information Element is not enterprise-specific,
             this state parameter is zero.

             Note that this parameter corresponds to
             ipfixTemplateDefinitionIeEnterpriseNumber in the IPFIX
             MIB module.";
          reference
            "RFC 6615, Section 8
             (ipfixTemplateDefinitionIeEnterpriseNumber);
             IANA registry for Private Enterprise Numbers,
             http://www.iana.org/assignments/enterprise-numbers";
        }

        leaf is-flow-key {
          when "../../set-id = 2" {
            description
              "This parameter is available for non-Options Templates
               (Set ID is 2).";
          }
          type empty;
          description
            "If present, this is a Flow Key field.

             Note that this corresponds to flowKey(1) being set in
             ipfixTemplateDefinitionFlags.";
          reference
            "RFC 6615, Section 8
             (ipfixTemplateDefinitionFlags)";
        }

        leaf is-scope {
          when "../../set-id = 3" {
            description
              "This parameter is available for Options
               Templates (Set ID is 3).";
          }
          type empty;
          description
            "If present, this is a scope field.

             Note that this corresponds to scope(0) being set in
             ipfixTemplateDefinitionFlags.";
          reference
            "RFC 6615, Section 8
             (ipfixTemplateDefinitionFlags)";
        }
      }
    }
  }

  grouping common-collector-parameters {
    description
      "Parameters of a Collecting Process that are common to all
       transport protocols.";

    choice local-address-method {
      description
        "Method to configure the local address of the collecting
         process.  Note that it is expected that other methods be
         available.  Those method can augment this choice.";

      case local-address {
        leaf-list local-address {
          type inet:host;
          description
            "List of local addresses on which the Collecting
             Process listens for IPFIX Messages.";
        }
      }
    }

    leaf local-port {
      type inet:port-number;
      description
        "If not configured, the Monitoring Device uses the default
         port number for IPFIX, which is 4739 without TLS or DTLS and
         4740 if TLS or DTLS is activated.";
    }
  }

  grouping tcp-collector-parameters {
    description
      "Parameters of a listening TCP socket at a Collecting
       Process.";

    uses common-collector-parameters;

    uses transport-layer-security-parameters;
  }

  grouping udp-collector-parameters {
    description
      "Parameters of a listening UDP socket at a Collecting
       Process.";

    uses common-collector-parameters;

    leaf template-life-time {
      type uint32;
      units seconds;
      default 1800;
      description
        "Sets the lifetime of Templates for all UDP Transport
         Sessions terminating at this UDP socket. Templates that are
         not received again within the configured lifetime become
         invalid at the Collecting Process.

         As specified in RFC 7011, the Template lifetime MUST be at
         least three times higher than the template-refresh-timeout
         parameter value configured on the corresponding Exporting
         Processes.

         Note that this parameter corresponds to
         ipfixTransportSessionTemplateRefreshTimeout in the IPFIX
         MIB module.";
      reference
        "RFC 7011, Section 10.3.7; RFC 6615, Section 8
         (ipfixTransportSessionTemplateRefreshTimeout).";
    }

    leaf options-template-life-time {
      type uint32;
      units seconds;
      default 1800;
      description
        "Sets the lifetime of Options Templates for all UDP Transport
         Sessions terminating at this UDP socket. Options Templates
         that are not received again within the configured lifetime
         become invalid at the Collecting Process.

         As specified in RFC 7011, the Options Template lifetime MUST
         be at least three times higher than the
         options-template-refresh-timeout parameter value configured
         on the corresponding Exporting Processes.

         Note that this parameter corresponds to
         ipfixTransportSessionOptionsTemplateRefreshTimeout in the
         IPFIX MIB module.";
      reference
        "RFC 7011, Section 8.4; RFC 6615, Section 8
         (ipfixTransportSessionOptionsTemplateRefreshTimeout).";
    }

    leaf template-life-packet {
      type uint32;
      units "IPFIX Messages";
      description
        "If this parameter is configured, Templates defined in a UDP
         Transport Session become invalid if they are neither
         included in a sequence of more than this number of IPFIX
         Messages nor received again within the period of time
         specified by template-life-time.

         Note that this parameter corresponds to
         ipfixTransportSessionTemplateRefreshPacket in the IPFIX
         MIB module.";
      reference
        "RFC 7011, Section 8.4; RFC 6615, Section 8
         (ipfixTransportSessionTemplateRefreshPacket).";
    }

    leaf options-template-life-packet {
      type uint32;
      units "IPFIX Messages";
      description
        "If this parameter is configured, Options Templates defined
         in a UDP Transport Session become invalid if they are
         neither included in a sequence of more than this number of
         IPFIX Messages nor received again within the period of time
         specified by options-template-life-time.

         Note that this parameter corresponds to
         ipfixTransportSessionOptionsTemplateRefreshPacket in the
         IPFIX MIB module.";
      reference
        "RFC 7011, Section 8.4; RFC 6615, Section 8
         (ipfixTransportSessionOptionsTemplateRefreshPacket).";
    }

    leaf maximum-reordering-delay {
      type uint32;
      units seconds;
      description
        "The maximum delay for the template to be received at the
         collector after the data record(s) has(have) been received.
         The collector is expected to buffer the data records till
         such a time.";
      reference
        "RFC 7011, Section 8.2";
    }

    uses transport-layer-security-parameters;
  }

  grouping sctp-collector-parameters {
    description
      "Parameters of a listening SCTP socket at a Collecting
       Process.";

    uses common-collector-parameters;

    leaf maximum-reordering-delay {
      type uint32;
      units seconds;
      description
        "The maximum delay for the template to be received at the
         collector after the data record(s) has(have) been received.
         The collector is expected to buffer the data records till
         such a time.";
      reference
        "RFC 7011, Section 8.2";
    }

    uses transport-layer-security-parameters;
  }

  grouping file-reader-state-parameters {
    description
      "State Parameters for the File Reader.";

    container file-reader-state {
      config false;
      description
        "File Reader parameters.";

      leaf bytes {
        type yang:counter64;
        units octets;
        description
          "The number of bytes read by the File Reader.

           Discontinuities in the value of this counter can occur at
           re-initialization of the management system, and at other
           times as indicated by the value of
           file-reader-discontinuity-time.";
      }

      leaf messages {
        type yang:counter64;
        units "IPFIX Messages";
        description
          "The number of IPFIX Messages read by the File Reader.

           Discontinuities in the value of this counter can occur at
           re-initialization of the management system, and at other
           times as indicated by the value of
           file-reader-discontinuity-time.";
      }

      leaf records {
        type yang:counter64;
        units "Data Records";
        description
          "The number of Data Records read by the File Reader.

           Discontinuities in the value of this counter can occur at
           re-initialization of the management system, and at other
           times as indicated by the value of
           file-reader-discontinuity-time.";
      }

      leaf templates {
        type yang:counter32;
        units "Templates";
        description
          "The number of Template Records (excluding Options Template
           Records) read by the File Reader.

           Discontinuities in the value of this counter can occur at
           re-initialization of the management system, and at other
           times as indicated by the value of
           file-reader-discontinuity-time.";
      }

      leaf options-templates {
        type yang:counter32;
        units "Options Templates";
        description
          "The number of Options Template Records read by the File
           Reader.

           Discontinuities in the value of this counter can occur at
           re-initialization of the management system, and at other
           times as indicated by the value of
           file-reader-discontinuity-time.";
      }

      leaf file-reader-discontinuity-time {
        type yang:date-and-time;
        description
          "Timestamp of the most recent occasion at which one or more
           File Reader counters suffered a discontinuity.

           In contrast to discontinuity times in the IPFIX MIB
           module, the time is absolute and not relative to
           sysUpTime.";
      }

      uses collection-template-state-parameters;
    }
  }

  grouping collecting-process-parameters {
    description
      "Parameters of a Collecting Process.";

    list tcp-collector {
      if-feature tcp-transport;
      key "name";
      description
        "List of TCP receivers (sockets) on which the Collecting
         Process receives IPFIX Messages.";

      leaf name {
        type name-type;
        description
          "An arbitrary string which uniquely identifies the TCP
           collector.";
      }

      uses tcp-collector-parameters;

      list transport-session {
        key name;
        config false;
        description
          "This list contains the currently established Transport
           Sessions terminating at the given socket.";

        leaf name {
          type name-type;
          description
            "An arbitrary string which uniquely identifies the
             transport session.";
        }

        uses transport-session-state-parameters;
        uses collection-template-state-parameters;
      }
    }

    list udp-collector {
      if-feature udp-transport;
      key "name";
      description
        "List of UDP receivers (sockets) on which the Collecting
         Process receives IPFIX Messages.";

      leaf name {
        type name-type;
        description
          "An arbitrary string which uniquely identifies the UDP
           Collector.";
      }

      uses udp-collector-parameters;

      list transport-session {
        key name;
        config false;
        description
          "This list contains the currently established Transport
           Sessions terminating at the given socket.";

        leaf name {
          type name-type;
          description
            "An arbitrary string which uniquely identifies the
             transport session.";
        }

        uses transport-session-state-parameters;
        uses collection-template-state-parameters;
      }
    }

    list sctp-collector {
      if-feature sctp-transport;
      key "name";
      description
        "List of SCTP receivers on which the Collecting Process
         receives IPFIX Messages.";

      leaf name {
        type name-type;
        description
          "An arbitrary string which uniquely identifies the SCTP
           Collector.";
      }

      uses sctp-collector-parameters;

      list transport-session {
        key name;
        config false;
        description
          "This list contains the currently established Transport
           Sessions terminating at the given socket.";

        leaf name {
          type name-type;
          description
            "An arbitrary string which uniquely identifies the
             transport session.";
        }

        leaf sctp-association-id {
          type uint32;
          config false;
          description
            "The association ID used for the SCTP session between the
             Exporter and the Collector of the IPFIX Transport
             Session.  It is equal to the sctpAssocId entry in the
             sctpAssocTable defined in the SCTP-MIB.
             This parameter is only available if the transport
             protocol is SCTP and if an SNMP agent on the same
             Monitoring Device enables access to the corresponding
             MIB objects in the sctpAssocTable.

             Note that this parameter corresponds to
             ipfixTransportSessionSctpAssocId in the IPFIX MIB
             module.";
          reference
            "RFC 6615, Section 8
             (ipfixTransportSessionSctpAssocId);
             RFC 3871";
        }

        uses transport-session-state-parameters;
        uses collection-template-state-parameters;
      }
    }

    list file-reader {
      if-feature file-reader;
      key "name";
      description
        "List of File Readers from which the Collecting Process reads
         the IPFIX Messages.";

      leaf name {
        type name-type;
        description
          "An arbitrary string which uniquely identifies the File
           Reader.";
      }

      leaf file {
        type inet:uri;
        mandatory true;
        description
          "URI specifying the location of the file.";
      }

      uses file-reader-state-parameters;
    }
  }

  grouping export-template-state-parameters {
    description
      "State parameters of a (Options) Template used by an Exporting
       Process in a specific Transport Session or by a File Writer.
       Parameter names and semantics correspond to the managed
       objects in IPFIX-MIB.";
    reference
      "RFC 7011; RFC 6615, Section 8 (ipfixTemplateEntry,
       ipfixTemplateDefinitionEntry, ipfixTemplateStatsEntry)";

    list template {
      key "name";
      description
        "This list contains the Templates and Options Templates that
         are transmitted by the Exporting Process or written by the
         File Writer.

         Withdrawn or invalidated (Options) Templates MUST be removed
         from this list.";

      leaf name {
        type name-type;
        description
          "An arbitrary string which uniquely identifies the
           template.";
      }

      leaf observation-domain-id {
        type uint32;
        description
          "The ID of the Observation Domain for which this Template
           is defined.

           Note that this parameter corresponds to
           ipfixTemplateObservationDomainId in the IPFIX MIB
           module.";
        reference
          "RFC 6615, Section 8
           (ipfixTemplateObservationDomainId).";
      }

      leaf template-id {
        type uint16 {
          range "256..65535";
        }
        description
          "This number indicates the Template ID in the IPFIX
           message.

           Note that this parameter corresponds to ipfixTemplateId in
           the IPFIX MIB module.";
        reference
          "RFC 6615, Section 8 (ipfixTemplateId).";
      }

      leaf set-id {
        type uint16 {
          range "2..3 | 256..65535";
        }
        description
          "This number indicates the Set ID of the Template.
           A value of 2 is reserved for Template Sets.  A value of 3
           is reserved for Options Template Sets.  Values from 4 to
           255 are reserved for future use.  Values 256 and above
           are used for Data Sets.  The Set ID values of 0 and 1 are
           not used for historical reasons.

           Note that this parameter corresponds to ipfixTemplateSetId
           in the IPFIX MIB module.";
        reference
          "RFC 7011, Section 3.3.2;
           RFC 6615, Section 8 (ipfixTemplateSetId)";
      }

      leaf access-time {
        type yang:date-and-time;
        description
          "This parameter contains the time when this (Options)
           Template was last sent to the Collector(s) or written to
           the file.

           Note that this parameter corresponds to
           ipfixTemplateAccessTime in the IPFIX MIB module.";
        reference
          "RFC 6615, Section 8 (
           ipfixTemplateAccessTime).";
      }

      leaf template-data-records {
        type yang:counter64;
        description
          "The number of transmitted Data Records defined by this
           (Options) Template.

           Discontinuities in the value of this counter can occur at
           re-initialization of the management system, and at other
           times as indicated by the value of
           template-discontinuity-time.

           Note that this parameter corresponds to
           ipfixTemplateDataRecords in the IPFIX MIB module.";
        reference
          "RFC 6615, Section 8 (ipfixTemplateDataRecords).";
      }

      leaf template-discontinuity-time {
        type yang:date-and-time;
        description
          "Timestamp of the most recent occasion at which the counter
           template-data-records suffered a discontinuity.

           Note that this parameter functionally
           corresponds to ipfixTemplateDiscontinuityTime in the IPFIX
           MIB module. In contrast to
           ipfixTemplateDiscontinuityTime, the time is absolute and
           not relative to sysUpTime.";
        reference
          "RFC 6615, Section 8
           (ipfixTemplateDiscontinuityTime).";
      }

      list field {
        key "name";
        description
          "This list contains the (Options) Template fields of which
           the (Options) Template is defined.

           The order of the list corresponds to the order
           of the fields in the (Option) Template Record.";

        leaf name {
          type name-type;
          description
            "An arbitrary string which uniquely identifies the
             template field.";
        }

        leaf ie-id {
          type ie-id-type;
          description
            "This parameter indicates the Information Element
             identifier of the field.

             Note that this parameter corresponds to
             ipfixTemplateDefinitionIeId in the IPFIX MIB module.";
          reference
            "RFC 7011; RFC 6615, Section 8
             (ipfixTemplateDefinitionIeId).";
        }

        leaf ie-length {
          type uint16;
          units "octets";
          description
            "This parameter indicates the length of the Information
             Element of the field.

             Note that this parameter corresponds to
             ipfixTemplateDefinitionIeLength in the IPFIX MIB
             module.";
          reference
            "RFC 7011; RFC 6615, Section 8
             (ipfixTemplateDefinitionIeLength).";
        }

        leaf ie-enterprise-number {
          type uint32;
          description
            "This parameter indicates the IANA enterprise number of
             the authority defining the Information Element
             identifier.

             If the Information Element is not enterprise-specific,
             this state parameter is zero.

             Note that this parameter corresponds to
             ipfixTemplateDefinitionIeEnterpriseNumber in the IPFIX
             MIB module.";
          reference
            "RFC 6615, Section 8
             (ipfixTemplateDefinitionIeEnterpriseNumber);
             IANA registry for Private Enterprise Numbers,
             http://www.iana.org/assignments/enterprise-numbers.";
        }

        leaf is-flow-key {
          when "../../set-id = 2" {
          description
            "This parameter is available for non-Options Templates
             (Set ID is 2).";
          }
          type empty;
          description
            "If present, this is a Flow Key field.

             Note that this corresponds to flowKey(1) being set in
             ipfixTemplateDefinitionFlags.";
          reference
            "RFC 6615, Section 8
             (ipfixTemplateDefinitionFlags).";
        }

        leaf is-scope {
          when "../../set-id = 3" {
          description
            "This parameter is available for Options Templates
             (Set ID is 3).";
          }
          type empty;
          description
            "If present, this is a scope field.

             Note that this corresponds to scope(0) being set in
             ipfixTemplateDefinitionFlags.";
          reference
            "RFC 6615, Section 8
             (ipfixTemplateDefinitionFlags).";
        }
      }
    }
  }

  grouping common-exporter-parameters {
    description
      "Parameters of an export destination that are common to all
       transport protocols.";

    leaf ipfix-version {
      type uint16;
      default '10';
      description
        "IPFIX version number.";
      reference
        "RFC 7011.";
    }

    container source {
      description
        "Configuration corresponding to how exporter's source IP
         address is specified.";

      choice source-method {
        description
          "Method to configure the source address of the exporter
           or the interface to be used by the exporter.

           Note that it is expected that other methods be available.
           Those methods can augment this choice.";

        case interface-ref {
          leaf interface-ref {
            type if:interface-ref;
            description
              "The interface to be used by the Exporting Process.";
          }
        }

        case if-index {
          if-feature if-mib;
          leaf if-index {
            type uint32;
            description
              "Index of an interface as stored in the ifTable
               of IF-MIB.";
            reference
              "RFC 2863.";
          }
        }

        case if-name {
          if-feature if-mib;
          leaf if-name {
            type string;
            description
              "Name of an interface as stored in the ifTable
               of IF-MIB.";
            reference
              "RFC 2863.";
          }
        }
      }
    }

    container destination {
      description
        "Configuration corresponding to how exporter's destination IP
         address is specified.";
    }

    leaf destination-port {
      type inet:port-number;
      description
        "If not configured by the user, the Monitoring Device uses
         the default port number for IPFIX, which is 4739 without TLS
         or DTLS and 4740 if TLS or DTLS is activated.";
    }

    leaf send-buffer-size {
      type uint32;
      units "bytes";
      description
        "Size of the socket send buffer.

         If not configured by the user, this parameter is set by
         the Monitoring Device.";
    }

    leaf rate-limit {
      type uint32;
      units "bytes per second";
      description
        "Maximum number of bytes per second the Exporting Process may
         export to the given destination.  The number of bytes is
         calculated from the lengths of the IPFIX Messages exported.
         If not configured, no rate limiting is performed.";
      reference
        "RFC 5476, Section 6.3.";
    }
  }

  grouping tcp-exporter-parameters {
    description
      "Parameters of a TCP export destination.";

    uses common-exporter-parameters {
      augment "source/source-method" {
        description
          "Augment the source method to add the source IP address or
           hostname.";

        case source-address {
          leaf source-address {
            type inet:host;
            description
              "The source IP address or hostname used by the
               Exporting Process.";
          }
        }
      }

      augment "destination" {
        description
          "Augment the destination method to add the destination
           IP address or hostname.";

        choice destination-method {
          mandatory true;
          description
            "Method to configuring the destination address of the
             Collection Process to which IPFIX Messages are sent.

             Note it is expected that if other methods are available
             that they would augment from this statement.";

          case destination-address {
            leaf destination-address {
              type inet:host;
              description
                "The destination IP address or hostname of the
                 Collecting Process to which IPFIX Messages are sent.
                 A hostname may resolve to one or more IP
                 addresses.";
            }
          }
        }
      }
    }

    leaf connection-timeout {
      type uint32;
      units seconds;
      description
        "Time after which the exporting process deems the TCP
         connection to have failed.";
      reference
        "RFC 7011, Sections 10.4.4 and 10.4.5.";
    }

    leaf retry-schedule {
      type uint32 {
      range "60..max";
      }
      units seconds;
      description
        "Time after which the exporting process retries the TCP
         connection to a collector.";
      reference
        "RFC 7011, Section 10.4.4.";
    }

    uses transport-layer-security-parameters;
  }

  grouping udp-exporter-parameters {
    description
      "Parameters of a UDP export destination.";

    uses common-exporter-parameters {
      augment "source/source-method" {
        description
          "Augment the source method to add the source IP address or
           hostname.";

        case source-address {
          leaf source-address {
            type inet:host;
            description
              "The source IP address or hostname used by the
               Exporting Process.";
          }
        }
      }

      augment "destination" {
        description
          "Augment the destination method to add the destination
           IP address or hostname.";

        choice destination-method {
          mandatory true;
          description
            "Method to configuring the destination address of the
             Collection Process to which IPFIX Messages are sent.

             Note it is expected that if other methods are available
             that they would augment from this statement.";

          case destination-address {
            leaf destination-address {
              type inet:host;
              description
                "The destination IP address or hostname of the
                 Collecting Process to which IPFIX Messages are sent.
                 A hostname may resolve to one or more IP
                 addresses.";
            }
          }
        }
      }
    }

    leaf maximum-packet-size {
      type uint16;
      units octets;
      description
        "This parameter specifies the maximum size of IP packets sent
         to the Collector.  If set to zero, the Exporting Device MUST
         derive the maximum packet size from path MTU discovery
         mechanisms.

         If not configured by the user, this parameter is set by
         the Monitoring Device.";
    }

    leaf template-refresh-timeout {
      type uint32;
      units seconds;
      default 600;
      description
        "Sets time after which Templates are resent in the UDP
         Transport Session.

         Note that the configured lifetime MUST be adapted to the
         template-life-time parameter value at the receiving
         Collecting Process.

         Note that this parameter corresponds to
         ipfixTransportSessionTemplateRefreshTimeout in the IPFIX
         MIB module.";
      reference
        "RFC 7011, Section 8.4; RFC 6615, Section 8
         (ipfixTransportSessionTemplateRefreshTimeout).";
    }

    leaf options-template-refresh-timeout {
      type uint32;
      units seconds;
      default 600;
      description
        "Sets time after which Options Templates are resent in the
         UDP Transport Session.

         Note that the configured lifetime MUST be adapted to the
         options-template-life-time parameter value at the receiving
         Collecting Process.

         Note that this parameter corresponds to
         ipfixTransportSessionOptionsTemplateRefreshTimeout in the
         IPFIX MIB module.";
      reference
        "RFC 7011, Section 8.4; RFC 6615, Section 8
         (ipfixTransportSessionOptionsTemplateRefreshTimeout).";
    }

    leaf template-refresh-packet {
      type uint32;
      units "IPFIX Messages";
      description
        "Sets number of IPFIX Messages after which Templates are
         resent in the UDP Transport Session.

         Note that this parameter corresponds to
         ipfixTransportSessionTemplateRefreshPacket in the IPFIX
         MIB module.

         If omitted, Templates are only resent after timeout.";
      reference
        "RFC 7011, Section 8.4; RFC 6615, Section 8
         (ipfixTransportSessionTemplateRefreshPacket).";
    }

    leaf options-template-refresh-packet {
      type uint32;
      units "IPFIX Messages";
      description
        "Sets number of IPFIX Messages after which Options Templates
         are resent in the UDP Transport Session protocol.

         Note that this parameter corresponds to
         ipfixTransportSessionOptionsTemplateRefreshPacket in the
         IPFIX MIB module.

         If omitted, Templates are only resent after timeout.";
      reference
        "RFC 7011, Section 8.4; RFC 6615, Section 8
         (ipfixTransportSessionOptionsTemplateRefreshPacket).";
    }

    uses transport-layer-security-parameters;
  }

  grouping sctp-exporter-parameters {
    description
      "Parameters of a SCTP export destination.";

    uses common-exporter-parameters {
      augment "source/source-method" {
        description
          "Augment the source method to add the source IP address or
           hostname.";

        case source-address {
          leaf-list source-address {
            type inet:host;
            description
              "The source IP address(es) or hostname(s) used by the
               Exporting Process.";
          }
        }
      }

      augment "destination" {
        description
          "Augment the destination method to add the destination
           IP address or hostname.";

        choice destination-method {
          mandatory true;
          description
            "Method to configuring the destination address of the
             Collection Process to which IPFIX Messages are sent.

             Note it is expected that if other methods are available
             that they would augment from this statement.";

          case destination-address {
            leaf-list destination-address {
              type inet:host;
              description
                "List of destination IP addresses or hostnames.
                 A hostname may resolve to one or more IP addresses.

                 The user must ensure that all configured IP
                 addresses belong to the same Collecting Process.

                 The SCTP Exporting Processs tries to establish an
                 SCTP association to any of the configured
                 destination IP addresses.";
            }
          }
        }
      }
    }

    leaf timed-reliability {
      type uint32;
      units milliseconds;
      default 0;
      description
        "Lifetime in milliseconds until an IPFIX Message containing
         Data Sets only is 'abandoned' due to the timed reliability
         mechanism of PR-SCTP.

         If this parameter is set to zero, reliable SCTP transport is
         used for all Data Records.

         Regardless of the value of this parameter, the Exporting
         Process MAY use reliable SCTP transport for Data Sets
         associated with Options Templates.";
      reference
        "RFC 3758; RFC 4960.";
    }

    leaf association-timeout {
      type uint32;
      units seconds;
      description
        "Time after which the exporting process deems the SCTP
         association to have failed.";
      reference
        "RFC 7011, Sections 10.2.4 and 10.2.5.";
    }

    uses transport-layer-security-parameters;
  }

  grouping file-writer-state-parameters {
    description
      "State Parameters for the File Writer.";

    container file-writer-state {
      config false;
      description
        "File Writer parameters.";

      leaf bytes {
        type yang:counter64;
        units octets;
        description
          "The number of bytes written by the File Writer.

           Discontinuities in the value of this counter can occur at
           re-initialization of the management system, and at other
           times as indicated by the value of
           file-writer-discontinuity-time.";
      }

      leaf messages {
        type yang:counter64;
        units "IPFIX Messages";
        description
          "The number of IPFIX Messages written by the File Writer.

           Discontinuities in the value of this counter can occur at
           re-initialization of the management system, and at other
           times as indicated by the value of
           file-writer-discontinuity-time.";
      }

      leaf discarded-messages {
        type yang:counter64;
        units "IPFIX Messages";
        description
          "The number of IPFIX Messages that could not be written by
           the File Writer due to internal buffer overflows, limited
           storage capacity, etc.

           Discontinuities in the value of this counter can occur at
           re-initialization of the management system, and at other
           times as indicated by the value of
           file-writer-discontinuity-time.";
      }

      leaf records {
        type yang:counter64;
        units "Data Records";
        description
          "The number of Data Records written by the File Writer.

           Discontinuities in the value of this counter can occur at
           re-initialization of the management system, and at other
           times as indicated by the value of
           file-writer-discontinuity-time.";
      }

      leaf templates {
        type yang:counter32;
        units "Templates";
        description
          "The number of Template Records (excluding Options Template
           Records) written by the File Writer.

           Discontinuities in the value of this counter can occur at
           re-initialization of the management system, and at other
           times as indicated by the value of
           file-writer-discontinuity-time.";
      }

      leaf options-templates {
        type yang:counter32;
        units "Options Templates";
        description
          "The number of Options Template Records written by the File
           Writer.

           Discontinuities in the value of this counter can occur at
           re-initialization of the management system, and at other
           times as indicated by the value of
           file-writer-discontinuity-time.";
      }

      leaf file-writer-discontinuity-time {
        type yang:date-and-time;
        description
          "Timestamp of the most recent occasion at which one or more
           File Writer counters suffered a discontinuity.

           In contrast to discontinuity times in the IPFIX MIB
           module, the time is absolute and not relative to
           sysUpTime.";
      }

      uses export-template-state-parameters;
    }
  }

  grouping exporting-process-parameters {
    description
      "Parameters of an Exporting Process.";

    leaf export-mode {
      type identityref {
        base export-mode;
      }
      default 'parallel';
      description
        "This parameter determines to which configured destination(s)
         the incoming Data Records are exported.";
    }

    list destination {
      key "name";
      min-elements 1;
      description
        "List of export destinations.";

      leaf name {
        type name-type;
        description
          "An arbitrary string which uniquely identifies the export
           destination.";
      }

      choice destination-parameters {
        mandatory true;
        description
          "Destination configuration.";

        case tcp-exporter {
          container tcp-exporter {
            if-feature tcp-transport;
            description
              "TCP parameters.";

            uses tcp-exporter-parameters;

            container transport-session {
              config false;
              description
                "Transport session state data.";

              uses transport-session-state-parameters;
              uses export-template-state-parameters;
            }
          }
        }

        case udp-exporter {
          container udp-exporter {
            if-feature udp-transport;
            description
              "UDP parameters.";
            uses udp-exporter-parameters;

            container transport-session {
              config false;
              description
                "Transport session state data.";

              uses transport-session-state-parameters;
              uses export-template-state-parameters;
            }
          }
        }

        case sctp-exporter {
          container sctp-exporter {
            if-feature sctp-transport;
            description
              "SCTP parameters.";

            uses sctp-exporter-parameters;

            container transport-session {
              config false;
              description
                "Transport session state data.";

              leaf sctp-association-id {
                type uint32;
                description
                  "The association ID used for the SCTP session
                   between the Exporter and the Collector of the
                   IPFIX Transport Session.  It is equal to the
                   sctpAssocId entry in the sctpAssocTable defined in
                   the SCTP-MIB.

                   This parameter is only available if the transport
                   protocol is SCTP and if an SNMP agent on the same
                   Monitoring Device enables access to the
                   corresponding MIB objects in the sctpAssocTable.

                   Note that this parameter corresponds to
                   ipfixTransportSessionSctpAssocId in the IPFIX MIB
                   module.";
                reference
                  "RFC 6615, Section 8
                   (ipfixTransportSessionSctpAssocId);
                   RFC 3871";
              }
              uses transport-session-state-parameters;
              uses export-template-state-parameters;
            }
          }
        }

        case file-writer {
          container file-writer {
            if-feature file-writer;
            description
              "File Writer parameters.";

            leaf ipfix-version {
              type uint16;
              default 10;
              description
                "IPFIX version number.";
              reference
                "RFC 7011.";
            }

            leaf file {
              type inet:uri;
              mandatory true;
              description
                "URI specifying the location of the file.";
            }

            uses file-writer-state-parameters;
          }
        }
      }
    }

    list options {
      key "name";
      description
        "List of options reported by the Exporting Process.";

      leaf name {
        type name-type;
        description
          "An arbitrary string which uniquely identifies the
           option.";
      }
      uses options-parameters;
    }
  }
  grouping options-parameters {
    description
      "Parameters specifying the data export using an Options
       Template.";

    leaf options-type {
      type identityref {
        base options-type;
      }
      mandatory true;
      description
        "Type of the exported options data.";
    }

    leaf options-timeout {
      type uint32;
      units "milliseconds";
      description
        "Time interval for periodic export of the options data. If
         set to zero, the export is triggered when the options data
         has changed.

         If not configured by the user, this parameter is set by the
         Monitoring Device.";
    }
  }

  container ipfix {
    description
      "IPFIX Exporter and/or Collector data nodes.";

    list collecting-process {
      if-feature collector;
      key "name";
      description
        "Collecting Process of the Monitoring Device.";

      leaf name {
        type name-type;
        description
          "An arbitrary string which uniquely identifies the
           Collecting Process.";
      }

      uses collecting-process-parameters;

      leaf-list exporting-process {
        if-feature exporter;
        type leafref {
          path "/ietf-ipfix:ipfix"
             + "/ietf-ipfix:exporting-process"
             + "/ietf-ipfix:name";
        }
        description
          "Export of received records without any modifications.
           Records are processed by all Exporting Processes in the
           list.";
      }
    }

    list exporting-process {
      if-feature exporter;
      key "name";
      description
        "List of Exporting Processes of the IPFIX Monitoring Device
         for which configuration will be applied.";

      leaf name {
        type name-type;
        description
          "An arbitrary string which uniquely identifies the
           Exporting Process.";
      }

      leaf enabled {
        type boolean;
        default "true";
        description
          "If true, this Exporting Process is enabled for
           exporting.";
      }

      uses exporting-process-parameters;

      leaf exporting-process-id {
        type uint32;
        config false;
        description
          "The identifier of the Exporting Process.  This parameter
           corresponds to the Information Element exportingProcessId.
           Its occurrence helps to associate Exporting Process
           parameters with Exporing Process statistics exported by
           the Monitoring Device using the Exporting Process
           Reliability Statistics Template as defined by the IPFIX
           protocol specification.";
        reference
          "RFC 7011, Section 4.3; IANA registry for IPFIX
           Entities, http://www.iana.org/assignments/ipfix.";
      }
    }
  }
}
