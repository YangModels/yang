module ietf-transport-network-slice {
  yang-version 1.1;
  namespace
    "urn:ietf:params:xml:ns:yang:ietf-transport-network-slice";
  prefix "tns";

  import ietf-inet-types {
    prefix inet;
    reference
      "RFC 6991: Common YANG Data Types";
  }

  import ietf-te-types {
    prefix "te-types";
    reference
      "RFC 8776: Traffic Engineering Common YANG Types";
  }

  import ietf-network-slice-service {
    prefix "ietf-nss";
    reference
      "draft-ietf-teas-ietf-network-slice-nbi-yang-00:
       IETF Network Slice Service YANG Model";
  }

  organization
    "IETF CCAMP Working Group";
  contact
    "WG Web: <http://tools.ietf.org/wg/ccamp/>
     WG List: <mailto:ccamp@ietf.org>

     Editor: Haomian Zheng
             <mailto:zhenghaomian@huawei.com>

     Editor: Italo Busi
             <mailto:italo.busi@huawei.com>

     Editor: Aihua Guo
             <mailto:aihuaguo.ietf@gmail.com>

     Editor: Sergio Belotti
             <mailto:sergio.belotti@nokia.com>";

  description
    "This module defines a base YANG data model for configuring
     generic network slices in optical transport networks, e.g.,
     Optical Transport Network (OTN).

     The model fully conforms to the Network Management Datastore
     Architecture (NMDA).

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see the
     RFC itself for full legal notices.";

  revision "2022-10-12" {
    description
      "Latest revision of NBI YANG model for OTN slicing.";
    reference
      "draft-ietf-ccamp-yang-otn-slicing-03: Framework and Data
       Model for OTN Network Slicing";
  }

  /*
   * Identities
   */
  identity isolation-level {
    description
      "Base identity for the isolation-level.";
    reference
      "GSMA-NS-Template: Generic Network Slice Template,
       Version 3.0.";
  }
  identity no-isolation {
    base isolation-level;
    description
      "Network slices are not separated.";
  }
  identity physical-isolation {
    base isolation-level;
    description
      "Network slices are physically separated (e.g. different
       rack, different hardware, different location, etc.).";
  }
  identity logical-isolation {
    base isolation-level;
    description
      "Network slices are logically separated.";
  }
  identity process-isolation {
    base physical-isolation;
    description
      "Process and threads isolation.";
  }
  identity physical-memory-isolation {
    base physical-isolation;
    description
      "Process and threads isolation.";
  }
  identity physical-network-isolation {
    base physical-isolation;
    description
      "Process and threads isolation.";
  }
  identity virtual-resource-isolation {
    base logical-isolation;
    description
      "A network slice has access to specific range of resources
       that do not overlap with other network slices
       (e.g. VM isolation).";
  }
  identity network-functions-isolation {
    base logical-isolation;
    description
      "NF (Network Function) is dedicated to the network slice,
       but virtual resources are shared.";
  }
  identity service-isolation {
    base logical-isolation;
    description
      "NSC data are isolated from other NSCs, but virtual
       resources and NFs are shared.";
  }

  identity resize-option {
    description
      "Base identity for link or connectivity resizing options";
  }

  identity resize-none {
    base resize-option;
    description
      "Not resizable";
  }

  identity resize-with-hit {
    base resize-option;
    description
      "Resizable with traffic hits";
  }

  identity resize-hitless {
    base resize-option;
    description
      "Hitless resizable";
  }

  /*
   * Groupings
   */

  grouping tns-slo-sle-policy {
    description
      "Policy grouping for Transport Network Slices.";

    leaf optimization-criterion {
        type identityref {
          base te-types:objective-function-type;
        }
        description
          "Optimization criterion applied to this topology.";
    }
    leaf delay-tolerance {
      type boolean;
      description
        "'true' if is not too critical how long it takes to
         deliver the amount of data.";
      reference
        "GSMA-NS-Template: Generic Network Slice Template,
         Version 3.0.";
    }
    leaf-list periodicity {
      type uint64;
      units seconds;
      description
        "A list of periodicities supported by the network
         slice.";
      reference
        "GSMA-NS-Template: Generic Network Slice Template,
         Version 3.0.";
    }
    leaf resize-requirement {
      type identityref {
        base resize-option;
      }
      description
        "Indicates resizing requirments";
    }
    leaf service-info {
      type string;
      description
        "Describe type of services running on the slice. It may be
         useful information to help the slice controller to
         optimize resource allocation";
    }
  }

  grouping tns-steering-constraints {
    description
      "Policy grouping for specifying steering constraints for
       Transport Network Slices.";

    leaf disjointness {
      type te-types:te-path-disjointness;
      description
        "Indicate the level of disjointness for slice
         resources.";
    }
    leaf service-info {
      type string;
      description
        "Describe type of services running on the slice. It may be
         useful information to help the slice controller to
         optimize resource allocation";
    }
  }

  grouping network-topology-def {
    description
      "Network topology definition";
    uses ietf-nss:service-slo-sle-policy;
    list node {
      key "node-id";
      description
      "The inventory of nodes of this topology.";
      leaf node-id {
        type inet:uri;
        description
          "Node identifier.";
      }
      uses ietf-nss:service-slo-sle-policy;
      list termination-point {
        key "tp-id";
        description
          "TP identifier";
        leaf tp-id {
          type inet:uri;
          description
            "Termination point identifier.";
        }
        leaf sdp-id {
          type leafref {
            path "/ietf-nss:network-slice-services"+
                 "/ietf-nss:slice-service"+
                 "[ietf-nss:service-id=current()"+
                 "/../../../../../ietf-nss:service-id]"+
                 "/ietf-nss:sdps/ietf-nss:sdp/ietf-nss:sdp-id";
          }
          description
            "Relative reference to SDP id.";
        }
        uses ietf-nss:service-slo-sle-policy;
      }
    }
    list link {
      key "link-id";
      description
        "Link identifier.";
      leaf link-id {
        type inet:uri;
        description
          "Link identifier.";
      }
      uses ietf-nss:service-slo-sle-policy;
      container source {
        description
          "Link source node";
        leaf source-node {
          type leafref {
            path "../../../node/node-id";
          }
          description
            "Source node identifier, must be in same topology.";
        }
        leaf source-tp {
          type leafref {
            path "../../../node[node-id=current()/../"+
                 "source-node]/termination-point/tp-id";
          }
          description
            "Termination point within source node that
             terminates the link.";
        }
      }
      container destination {
        description
          "Link destination node";
        leaf dest-node {
          type leafref {
            path "../../../node/node-id";
          }
          description
            "Destination node identifier, must be in same
             topology.";
        }
        leaf dest-tp {
          type leafref {
            path "../../../node[node-id=current()/../"+
                 "dest-node]/termination-point/tp-id";
          }
          description
            "Termination point within destination node that
             terminates the link.";
        }
      }
    }
  }

  grouping topology-ref {
    description
      "Grouping for network topology reference.";
    leaf topology-id {
      type leafref {
        path "../../../../network-topologies/network-topology"+
             "/topology-id";
      }
      description
        "Relative reference to network topology id.";
    }
    uses explicit-path;
  }

  grouping explicit-path {
    description
      "Explicit path for a connectivity matrix entry";

    list explicit-path {
      key "tp-id";
      description
        "List of TPs within a network topology that form a
         path.";
      leaf tp-id {
        type leafref {
          path "/ietf-nss:network-slice-services"+
               "/ietf-nss:slice-service"+
               "[ietf-nss:service-id=current()"+
               "/../../../../../ietf-nss:service-id]"+
               "/network-topologies"+
               "/network-topology[topology-id=current()"+
               "/../../topology-id]/node/termination-point"+
               "/tp-id";
        }
        description
          "Relative reference to TP id.";
      }
    }
  }

  /*
   * Augmented data nodes
   */
  augment "/ietf-nss:network-slice-services" +
          "/ietf-nss:slice-service" {
    description
      "Augment IETF network slice services to include network
       topologies.";
    container network-topologies {
      description
        "Set of network topologies referenced by network slices";

      list network-topology {
        key "topology-id";
        description
          "List of network topologies";
        leaf topology-id {
          type string;
          description
            "Topology identifier";
        }
        uses network-topology-def;
      }
    }
  }

  augment "/ietf-nss:network-slice-services" +
          "/ietf-nss:slice-service" +
          "/ietf-nss:connection-groups" +
          "/ietf-nss:connection-group" +
          "/ietf-nss:connectivity-construct"{
    description
      "Add toplogy id and explicit path to a connectivity
       construct";
    uses topology-ref;
  }

  augment "/ietf-nss:network-slice-services" +
          "/ietf-nss:slice-service" +
          "/ietf-nss:slo-sle-policy" +
          "/ietf-nss:custom" +
          "/ietf-nss:service-slo-sle-policy" {
    description
       "Augment IETF network slice services to include technology-
        specific SLO/SLE policy for connectivity-based transport
       network slices.";

    uses tns-slo-sle-policy;
  }

  augment "/ietf-nss:network-slice-services" +
          "/ietf-nss:slice-service" +
          "/ietf-nss:slo-sle-policy" +
          "/ietf-nss:custom" +
          "/ietf-nss:service-slo-sle-policy" +
          "/ietf-nss:steering-constraints" {
    description
      "Augment IETF network slice services to include steering
      constraints for connectivity-based transport network
      slices.";

    uses tns-steering-constraints;
  }

  /* network topology augments */
  augment "/ietf-nss:network-slice-services" +
          "/ietf-nss:slice-service" +
          "/tns:network-topologies" +
          "/tns:network-topology" +
          "/tns:slo-sle-policy" +
          "/tns:custom" +
          "/tns:service-slo-sle-policy" {
    description
      "Augment IETF network slice services to include technology-
       specific SLO/SLE policy for the network topology of a
       resource-based transport network slice.";

    uses tns-slo-sle-policy;
  }

  augment "/ietf-nss:network-slice-services" +
          "/ietf-nss:slice-service" +
          "/tns:network-topologies" +
          "/tns:network-topology" +
          "/tns:slo-sle-policy" +
          "/tns:custom" +
          "/tns:service-slo-sle-policy" +
          "/tns:steering-constraints" {
    description
      "Augment IETF network slice services to include steering
       constraints for links within a resource-based transport
       network slice.";

    uses tns-steering-constraints;
  }

  augment "/ietf-nss:network-slice-services" +
          "/ietf-nss:slice-service" +
          "/tns:network-topologies" +
          "/tns:network-topology" +
          "/tns:node" +
          "/tns:slo-sle-policy" +
          "/tns:custom" +
          "/tns:service-slo-sle-policy" {
    description
      "Augment IETF network slice services to include technology-
       specific SLO/SLE policy for nodes within a resource-based
       transport network slice.";

    uses tns-slo-sle-policy;
  }

  augment "/ietf-nss:network-slice-services" +
          "/ietf-nss:slice-service" +
          "/tns:network-topologies" +
          "/tns:network-topology" +
          "/tns:node" +
          "/tns:termination-point" +
          "/tns:slo-sle-policy" +
          "/tns:custom" +
          "/tns:service-slo-sle-policy" {
    description
      "Augment IETF network slice services to include technology-
       specific SLO/SLE policy for termination points within a
       resource-based transport network slice.";

    uses tns-slo-sle-policy;
  }

  augment "/ietf-nss:network-slice-services" +
          "/ietf-nss:slice-service" +
          "/tns:network-topologies" +
          "/tns:network-topology" +
          "/tns:link" +
          "/tns:slo-sle-policy" +
          "/tns:custom" +
          "/tns:service-slo-sle-policy" {
    description
      "Augment IETF network slice services to include technology-
       specific SLO/SLE policy for links within a resource-based
       transport network slice.";

    uses tns-slo-sle-policy;
  }

  augment "/ietf-nss:network-slice-services" +
          "/ietf-nss:slice-service" +
          "/tns:network-topologies" +
          "/tns:network-topology" +
          "/tns:link" +
          "/tns:slo-sle-policy" +
          "/tns:custom" +
          "/tns:service-slo-sle-policy" +
          "/tns:steering-constraints" {
    description
      "Augment IETF network slice services to include steering
       constraints for links within a resource-based transport
       network slice.";

    uses tns-steering-constraints;
  }

  /* connectivity construct augments */
  augment "/ietf-nss:network-slice-services" +
          "/ietf-nss:slice-service" +
          "/ietf-nss:connection-groups" +
          "/ietf-nss:connection-group" +
          "/ietf-nss:slo-sle-policy" +
          "/ietf-nss:custom" +
          "/ietf-nss:service-slo-sle-policy" {
    description
      "Augment IETF network slice services to include technology-
       specific SLO/SLE policy for connectivity-constructs within
       a connectivity-based transport network slice.";
    uses tns-slo-sle-policy;
  }

  augment "/ietf-nss:network-slice-services" +
          "/ietf-nss:slice-service" +
          "/ietf-nss:connection-groups" +
          "/ietf-nss:connection-group" +
          "/ietf-nss:slo-sle-policy" +
          "/ietf-nss:custom" +
          "/ietf-nss:service-slo-sle-policy" +
          "/ietf-nss:steering-constraints" {
    description
      "Augment IETF network slice services to include steering
      constraints for connectivity-constructs within a
      connectivity-based transport network slice.";
    uses tns-steering-constraints;
  }

  augment "/ietf-nss:network-slice-services" +
          "/ietf-nss:slice-service" +
          "/ietf-nss:connection-groups" +
          "/ietf-nss:connection-group" +
          "/ietf-nss:connectivity-construct" +
          "/ietf-nss:slo-sle-policy" +
          "/ietf-nss:custom" +
          "/ietf-nss:service-slo-sle-policy" {
    description
      "Augment IETF network slice services to include technology-
       specific SLO/SLE policy for connectivity-constructs within
       a connectivity-based transport network slice.";
    uses tns-slo-sle-policy;
  }

  augment "/ietf-nss:network-slice-services" +
          "/ietf-nss:slice-service" +
          "/ietf-nss:connection-groups" +
          "/ietf-nss:connection-group" +
          "/ietf-nss:connectivity-construct" +
          "/ietf-nss:slo-sle-policy" +
          "/ietf-nss:custom" +
          "/ietf-nss:service-slo-sle-policy" +
          "/ietf-nss:steering-constraints" {
    description
      "Augment IETF network slice services to include steering
      constraints for connectivity-constructs within a
      connectivity-based transport network slice.";
    uses tns-steering-constraints;
  }

  augment "/ietf-nss:network-slice-services" +
          "/ietf-nss:slice-service" +
          "/ietf-nss:connection-groups" +
          "/ietf-nss:connection-group" +
          "/ietf-nss:connectivity-construct" +
          "/ietf-nss:connectivity-construct-type" +
          "/ietf-nss:a2a" +
          "/ietf-nss:a2a-sdp" +
          "/ietf-nss:slo-sle-policy" +
          "/ietf-nss:custom" +
          "/ietf-nss:service-slo-sle-policy" {
    description
      "Augment IETF network slice services to include technology-
       specific SLO/SLE policy for a2a connectivity-constructs
       within a connectivity-based transport network slice.";
    uses tns-slo-sle-policy;
  }

  augment "/ietf-nss:network-slice-services" +
          "/ietf-nss:slice-service" +
          "/ietf-nss:connection-groups" +
          "/ietf-nss:connection-group" +
          "/ietf-nss:connectivity-construct" +
          "/ietf-nss:connectivity-construct-type" +
          "/ietf-nss:a2a" +
          "/ietf-nss:a2a-sdp" +
          "/ietf-nss:slo-sle-policy" +
          "/ietf-nss:custom" +
          "/ietf-nss:service-slo-sle-policy" +
          "/ietf-nss:steering-constraints" {
    description
      "Augment IETF network slice services to include steering
      constraints for a2a connectivity-constructs within a
      connectivity-based transport network slice.";
    uses tns-steering-constraints;
  }
}
