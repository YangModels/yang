module acl-ip {
    namespace "urn:cisco:params:xml:ns:yang:acl-ip";
    // replace with IANA namespace when assigned
    prefix acl-ip;

    import acl { prefix acl;  }
    import ietf-inet-types {
        prefix "inet";
    }
    import common-types {
        prefix "c-types";
    }

    organization
       "IETF NETMOD (NETCONF Data Modeling Language) Working Group";

    contact
    "WG Web: http://tools.ietf.org/wg/netmod/
        WG List: netmod@ietf.org

        WG Chair: David Kessens
        david.kessens@nsn.com

        WG Chair: Juergen Schoenwaelder
        j.schoenwaelder@jacobs-university.de

        Editor: Lisa Huang
        yihuan@cisco.com

        Editor: Alexander Clemm
        alex@cisco.com";

     description
        "This YANG module augments the 'acl' module with configuration
        and operational data for IPv4 and IPv6 access control list.

        An ACL is an ordered set of rules and actions used to filter
        traffic.
        Each set of rules and actions is represented as an Access
        Control Entries (ACE). Each ACE is evaluated sequentially.
        When the rule matches then action for that rule is applied
        to the packet.

        IP ACLs are ordered sets of rules that can use to
        filter traffic based on IP information in the Layer 3 header
        of packets.
        The device applies IP ACLs only to IP traffic. IP ACL
        can be IPv4 or IPv6.

        Terms and Acronyms
         ACE (ace): Access Control Entry

         ACL (acl): Access Control List

         AFI (afi): Authority and Format Identifier (Address Field
             Identifier)

         DSCP (dscp): Differentiated Services Code Point

         ICMP (icmp): Internet Control Message Protocol

         IGMP (igmp): Internet Group Management Protocol

         IP (ip): Internet Protocol
         IPv4 (ipv4):Internet Protocol Version 4

         IPv6 (ipv6): Internet Protocol Version 6

         QoS: Quality of Service

         TCP (tcp): Transmission Control Protocol

         ToS (tos): Type of Service

         TTL (ttl): Time to Live

         UDP (udp): User Datagram Protocol

         VLAN (vlan): Virtual Local Area Network

         VRF(vrf) : Virtual Routing and Forwarding
       ";

    revision 2012-08-31 {
        description "Initial revision. ";
    }

    grouping ACTIONS {
        leaf action {
            type acl:ACL-Action;
            mandatory true;
            description "Permit/deny action.";
        }
        choice log-choice {
            case log {
                leaf log {
                    type empty;
                    description
                        "Causes an informational
                        logging message about the
                        packet that matches the entry
                        to be sent to the console.";
                }
            }
            case log-input {
                leaf log-input {
                    type empty;
                    if-feature acl:log-input;
                    description
                        "Provides the same function
                        as the enable-log leaf,  except
                        that the logging message also
                        includes the input interface";
                }
            }
        }
    }

    grouping SRC-PORT-GROUP {
        description
            "Using comparator and port, or port-upper and port-lower
            to specify a port range. ";
        choice src-ports {
            case port-number-range {
                description
                    "Port group includes all ports between port-lower
                    and port-upper (including those)";
                leaf src-port-lower {
                    type inet:port-number;
                    description "Lower Port number.";
                    mandatory true;
                }
                leaf src-port-upper {
                    type inet:port-number;
                    description "Upper Port number.";
                    mandatory true;
                    must "../src-port-lower <= ../src-port-upper";
                }
            }
            case port-number {
                description
                    "Port group includes all ports that are greater
                    than, greater or equal, less than, less or equal,
                    or not equal the port, per the indicated
                    comparator.  It is possible for the port group
                    to be empty (for example, in case a port group
                    that is less than the minimum port number is
                    specified).";
                leaf src-comparator {
                    type acl:Comparator;
                    mandatory true;
                }
                leaf src-port {
                    type inet:port-number;
                    description "Port number.";
                    mandatory true;
                }
            }
            case port-group-ref {
                if-feature acl:port-group;
                leaf src-port-group-name {
                    type acl:Port-Group-Ref;
                    mandatory true;
                    description
                        "Reference a port group by the Port
                        Group name.";
                }
            }
        }
    }

    grouping DES-PORT-GROUP {
        description "Using comparator and port, or port-upper and
            port-lower to specify a port range. ";
        choice des-ports {
            case port-number-range {
                description "Port group includes all ports between
                    port-lower and port-upper (including those)";
                leaf des-port-lower {
                    type inet:port-number;
                    description "Lower Port number.";
                    mandatory true;
                }
                leaf des-port-upper {
                    type inet:port-number;
                    description "Upper Port number.";
                    mandatory true;
                    must "../des-port-lower <= ../des-port-upper";
                }
            }
            case port-number {
                description "Port group includes all ports that
                    are greater than, greater or equal, less than,
                    less or equal, or not equal the port, per the
                    indicated comparator.  It is possible for the
                    port group to be empty (for example, in case a
                    port group that is less than the minimum port
                    number is specified).";
                leaf des-comparator {
                    type acl:Comparator;
                    mandatory true;
                }
                leaf des-port {
                    type inet:port-number;
                    description "Port number.";
                    mandatory true;
                }
            }
            case port-group-ref {
                if-feature acl:port-group;
                leaf des-port-group-name {
                    type acl:Port-Group-Ref;
                    mandatory true;
                    description
                    "Reference a port group by the Port Group name.";
                }
            }
        }
    }
    grouping IP-ACE-FILTERS {
        leaf protocol {
            type c-types:IP-Protocol;
            description "IP protocol number.";

        }
        leaf enable-capture {
            type boolean ;
            description
                "Enable packet capture on this filter
                for this session.";
        }
        leaf capture-session-id {
            when "../enable-capture = 'true'";
            type uint32 {
                range "1..48";
            }
            description
                "Enable packet capture on this filter
                for this session id.";
            if-feature acl:capture-session-id;
        }

        leaf fragments {
            type empty;
            description "Check non-initial fragments";
        }

        leaf time-range {
            type acl:Time-Range-Ref;
            description
                "Refer a time range object by
                name (Max Size 64).";
        }
        uses SRC-PORT-GROUP {
             when
                "../protocol = '6' or
                ../protocol = '17' or
                ../protocol = '132'";
            description
                "Apply only when the protocol is TCP,
                UDP or SCTP.";
        }

        uses DES-PORT-GROUP {
             when
                "../protocol = '6' or
                ../protocol = '17' or
                ../protocol = '132'";
            description
                "Apply only when the protocol is TCP,
                UDP or SCTP.";
        }
        leaf icmp-type {
            when "../protocol = '1'";
            type c-types:ICMP-Type;
            description
                "ICMP message type number.
                Apply only when the protocol is icmp";
        }

        leaf icmp-code {
            when "boolean(../icmp-type) ";
            type c-types:ICMP-Code;
            description
            "ICMP subtype for a given icmp type.";
        }

        choice packet-length-or-range {
            if-feature acl:packet-length;
            case length {
                leaf packet-length-comparator {
                    type acl:Comparator;
                    description
                        "Operant that compare the packet
                        length. Operands are lt (less than),
                        gt (greater than), eq (equal), and neq
                        (not equal).";
                    mandatory true;
                }
                leaf packet-length {
                    type uint32 {
                        range "20..9210";
                    }
                    description
                        "Packet legth value for
                        operation gt, eq, etc, other
                        than range";
                    mandatory true;
                }
            }
            case range {
                leaf packet-length-upper {
                    type uint32 {
                        range "20..9210";
                    }
                    description "Upper Packet legth";
                    mandatory true;
                }

                leaf packet-length-lower {
                    type uint32 {
                        range "20..9210";
                    }
                    description "Lower packet length";
                    must
                        "number(../packet-length-lower) <=
                        number(../packet-length-upper)";
                    mandatory true;
                }
                description
                    "Packet operater 'range' takes
                    both lower and upper value.";
            }
        }
        leaf tcp-flag-value {
            type c-types:TCP-Flag-Type ;
            description "TCP flag bits that needs to be checked";
        }
        leaf tcp-flag-mask {
            when "boolean(../tcp-flag-value)" ;
            type c-types:TCP-Flag-Type ;
            description "TCP flag bit that needs to be checked";
        }

        leaf tcp-flag-operation {
            when "boolean(../tcp-flag-value)" ;
            description
                "TCP flag Match option.
                A match occurs if the TCP
                datagram has certain TCP flags
                set or not set. You use the
                match-any keyword to allow a match
                to occur if any of the specified
                TCP flags are present, or you can
                use the match-all keyword to allow
                a match to occur only if all of
                the specified TCP flags are
                present. You must follow the
                match-any and match-all keywords
                with the + or - keyword and the
                flag-name argument to match on
                one or more TCP flags. ";
            default match-any;
            type enumeration {
                enum match-any {
                    description "match any";
                }
                enum match-all {
                    description "match all";
                }
            }

        }
        choice ttl-value-or-range {
            if-feature acl:time-to-live;
            case value {
                leaf ttl-comparator {
                    type Comparator;

                    description
                        "Compares the TTL value in the packet
                        to the TTL value specified in this
                        ACE statement. Operands are lt (less
                        than), gt (greater than), and eq
                        (equal),  neq (not equal).";
                }
                leaf ttl-value {
                    type c-types:Time-to-Live;
                }
            }
            case range {
                leaf ttl-value-lower {
                    type c-types:Time-to-Live;
                    description "Lower ttl number.";
                }
                leaf ttl-value--upper {
                    type c-types:Time-to-Live;
                    description "Upper ttl number.";

                }
            }
        }
    }

    grouping IPV4-ACE-GROUP {
        description "Layer 3 Access Control Entry (ACE).";

        container ipv4-aces {
            description
                " The ip-aces container contains a list of ip-ace.
                Each ip-ace is made of a sequence number and a choice
                of remark(comment) or filter. The filter requires a
                mandatory action (permit/deny) and one or more options
                such as source-address with mask,ttl etc";

            list ipv4-ace {
                key "sequence-num";
                description "Layer 3 Access Control Element (ACE)";

                leaf sequence-num {
                    type acl:Sequence-Number;
                    description "This number determines the order in
                        which the statements within the access list
                        will be evaluated.";
                }

                choice remark-or-filter {
                    case remark {
                        leaf remark {
                            type acl:Remark;
                            mandatory true;
                            description "A remark is a comment that
                                can be inserted into an ACL in order
                                to make the access list easier for
                                the network administrator to
                                understand.
                                It is retained to facilitate
                                co-existence with  CLI.";
                        }
                    }
                    case filter {
                        container filters {

                            uses acl:IP-SOURCE-NETWORK;
                            uses acl:IP-DESTINATION-NETWORK;
                            uses IP-ACE-FILTERS ;

                            choice dscp-or-tos {
                                case dscp {
                                    leaf dscp {
                                        type inet:dscp;
                                        description
                                            "Match packets with given
                                            dscp value";
                                    }
                                }
                                case tos {
                                    leaf tos {
                                        type c-types:ToS;
                                        description
                                            "Match packets with
                                            given TOS value";

                                    }
                                    leaf precedence {
                                        when "boolean(../tos)" ;
                                        type c-types:Precedence;
                                        description
                                            "Match packets with given
                                            precedence value";
                                    }
                                }
                            }
                        }
                        container actions {
                            uses ACTIONS ;
                        }

                        leaf match {
                            config false;
                            type uint64;
                            description "The total packet that have
                                matched for the particular ACE";
                        }
                    }
                }
            }

        }

    }
    grouping IPV6-ACE-GROUP {
        description "Layer 3 Access Control Entry (ACE).";

        container ipv6-aces {
            description
                " The ip-aces container contains a list of ip-ace.
                Each ip-ace is made of a sequence number and a
                choice of remark(comment) or filter. The filter
                requires a mandatory action (permit/deny) and one or
                more options such as source-address with mask,ttl etc";

            list ipv6-ace {
                key "sequence-num";
                description "Layer 3 Access Control Element (ACE)";

                leaf sequence-num {
                    type acl:Sequence-Number;
                    description "This number determines the order in
                        which the statements within the access list
                        will be evaluated.";
                }

                choice remark-or-filter {
                    case remark {
                        leaf remark {
                            type string {
                                length "0..100";
                            }
                            description "The remark is the comments
                                about each acl which is to make the
                                access list easier for the network
                                administrator to understand.";
                        }
                    }
                    case filter {
                        container filters {

                            uses acl:IP-SOURCE-NETWORK;
                            uses acl:IP-DESTINATION-NETWORK;
                            uses IP-ACE-FILTERS ;

                            choice dscp-or-tos {
                                case dscp {
                                    leaf dscp {
                                        type inet:dscp;
                                        description
                                            "Match packets with given
                                            dscp value";
                                    }
                                }
                            }
                            leaf igmp-type {
                                when
                                    "../protocol = '2' ";
                                type c-types:IGMP-Code;
                                description
                                   "IGMP message type (0 to 15) for
                                   filtering IGMP packets. Apply only
                                   when the protocol is igmp in ipv4";
                            }
                            leaf flow-label {
                                when
                                    "../protocol = '17'";
                                type uint64 {
                                    range "0..1048575";
                                }
                                description
                                    "Flow label value. Apply only when
                                    the protocol is UDP in ipv6.";
                                reference
                                    "RFC3697 IPv6 Flow Label
                                    Specification";
                                if-feature acl:flow-label;
                            }
                        }

                        container actions {
                            uses ACTIONS ;
                        }

                        leaf match {
                            config false;
                            type uint64;
                            description
                                "The total packet that have matched for
                                the particular ACE";
                        }
                    }
                }
            }

        }

    }

    augment "/acl:acls/acl:acl" {
        when "acl:acl-type = 'ip-acl'";
        leaf afi {
            type inet:ip-version ;
            default "ipv4";
        }
        uses IPV6-ACE-GROUP {
            when "../afi = 'ipv6'" ;
        }
        uses IPV4-ACE-GROUP {
            when "../afi = 'ipv4'" ;
        }

        leaf global-fragments {
            default "not-set";
            type enumeration {
                enum not-set;
                enum permit-all {
                    description "Allow all fragments";
                }
                enum deny-all {
                    description "Drop all fragments";
                }
            }
            description
                "Optimizes fragment handling for noninitial fragments.
                When this leaf is set to 'permit-all', noninitial
                fragments willbe permitted unless explicitly denied.
                When this leaf is set to 'deny-all', noninitial
                fragments will be denied unless explicitly
                permitted. ";
        }
    }

}
