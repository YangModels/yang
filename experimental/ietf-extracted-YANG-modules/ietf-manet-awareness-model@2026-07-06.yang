module ietf-manet-awareness-model {
    namespace "urn:de:fraunhofer:fkie:rhn:mam";

    prefix mam;

    import ietf-inet-types { prefix inet; }
    import ietf-yang-types { prefix yang; }

    contact
        "Editor: Henning Rogge
         <mailto:henning.rogge@fkie.fraunhofer.de>
         Editor: Julia Niewiejska
         <mailto:julia.niewiejska@fkie.fraunhofer.de>";

    description
        "This module defines a standardized information access for
         middleware and applications to the current state and
         knowledge of a MANET router";

    organization "ietf manet wg";

    revision "2026-07-06" {
        description
            "Flatten traffic attributes, classifiers, and selectors
             to concrete fields";
    }

    grouping comparator {
        description
            "Comparison operator for use in traffic-classifiers.
             Combined with a metric value it forms a boolean
             threshold condition, e.g. latency less-equal 0.020.";
        leaf comparator {
            description "comparator between two numeric values.";
            mandatory true;
            type enumeration {
                enum less;
                enum less-equal;
                enum greater;
                enum greater-equal;
            }
        }
    }
    grouping attr-max-bitrate-rx {
        description
            "Value leaf for the hardware-limited maximum
             receive rate.";
        leaf value {
            description "maximum receive bitrate in bits/s";
            mandatory true;
            type uint64;
        }
    }
    grouping attr-max-bitrate-tx {
        description
            "Value leaf for the hardware-limited maximum
             transmit rate.";
        leaf value {
            description "maximum transmit bitrate in bits/s";
            mandatory true;
            type uint64;
        }
    }
    grouping attr-bitrate-rx {
        description
            "Value leaf for the currently achievable receive rate.";
        leaf value {
            description "current receive bitrate in bits/s";
            mandatory true;
            type uint64;
        }
    }
    grouping attr-bitrate-tx {
        description
            "Value leaf for the currently achievable transmit rate.";
        leaf value {
            description "current transmit bitrate in bits/s";
            mandatory true;
            type uint64;
        }
    }
    grouping attr-latency {
        description
            "Value leaf for the one-way propagation and processing
             delay.";
        leaf value {
            description "latency in seconds";
            mandatory true;
            type decimal64 {
                fraction-digits 9;
                range "0 .. max";
            }
        }
    }
    grouping attr-lossrate {
        description
            "Value leaf for the frame loss fraction.";
        leaf value {
            description "packet loss rate";
            mandatory true;
            type decimal64 {
                fraction-digits 2;
                range "0 .. 1";
            }
        }
    }
    grouping attr-hopcount {
        description
            "Value leaf for the hop count.";
        leaf value {
            description "hop count";
            mandatory true;
            type uint8;
        }
    }
    grouping attr-rt-metric {
        description
            "Value leaf for the routing protocol cost.";
        leaf value {
            description "additive routing metric";
            mandatory true;
            type uint64;
        }
    }
    grouping traffic-attributes {
        description
            "Optional presence containers reporting measured or
             configured properties of a link or path. Each metric
             container is independently optional; an absent
             container indicates the metric is unavailable or not
             applicable.";
        container max-bitrate-rx {
            presence "max rx bitrate is available";
            description
                "Hardware-limited maximum receive rate;
                 does not reflect current load.";
            uses attr-max-bitrate-rx;
        }
        container max-bitrate-tx {
            presence "max tx bitrate is available";
            description
                "Hardware-limited maximum transmit rate;
                 does not reflect current load.";
            uses attr-max-bitrate-tx;
        }
        container bitrate-rx {
            presence "rx bitrate is available";
            description
                "Currently achievable receive rate.";
            uses attr-bitrate-rx;
        }
        container bitrate-tx {
            presence "tx bitrate is available";
            description
                "Currently achievable transmit rate.";
            uses attr-bitrate-tx;
        }
        container latency {
            presence "latency is available";
            description
                "One-way propagation and processing delay.";
            uses attr-latency;
        }
        container lossrate {
            presence "lossrate is available";
            description
                "Frame loss fraction.";
            uses attr-lossrate;
        }
        container hopcount {
            presence "hopcount is available";
            description
                "Number of link-layer hops traversed to reach
                 this destination.";
            uses attr-hopcount;
        }
        container rt-metric {
            presence "router metric is available";
            description
                "Accumulated routing cost as reported by the
                 routing protocol.";
            uses attr-rt-metric;
        }
    }

    grouping traffic-classifiers {
        description
            "Optional presence containers expressing threshold
             conditions on traffic attributes. Each container
             pairs a metric value with a comparison operator.
             Multiple present classifiers are all required to
             hold simultaneously.";
        container max-bitrate-rx {
            presence "max rx bitrate is used as classifier";
            description
                "Threshold condition on the maximum receive
                 rate.";
            uses attr-max-bitrate-rx;
            uses comparator;
        }
        container max-bitrate-tx {
            presence "max tx bitrate is used as classifier";
            description
                "Threshold condition on the maximum transmit
                 rate.";
            uses attr-max-bitrate-tx;
            uses comparator;
        }
        container bitrate-rx {
            presence "rx bitrate is used as classifier";
            description
                "Threshold condition on the currently available
                 receive rate.";
            uses attr-bitrate-rx;
            uses comparator;
        }
        container bitrate-tx {
            presence "tx bitrate is used as classifier";
            description
                "Threshold condition on the currently available
                 transmit rate.";
            uses attr-bitrate-tx;
            uses comparator;
        }
        container latency {
            presence "latency is used as classifier";
            description "Threshold condition on the one-way delay.";
            uses attr-latency;
            uses comparator;
        }
        container lossrate {
            presence "lossrate is used as classifier";
            description
                "Threshold condition on the frame loss
                 fraction.";
            uses attr-lossrate;
            uses comparator;
        }
        container hopcount {
            presence "hopcount is used as classifier";
            description "Threshold condition on the hop count.";
            uses attr-hopcount;
            uses comparator;
        }
        container rt-metric {
            presence "router metric is used as classifier";
            description
                "Threshold condition on the accumulated routing
                 cost.";
            uses attr-rt-metric;
            uses comparator;
        }
    }

    grouping interface-addresses {
        description
            "represents the addresses an interface is
             associated with.";
        leaf-list ip {
            description "IP addresses set on the interface";
            type inet:ip-address;
            min-elements 1;
        }
        leaf mac {
            description "Ethernet MAC address of the interface";
            type yang:mac-address;
        }
    }

    grouping host-dns {
        description
            "DNS hostname and optional fully qualified domain
             name of a node or attached network prefix.";
        container dns {
            presence "DNS information is available";
            description "DNS naming for this entity.";
            leaf hostname {
                description
                    "Unqualified host name, without domain
                     suffix.";
                type string;
                mandatory true;
            }
            leaf fqdn {
                description
                    "Fully qualified domain name, including
                     hostname and all domain labels.";
                type string;
            }
        }
    }

    container db {
        description
            "Top-level read-only operational data exported by
             this router, reflecting its current knowledge at
             request time.";
        config false;
        container dataprovider {
            description
                "Metadata identifying the router that generated
                 this data set and the timestamps associated
                 with it.";
            leaf node-id {
                description "ID of the router providing this data";
                type leafref {
                    path "/db/nodes/node-id";
                }
            }
            leaf creation-time {
                description
                    "Timestamp when the data was put together by the
                     router, the time the most recent data included
                     in the update was gathered.";
                reference
                    "RFC 3339, Section 5.6: Date and Time on
                     the Internet: Timestamps";
                type yang:date-and-time;
            }
            leaf request-time {
                description
                    "Timestamp when this data was requested by
                     the client";
                reference
                    "RFC 3339, Section 5.6: Date and Time on
                     the Internet: Timestamps";
                type yang:date-and-time;
            }
        }
        list topologies {
            description
                "Each topology represents a way traffic service
                 classes are handled by the networks
                 routing protocol.";
            key "topology-id";

            leaf topology-id {
                description "Unique identification of a traffic
                    topology of the network";
                type string;
            }
            container capabilities {
                description
                    "minimal features interfaces must provide to be
                     contained in this topology which is also a
                     minimum capability the application can assume.";
                uses traffic-classifiers;
            }
            container restrictions {
                description
                    "maximum traffic attributes an router/application
                     is allowed to use on this topology";
                uses traffic-classifiers;
            }
            container selectors {
                description
                    "traffic selectors mapped to this topology. an
                     empty selectors container means this topology is
                     the 'default' one that gets all traffic not put
                     into other topologies.";

                container dscp {
                    presence "DSCP is used as selector";
                    description
                        "Traffic classified by the 6-bit DSCP
                         field in the IP header, applicable to
                         both IPv4 and IPv6.";
                    leaf value {
                        description
                            "DSCP (6 bits) value selecting traffic
                            for this topology";
                        mandatory true;
                        type uint8 {
                            range "0 .. 63";
                        }
                    }
                }
                container vlan-tos {
                    presence
                        "VLAN type of service is used as selector";
                    description
                        "Traffic classified by the 3-bit Priority
                         Code Point (PCP) field in the 802.1Q
                         VLAN header.";
                    leaf value {
                        description
                            "VLAN TOS value selecting traffic for
                            this topology";
                        mandatory true;
                        type uint8 {
                            range "0 .. 7";
                        }
                    }
                }
                container vlan-id {
                    presence "VLAN ID is used as selector";
                    description
                        "Traffic classified by VLAN membership;
                         all frames carrying this VLAN ID are
                         mapped to the topology.";
                    leaf value {
                        description
                            "VLAN ID selecting traffic for this
                             topology";
                        mandatory true;
                        type uint16 {
                            range "0 .. 4095";
                        }
                    }
                }
                container udp-port {
                    presence
                        "UDP destination port is used as selector";
                    description
                        "Traffic classified by UDP destination
                         port, applicable to both IPv4 and
                         IPv6.";
                    leaf value {
                        description
                            "UDP port selecting traffic for
                             this topology";
                        mandatory true;
                        type uint16;
                    }
                }
                container tcp-port {
                    presence
                        "TCP destination port is used as selector";
                    description
                        "Traffic classified by TCP destination
                         port, applicable to both IPv4 and
                         IPv6.";
                    leaf value {
                        description
                            "TCP port selecting traffic for
                             this topology";
                        mandatory true;
                        type uint16;
                    }
                }
            }
        }
        list nodes {
            description
                "a node represents an entity of the network, either a
                 single router or a group of routers represented
                 by aggregated data.";
            key "node-id";
            uses host-dns;

            leaf node-id {
                description
                    "node-id is a router/entity-local identification
                     of a single node in this data description. There
                     is no guarantee that different nodes queried for
                     this data will assign the same node-id to the
                     same router/entity";
                type string;
            }
            leaf-list members {
                description
                    "the list of nodes that are part of this compound
                     node or group of nodes.";
                type leafref {
                    path "/db/nodes/node-id";
                }
            }
            leaf-list ip {
                description
                    "the list of IP addresses that are locally on
                     the network node.";
                type inet:ip-prefix;
            }
            list interfaces {
                description
                    "the list of network interfaces locally attached
                     to this node that are used to communicate to
                     other network nodes";
                key "interface-id";
                uses traffic-attributes;

                leaf interface-id {
                    description
                        "Identification of an interface of a node";
                    type string;
                }
                container medium {
                    presence "details about interface technology";
                    description
                        "a description of the communication medium
                         attached to the network node interface.";
                    leaf technology-id {
                        description
                            "Technology used by an interface.";
                        mandatory true;
                        type enumeration {
                            enum radio-hf;
                            enum radio-vhf;
                            enum radio-uhf;
                            enum radio-shf;
                            enum cable;
                            enum cellular;
                            enum satcom;
                            enum wifi;
                            enum other;
                        }
                    }
                    leaf description {
                        description
                            "Optional free-text label for the
                             medium, e.g. a radio model name.";
                        type string;
                    }
                }
                container interface-endpoint {
                    description
                        "the local addresses of the interface. These
                         addresses might not be globally reachable";
                    uses interface-addresses;
                }
                list links {
                    description
                        "a list of known network nodes that can be
                         reached over this interface";
                    key "remote-id";
                    uses traffic-attributes;

                    leaf remote-id {
                        description
                            "The neighbour reachable over this
                             direct link.";
                        type leafref {
                            path "/db/nodes/node-id";
                        }
                    }
                    container interface-endpoint {
                        description
                            "the interface addresses of the
                             remote neighbor";
                        uses interface-addresses;
                    }
                }
            }
            list services {
                description
                    "a list of services that are on this network node
                     or on an attached network prefix of the node";
                key "service-id ip port";

                leaf service-id {
                    description
                        "Unique identification of a service as
                        defined by the services application";
                    type string;
                }
                leaf ip {
                    description
                        "IP address on which the service
                         listens.";
                    type inet:ip-address;
                }
                leaf port {
                    description
                        "Network port on which the service
                         accepts connections.";
                    type uint16;
                }
                leaf protocol {
                    description
                        "Transport or application-layer protocol
                         required to access the service.";
                    mandatory true;
                    type enumeration {
                        enum TCP;
                        enum UDP;
                        enum HTTP;
                        enum HTTPS;
                        enum HTTP3;
                        enum OTHER;
                    }
                }
                leaf description {
                    description
                        "Human-readable description of the
                         service, its purpose, or usage
                         hints.";
                    type string;
                }
            }
            list identities {
                description
                    "a list of geoposition markers generated by the
                     network node. One of them can be the position of
                     the network node itself.";
                key "identity-id";

                leaf identity-id {
                    description
                        "Identification of an entity that was created
                        and is handled by the local node. This can be
                        the node itself, dismounted personal of a
                        vehicle, remote controlled drones or an
                        remote entity tracked by the node.";
                    type string;
                }
                container geo-location {
                    description
                        "geo-location is modelled after the TPV
                         object of gpsd-json";

                    leaf time {
                        description
                            "Time/date stamp in UTC as defined in
                             RFC 3339";
                        reference
                            "RFC 3339, Section 5.6: Date and Time on
                             the Internet: Timestamps";
                        mandatory true;
                        type yang:date-and-time;
                    }
                    leaf altitude {
                        description
                            "Altitude, height above ellipsoid,
                             in meters";
                        type decimal64 {
                            fraction-digits 2;
                        }
                    }
                    leaf climb {
                        description
                            "Climb (positive) or sink (negative)
                             rate, meters per second";
                        type decimal64 {
                            fraction-digits 2;
                        }
                    }
                    leaf latitude {
                        description
                            "Latitude in degrees, positive means
                             North, negative means South";
                        mandatory true;
                        type decimal64 {
                            fraction-digits 9;
                            range "-90 .. 90";
                        }
                    }
                    leaf longitude {
                        description
                            "Longitude in degrees, positive means
                             East, negative means West";
                        mandatory true;
                        type decimal64 {
                            fraction-digits 9;
                            range "-180 .. 180";
                        }
                    }
                    leaf track {
                        description
                            "Course over ground, degrees from true
                             north. Values range from 0 to 360,
                             where 0 and 360 represent the same
                             bearing (due north).";
                        type decimal64 {
                            fraction-digits 2;
                            range "0 .. 360";
                        }
                    }
                    leaf speed {
                        description
                            "Speed over ground, meters per second";
                        type decimal64 {
                            fraction-digits 2;
                            range "0 .. max";
                        }
                    }
                }
                leaf self {
                    description
                        "a value of true means that this geoposition
                         is the one of the network node itself";
                    type boolean;
                }
                list mapping {
                    description
                        "a list of application specific mappings of
                         the geoposition to existing data within the
                         application. With this mapping, applications
                         can integrate geopositions reported by this
                         data model back into their own database";
                    key "namespace key";

                    leaf namespace {
                        description
                            "the name or identifier of the
                             application defining this mapping";
                        type string;
                    }
                    leaf key {
                        description
                            "an application specific key describing
                             an aspect of this geoposition marker";
                        type string;
                    }
                    leaf value {
                        description
                            "the application specific value
                             corresponding to the key for this
                             geoposition marker";
                        type string;
                        mandatory true;
                    }
                }
            }
            list destinations {
                description
                    "a list of IP prefixes reachable from this
                    network node over a specific topology";
                key "ip topology-id";
                uses traffic-attributes;

                leaf ip {
                    description
                        "Destination prefix reachable via this
                         routing entry.";
                    type inet:ip-prefix;
                }
                leaf topology-id {
                    description
                        "Topology over which this destination
                         is reachable.";
                    type leafref {
                        path "/db/topologies/topology-id";
                    }
                }
                list path {
                    description
                        "a list of intermediate nodes on the way to
                         the destination. This allows to map a
                         destination to the hop-by-hop
                         connectivity.";
                    key "hop";

                    leaf hop {
                        description
                            "Sequence position of this node in
                             the path, starting at 1; defines
                             the hop ordering toward the
                             destination.";
                        type uint8;
                    }
                    leaf remote-id {
                        description
                            "Node at this sequence position on
                             the path to the destination.";
                        type leafref {
                            path "/db/nodes/node-id";
                        }
                    }
                }
            }
            list connectivity {
                description
                    "a list of topology specific neighbour network
                    nodes reachable without any intermediate
                    hop that are part of the same network";

                key "remote-id topology-id";
                uses traffic-attributes;

                leaf remote-id {
                    description
                        "The neighbour forming this direct
                         adjacency.";
                    type leafref {
                        path "/db/nodes/node-id";
                    }
                }
                leaf topology-id {
                    description
                        "Topology within which this direct
                         adjacency is active.";
                    type leafref {
                        path "/db/topologies/topology-id";
                    }
               }
            }
            list attached {
                description
                    "a list of IP prefixes that are reachable
                     directly through this network node";
                key "ip topology-id";
                uses host-dns;
                uses traffic-attributes;

                leaf ip {
                    description
                        "IP prefix directly reachable through
                         this node.";
                    type inet:ip-prefix;
                }
                leaf topology-id {
                    description
                        "Topology through which this prefix is
                         directly reachable.";
                    type leafref {
                        path "/db/topologies/topology-id";
                    }
                }
            }
        }
    }
}
