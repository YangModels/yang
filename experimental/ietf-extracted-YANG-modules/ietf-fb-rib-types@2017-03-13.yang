module ietf-fb-rib-types {

 yang-version "1";

 // namespace
   namespace "urn:ietf:params:xml:ns:yang:ietf-fb-rib-types";
   prefix "fb-rib-t";
       import ietf-interfaces {prefix "if";}
       import ietf-routing {prefix "rt";}
       import ietf-pkt-eca-policy {prefix "pkt-eca";}
       import ietf-access-control-lists {prefix "acls";}

 // meta
 organization
   "IETF";

 contact
    "email: shares@ndzh.com;
         email: sriganesh.kini@ericsson.com
     email: cengiz@packetdesign.com
     email: ivandean@gmal.org
     email: linda.dunbar@huawei.com;
     email: russ@riw.com;
        ";

 description
   "This module describes a YANG model for the I2RS
   Filter-based RIB Types.  These types
   specify types for the Filter-Based RIB.

       Copyright (c) 2015 IETF Trust and the persons identified as
   the document authors.  All rights reserved.

   Redistribution and use in source and binary forms, with or
   without modification, is permitted pursuant to, and subject
   to the license terms contained in, the Simplified BSD
   License set forth in Section 4.c of the IETF Trust's Legal
   Provisions Relating to IETF Documents
   (http://trustee.ietf.org/license-info).";

 revision "2017-03-13" {
     description
       "Filter-Based RIB protocol ";
       reference "draft-ietf-i2rs-fb-rib-data-model-01";
   }

   typedef fb-rib-type-def {
          type identityref {
            base "fb-rib-type";
                }
               description
               "This type is used to refer to
                source of Filter-Based RIB:
                configuration, I2RS, Flow-Spec.";
    }

       identity fb-rib-type {
               description
               "This type is used to refer to
                source of Filter-Based RIB:
                configuration, I2RS, Flow-Spec.";
       }

       identity fb-rib-config-type {
                base fb-rib-type;
            description
            "config Filter-Based RIB";
        }

       identity fb-rib-i2rs-ephemeral-type {
                base fb-rib-type;
            description
            "I2RS Reboot ephemeral Filter-Based RIB";
        }

       identity fb-rib-BGP-FS-type {
                base fb-rib-type;
            description
            "BGP Flow Specification Filter-Based RIB";
        }

   typedef fb-rib-policy-type-def {
          type identityref {
            base "fb-rib-policy-type";
                }
               description
               "This type is used to refer to FB-RIB type";
    }

       identity fb-rib-policy-type {
            description
            "Types of filter-based policies
                 acl and eca";
        }

          identity fb-rib-acl {
                 base fb-rib-policy-type;
             description
         "filter based policy based on access-lists";
           }

          identity fb-bnp-eca-rules {
                 base fb-rib-policy-type;
             description
         "filter based policy based on qos forwarding rules";
           }

       typedef fb-rules-status  {
          type identityref {
            base "fb-rule-opstat";
                }
               description
               "This type is used to refer to FB-RIB type";
        }

         identity fb-rule-opstat {
               description
               "operational statues for filter rules
                inactive and active";
                }

         identity fb-rule-inactive {
               base fb-rule-opstat;
               description
               "policy rule is inactive";
          }

         identity fb-rule-active {
               base fb-rule-opstat;
               description
               "policy rule is active";
          }

         grouping fb-rib-rule-order-status {
         leaf statement-order {
                 type uint16;
                 description "order identifier";
          }
          leaf statement-oper_status {
                  type fb-rules-status;
                  description "status of rule";
               }
               description "filter-rib
                 policy rule order and status";
         }

    grouping fb-rib-group-order-status {
         leaf group-refcnt {
           type uint16;
           description "refcnt for this group";
               }
          leaf group-installed {
           type uint32;
           description "number of rules installed";
               }
               leaf group-matches {
                type uint64;
                description "number of matches by all
                 rules in group";
               }
               description "fb-rib group list order
                  and status info.";
         }

       grouping fb-rib-updates {
          leaf fb-rib-update-ref {
                type uint64;
            description
                "number of updates to this FB RIB
                 since last reboot";
          }
          description "FB-RIB update info";
        }

       grouping default-fb-rib {
          // configuration instance for default RIB
       leaf config-instance {
               type string;
               description "instance name - string until
                  netmod fixes mount issues";
               }
               leaf config-rib {
                 type string;
                 description "name of config default RIB";
               }
               //I2RS default instance for default RIB
           leaf i2rs-instance-name {
                type string;
                description "I2RS instance name";
               }
               leaf i2rs-rib-name {
                       type string;
               description "name of default I2RS RIB";
               }
               leaf bgp-instance-name {
                  type string;
                  description "name of bgp instance";
               }

               leaf bgp-fs-rib-name {
                   type string;
                       description "name of BGP
                        flow specification default RIB";
               }
           description "default RIB for forwarding
                  if the policy match";
   }

   grouping fb-ribs {
           list fb-rib {
                   key fb-rib-name;
                   leaf fb-rib-name {
                       type string;
                               mandatory true;
                       description "RIB name";
           }
                   uses rt:address-family;
                   leaf fb-type {
                           type fb-rib-type-def;
                           description "type of RIB
                               list: config, I2RS rebooot
                               ephemeral, BGP Flow Specification
                               ephemeral. ";
                   }
               list fb-rib-intf {
                         key "name";
                         leaf name {
                               type if:interface-ref;
                           description
                            "A reference to the name of a
                                configured network layer
                            interface.";
                          }
                         description "This represents
                           the list of interfaces
                           associated with this routing instance.
                           The interface list helps constrain the
                           boundaries of packet forwarding.
                           Packets coming on these interfaces are
                           directly associated with the given routing
                           instance. The interface list contains a
                           list of identifiers, with each identifier
                           uniquely identifying an interface.";
               }
                       uses default-fb-rib;  // defaults ribs
                       uses fb-rib-updates;  // write refs to this RIB
               list instance-using {
                         key instance-name;
                         leaf instance-name {
                           type string;
                           description
                               " name of instance using this fb-rib
                                rt:routing-instance";
                          }
                         description "instances using
                          this fb-rib";
                       }
                   // ordered rule list + group list
                   uses pkt-eca:pkt-eca-policy-set;

                       // ordered acl list
                       uses acls:access-lists;

                 description "Configuration of
                    an filter-based rib list";
           }
          description "fb-rib group";
   }

       grouping fb-ribs-oper-status {
           list fb-rib-oper-status {
             key fb-rib-name;
                 leaf fb-rib-name {
                         type string;
                         description "rib name";
                 }
                 leaf pkt-eca-cfged {
                     type boolean;
                         description
                         "pkt eca configured";
                  }
                 leaf acls-cfged {
                     type boolean;
                         description
                         "acls configured";
                  }
         uses pkt-eca:pkt-eca-opstate;
                 description
                  "Configuration of
                    an filter-based rib list";
           }
          description
          "list of FB-FIB operational
            status";
   }

}
