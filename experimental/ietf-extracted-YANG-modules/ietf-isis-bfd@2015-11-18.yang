module ietf-isis-bfd {
     namespace "urn:ietf:params:xml:ns:yang:ietf-isis-bfd";

     prefix isis-bfd;

     import ietf-routing {
       prefix "rt";
     }
     import ietf-bfd {
       prefix "bfd";
     }
     import ietf-isis {
       prefix "isis";
        }

        organization
       "IETF ISIS Working Group";

        contact
        "
         WG List:  <mailto:isis-wg@ietf.org>

         Editor:   Stephane Litkowski
                   <mailto:stephane.litkowski@orange.com>
         Author:   Derek Yeung
                   <mailto:myeung@cisco.com>
         Author:   Yingzhen Qu
                   <mailto:yiqu@cisco.com>
         Author:   Acee Lindem
                   <mailto:acee@cisco.com>
         Author:   Jeffrey Zhang
                   <mailto:zzhang@juniper.net>
         Author:   Ing-Wher Chen
                   <mailto:ing-wher.chen@ericsson.com>
         Author:   Greg Hankins
                   <mailto:greg.hankins@alcatel-lucent.com>";

        description
       "This YANG module defines the generic configuration
        and operational state for ISIS BFD, which is common
        across all of the vendor implementations. It is
        intended that the module will be extended by vendors to
        define vendor-specific ISIS BFD configuration
        and operational parameters and policies.";

        revision 2015-11-18 {
       description
         "Initial revision.";
       reference
         "RFC XXXX: A YANG Data Model for ISIS BFD.";
     }

        feature bfd-protocol-parms {
       description
         "ISIS BFD protocol specific parameters support.";
     }

        /* Configuration */

     augment "/rt:routing/rt:routing-instance/rt:routing-protocols/"
           + "rt:routing-protocol/isis:isis/"
           + "isis:interfaces/isis:interface" {
       when "../../../../../../rt:type = 'isis:isis'" {
         description
         "This augments the ISIS routing protocol when used";
       }
       description
        "This augments ISIS protocol configuration
         with BFD.";

       container bfd {
         description "BFD configuration.";
         leaf enabled {
           type boolean;
           default false;
           description
             "True if BFD is enabled for the ISIS interface.";
         }
         uses bfd:bfd-grouping-base-cfg-parms {
           if-feature bfd-protocol-parms;
         }
       }
     }

          /* Operational states */

     augment "/rt:routing-state/rt:routing-instance/"
           + "rt:routing-protocols/rt:routing-protocol/"
           + "isis:isis/"
           + "isis:interfaces/isis:interface" {
       when "../../../../../../rt:type = 'isis:isis'" {
         description
         "This augments the ISIS routing protocol when used";
       }
       description
        "This augments ISIS protocol operation
         with BFD.";

       container bfd {
         description "BFD operation.";
         leaf enabled {
           type boolean;
           description
             "True if BFD is enabled for the ISIS interface.";
         }
         uses bfd:bfd-grouping-base-cfg-parms {
           if-feature bfd-protocol-parms;
         }
       }
     }
}
