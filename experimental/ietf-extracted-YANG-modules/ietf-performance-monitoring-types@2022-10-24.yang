module ietf-performance-monitoring-types {
  yang-version 1.1;
  namespace "urn:ietf:params:xml:ns:yang:ietf-performance-monitoring-types";
  prefix pm-types;

  organization
    "IETF CCAMP Working Group";
  contact
    "WG Web:   <https://datatracker.ietf.org/wg/ccamp/>
     WG List:  <mailto:ccamp@ietf.org>

     Editor:   Chaode Yu
               <yuchaode@huawei.com>";

  description
    "This module defines types model for optical performance
    monitoring which will be imported by ietf-performance-monitoring
    data model.

    The model fully conforms to the Network Management
    Datastore Architecture (NMDA).

    Copyright (c) 2022 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  revision 2022-10-24 {
    description  "Initial revision.";
    reference "draft-yu-performance-monitoring-yang-00";
  }

  identity resource-type {
    description "this is the base type of all the rerource type";
  }

  identity network-element {
    base resource-type;
    description "NE resource type";
  }

  identity board {
    base resource-type;
    description "board resource type";
  }

  identity port {
    base resource-type;
    description "port resource type";
  }

  identity period {
    description "this is the base type of all the performace monitoring priod type.";
  }

  identity period-15-minutes {
    base period;
    description
      "the during of monitoring task will be repeated at every 15 minutes";
  }

  identity period-24-hours {
    base period;
    description
      "the during of monitoring task will be repeated at every 24 hours";
  }
}
