module ietf-network-inventory {
  yang-version 1.1;
  namespace "urn:ietf:params:xml:ns:yang:ietf-network-inventory";
  prefix nw-inv;

  import ietf-network {
    prefix nw;
    reference
      "RFC 8345: A YANG Data Model for Network Topologies";
  }
  import ietf-network-topology {
    prefix nt;
    reference
      "RFC 8345: A YANG Data Model for Network Topologies";
  }
  import ietf-inet-types {
    prefix inet;
    reference
      "RFC 6991: Common YANG Data Types";
  }
  import ietf-yang-types {
    prefix yang;
    reference
      "RFC 6991: Common YANG Data Types";
  }
  import ietf-geo-location {
    prefix geo;
    reference
      "RFC 9179: A YANG Grouping for Geographic Locations";
  }
  import ietf-network-inventory-types {
    prefix nw-inv-types;
  }

  organization
    "IETF OPSAWG (Operations and Management Area Working Group)";
  contact
    "WG Web:   <https://datatracker.ietf.org/wg/opsawg/>
     WG List:  <mailto:opsawg@ietf.org>

     Editor: Bo Wu
          <lana.wubo@huawei.com>
     Editor: Cheng Zhou
          <zhouchengyjy@chinamobile.com>
     Editor: Qin Wu
          <bill.wu@huawei.com>
     Editor: Mohamed Boucadair
          <mohamed.boucadair@orange.com>";
  description
    "This YANG module defines XXX.

     Copyright (c) 2023 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC XXXX
     (https://www.rfc-editor.org/info/rfcXXXX); see the RFC
     itself for full legal notices.";

  revision 2023-07-10 {
    description
      "Initial revision.";
    reference
      "RFC XXXX: A Network Inventory Management Model for
       Enterprise Networks ";
  }

  identity node-type {
    description
      "Base identity for node device type.";
  }

  identity switch {
    base node-type;
    description
      "Identity for switch device.";
  }

  identity router {
    base node-type;
    description
      "Identity for router device.";
  }

  identity firewall {
    base node-type;
    description
      "Identity for Firewall device.";
  }

  identity access-controller {
    base node-type;
    description
      "Identity for WIFI access controller device.";
  }

  identity access-point {
    base node-type;
    description
      "Identity for WIFI access point device.";
  }

  identity sdn-controller {
    base node-type;
    description
      "Identity for controller.";
  }

  identity server {
    base node-type;
    description
      "Identity for computing server device.";
  }

  identity vm {
    base node-type;
    description
      "Identity for VM node.";
  }

  identity camera {
    base node-type;
    description
      "Identity for camera device.";
  }

  identity printer {
    base node-type;
    description
      "Identity for camera device.";
  }

  identity cell-phone {
    base node-type;
    description
      "Identity for mobile phone.";
  }

  typedef oper-state {
    type enumeration {
      enum unknown {
        value 1;
        description
          "The resource is unable to report its operational
           state.";
      }
      enum disabled {
        value 2;
        description
          "The resource is totally inoperable.";
      }
      enum enabled {
        value 3;
        description
          "The resource is partially or fully operable.";
      }
      enum testing {
        value 4;
        description
          "The resource is currently being tested and cannot
           therefore report whether or not it is operational.";
      }
    }
    description
      "Represents the possible values of operational states.";
    reference
      "RFC 4268: Entity State MIB - EntityOperState";
  }

  grouping inventory-network-type {
    description
      "Indicates the topology type to be inventory.";
    container network-inventory {
      presence "Indicates Network Inventory.";
      description
        "The presence of the container node indicates
         Network Inventory.";
    }
  }

  grouping inventory-node-attributes {
    description
      "Augment used to define attach the node configuration";
    leaf name {
      type string;
      description
        "The name of the node.";
    }
    leaf node-type {
      type identityref {
        base node-type;
      }
      config false;
      description
        "Node type.";
    }
    leaf is-virtual {
      type boolean;
      default "false";
      config false;
      description
        "Set to true if the node is virtual.
         Set to false if the node is physical.";
    }
    leaf is-gateway {
      type boolean;
      default "false";
      config false;
      description
        "Set to true if the node is a gateway.
         Set to false if the node is not a gateway.";
    }
    leaf gateway-ref {
      type leafref {
        path "../name";
      }
      config false;
      description
        "gateway for endpoint device.";
    }
    leaf management-ipv4-address {
      type inet:host;
      description
        "The IP address or DNS domain name of the device.";
    }
    leaf management-ipv6-address {
      type inet:host;
      description
        "The IP address or DNS domain name of the device.";
    }
    leaf mac-address {
      type yang:mac-address;
      config false;
      description
        "The MAC address of the device.";
    }
    leaf mud-url {
      type inet:uri;
      config false;
      description
        "This is the MUD URL associated with the MUD device found
         in a MUD file.";
    }
    leaf transparency-info {
      type inet:uri;
      config false;
      description
        "Link to software bill of material,
         see draft-ietf-opsawg-sbom-access";
    }
    leaf site {
      type string;
      description
        "The site of the node.";
    }
    uses nw-inv-types:component-info;
    uses nw-inv-types:components;
    uses nw-inv-types:licenses;
    uses geo:geo-location;
  }

  grouping inventory-link-attributes {
    description
      "Augment used to define the inventory link attributes.";
    list link {
      key "link-id";
      description
        "An inventory link connects a set of nodes via a set of
         the respective node's termination points. ";
      leaf link-id {
        type yang:uuid;
        description
          "The identifier of a link in the topology.
           A link is specific to a topology to which it belongs.";
      }
      leaf link-description {
        type string;
        config false;
        description
          "A textual description of the interface.";
      }
      leaf link-type {
        type string;
        config false;
        description
          "The type of the link.";
      }
      leaf-list ltp-ref {
        type leafref {
          path "../../nw:node/nt:termination-point/nt:tp-id";
        }
        config false;
        description
          "The interfaces for this link.";
      }
      leaf oper-state {
        type oper-state;
        config false;
        description
          "The operational state for this link.";
      }
    }
  }

  /* Main blocks */

  augment "/nw:networks/nw:network/nw:network-types" {
    description
      "Introduces new network type for network inventory.";
    uses inventory-network-type;
  }

  augment "/nw:networks/nw:network/nw:node" {
    when '/nw:networks/nw:network/nw:network-types/
   nw-inv:network-inventory' {
      description
        "Augmentation parameters apply only for network inventory.";
    }
    description
      "Configuration parameters for inventory at the node
       level.";
    uses inventory-node-attributes;
  }

  augment "/nw:networks/nw:network" {
    when '/nw:networks/nw:network/nw:network-types/
  nw-inv:network-inventory' {
      description
        "Augmentation parameters apply only for network
         inventory.";
    }
    description
      "Augments inventory link information.";
    uses inventory-link-attributes;
  }
}
