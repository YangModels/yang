module ietf-dots-signal-config {
     yang-version 1.1;
     namespace "urn:ietf:params:xml:ns:yang:ietf-dots-signal-config";
     prefix "config";

    organization "IETF DOTS Working Group";

    contact
      "Konda, Tirumaleswar Reddy <TirumaleswarReddy_Konda@McAfee.com>
       Mohamed Boucadair <mohamed.boucadair@orange.com>
       Prashanth Patil <praspati@cisco.com>
       Andrew Mortensen <amortensen@arbor.net>
       Nik Teague <nteague@verisign.com>";

     description
       "This module contains YANG definition for DOTS
        signal channel session configuration.

        Copyright (c) 2017 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

     revision 2017-11-27 {
       description
         "Initial revision.";
       reference
         "RFC XXXX: A Distributed Denial-of-Service Open Threat
                    Signaling (DOTS) Signal Channel";
     }

     container signal-config {
          description
            "DOTS signal channel session configuration.";

          leaf session-id {
              type int32;
              description
                "An identifier for the DOTS signal channel
                 session configuration data.";
          }

          leaf heartbeat-interval {
              type int16;
              units "seconds";
              default 30;
              description
                "DOTS agents regularly send heartbeats to each other
                 after mutual authentication in order to keep
                 the DOTS signal channel open.";
          }

          leaf missing-hb-allowed {
              type int16;
              default 5;
              description
                "Maximum number of missing heartbeats allowed.";
          }

          leaf max-retransmit {
              type int16;
              default 3;
              description
                "Maximum number of retransmissions of a
                 Confirmable message.";
          }

          leaf ack-timeout {
              type int16;
              units "seconds";
              default 2;
              description
                 "Initial retransmission timeout value.";
          }

          leaf ack-random-factor {
              type decimal64 {
                fraction-digits 2;
              }
             default 1.5;
             description
               "Random factor used to influence the timing of
                retransmissions.";
         }
         leaf trigger-mitigation {
             type boolean;
             default true;
             description
               "If false, then mitigation is triggered
                only when the DOTS server channel session is lost";
         }
      }
}
