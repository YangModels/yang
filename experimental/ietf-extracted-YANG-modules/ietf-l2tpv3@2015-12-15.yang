module ietf-l2tpv3 {
        namespace "urn:ietf:params:xml:ns:yang:ietf-l2tpv3";
        prefix "l2tpv3";

    import ietf-interfaces {
        prefix if;
    }
/*
    import ietf-yang-types {
        prefix yang;
    }
*/
    import ietf-inet-types {
        prefix inet;
    }
        organization "ietf l2tpv3 working group";
        contact "shenhaoxing@huawei.com
                 leo.liubing@huawei.com";
        description "The module for implementing l2tpv3 protocol";
        revision 2015-12-15 {description "version-01, minor grammar revision to pass pyang compiler";}

        typedef hexBinary {
                type string {
                        length "1..127";
                        pattern "0[xX][0-9a-fA-F]+";
                }
        }

        typedef password {
                type string {
                        length "1..127";
                }
        }

        container l2tpv3CtrlInstances {

                list l2tpv3CtrlInstance {

                        key "ctrlName";
                        min-elements "0";

                         leaf ctrlName {
                                config "true";
                                type "string"{
                                        length "1..19";
                                }
                        }
                        leaf hostName {
                                config "true";
                                type "string";
                                mandatory "true";
                        }
                        leaf routerID {
                                config "true";
                                type "uint16";
                                mandatory "true";
                        }
                        leaf rcvWinSize {
                                config "true";
                                type "uint16";
                        }
                        leaf helloInterval {
                                config "true";
                                type "uint16";
                        }
                        leaf digestType{
                                config "true";
                                                type enumeration {
                                                        enum "HMAC_MD5";
                                                        enum "HMAC_SHA_1";
                                                }
                        }
                        leaf authenNonce{
                                config "true";
                                type password {
                                        length "1..16";
                                }
                        }
                }

        }
        container l2tpv3TunnelInstance {

                list l2tpv3TunnelInstance {

                        key "tunnelName";
                        min-elements "0";

                         leaf tunnelName {
                                config "true";
                                type "string"{
                                        length "1..19";
                                }
                        }
                        leaf sourceIfName {
                                config "true";
                type if:interface-ref;
                description
                "Interface name as defined by ietf-interfaces";

                        }
                        leaf sourceIP {
                                config "true";
                                mandatory "true";
                                type inet:ip-address;
                        }
                        leaf destIP {
                                config "true";
                                mandatory "true";
                                type inet:ip-address;
                        }
                        leaf tnlType {
                                        config "true";
                                        mandatory "true";
                                        type enumeration {
                                                enum "static";
                                                enum "auto";
                                        }
                        }
                    choice tunnelType {
                                mandatory "true";

                        case static{
                                    when "tnlType = 'static'";
                                        leaf localSessionId {
                                                config "true";
                                                default "4294967295";
                                                type uint32 {
                                                        range "1..4294967295";
                                                }
                                        }
                                        leaf remoteSessionId {
                                                config "true";
                                                default "4294967295";
                                                type uint32 {
                                                        range "1..4294967295";
                                                }
                                        }
                                        leaf localCookieAutoMode {
                                                config "true";
                                                mandatory "true";
                                                type enumeration {
                                                        enum "authNone";
                                                        enum "authPlain";
                                                        enum "authCipher";
                                                }
                                        }

                                        choice localCookieMode {
                                    default authNone;
                                    config true;
                                                case authNone {
                                                when "localCookieAutoMode = 'authNone'";

                                                }
                                                case authPlain {
                                                when "localCookieAutoMode = 'authPlain'";
                                                        leaf localCookieLength {
                                                                config "true";
                                                                default "4";
                                                                type enumeration {
                                                                        enum "4";
                                                                        enum "8";
                                                                }
                                                        }
                                                        leaf localHighCookie {
                                                                config "true";
                                                                type "hexBinary"{
                                                                    length "3..6";
                                                                }
                                                        }
                                                        leaf localLowCookie {
                                                                config "true";
                                                                type "hexBinary"{
                                                                    length "3..6";
                                                                }
                                                        }
                                                }
                                                case authCipher {
                                                when "localCookieAutoMode = 'authCipher'";
                                                        leaf localCookieCipher {
                                                                config "true";
                                                                type password {
                                                                        length "1..8";
                                                                }
                                                        }
                                                }
                                        }
                                        leaf remoteCookieAutoMode {
                                                config "true";
                                                mandatory "true";
                                                type enumeration {
                                                        enum "authNone";
                                                        enum "authPlain";
                                                        enum "authCipher";
                                                }
                                        }
                                        choice remoteCookieMode {
                                                default authNone;
                                                config true;
                                                case authNone {
                        when "remoteCookieAutoMode = 'authNone'";
                                                }
                                                case authPlain {
                                                when "remoteCookieAutoMode = 'authPlain'";
                                                        leaf remoteCookieLength {
                                                                config "true";
                                                                default "4";
                                                                type enumeration {
                                                                        enum "4";
                                                                        enum "8";
                                                                }
                                                        }
                                                        leaf remoteHighCookie {
                                                                config "true";
                                                                type "hexBinary"{
                                                                    length "3..6";
                                                                }
                                                        }
                                                        leaf remoteLowCookie {
                                                                config "true";
                                                                type "hexBinary"{
                                                                    length "3..6";
                                                                }
                                                        }
                                                }
                                                case authCipher {
                                                when "remoteCookieAutoMode = 'authCipher'";
                                                        leaf remoteCookieCipher {
                                                                config "true";
                                                                type password {
                                                                        length "1..8";
                                                                }
                                                        }
                                                }
                                        }
                }
                        case auto{
                    when "tnlType = 'auto'";
                                        leaf ctrlName {
                                                config "true";
                                                type string{
                                                        length "1..19";
                                                }
                                                mandatory "true";
                                        }
                                        leaf encapType {
                                                config "true";
                                                mandatory "true";
                                                type enumeration
                                                {
                                                        enum "HDLC";
                                                        enum "Ethernet";
                                                        enum "VLAN";
                                                        enum "ATM";
                                                }
                                        }

                            }
                    }

                        leaf sendPacket {
                                config "false";
                                type "uint64";
                        }
                        leaf sendByte {
                                config "false";
                                type "uint64";
                        }
                        leaf rcvPacket {
                                config "false";
                                type "uint64";
                        }
                        leaf receiveByte {
                                config "false";
                                type "uint64";
                        }
                        leaf recvDropPacket {
                                config "false";
                                type "uint64";
                        }
                        leaf cookieMisDropPacket {
                                config "false";
                                type "uint64";
                        }
                        leaf state {
                                config "false";
                                type enumeration {
                                        enum "down" {
                                                value "0";
                                                description "down:";
                                        }
                                        enum "up" {
                                                value "1";
                                                description "up:";
                                        }
                                }
                        }
                }
        }
}
