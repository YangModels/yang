module ietf-lpwan-schc-compound-ack {
  yang-version 1.1;
  namespace "urn:ietf:params:xml:ns:yang:ietf-lpwan-schc-compound-ack";
  prefix schc-compound-ack;

  import ietf-schc {
      prefix schc;
  }

 organization
   "IETF IPv6 over Low Power Wide-Area Networks (lpwan)
    working group";
  contact
    "WG Web:   <https://datatracker.ietf.org/wg/lpwan/about/>
     WG List:  <mailto:lp-wan@ietf.org>
     Editor:   Laurent Toutain
       <mailto:laurent.toutain@imt-atlantique.fr>
     Editor:   Juan Carlos Zuniga
       <mailto:j.c.zuniga@ieee.org>";
  description
     "
     Copyright (c) 2021 IETF Trust and the persons identified as
     authors of the code.  All rights reserved.
     Redistribution and use in source and binary forms, with or
     without modification, is permitted pursuant to, and subject to
     the license terms contained in, the Simplified BSD License set
     forth in Section 4.c of the IETF Trust's Legal Provisions
     Relating to IETF Documents
     (https://trustee.ietf.org/license-info).
     This version of this YANG module is part of RFC XXXX
     (https://www.rfc-editor.org/info/rfcXXXX); see the RFC itself
     for full legal notices.
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     ***************************************************************

     This module extends the ietf-schc module to include the
     Compound ACK behavior for ACK-on-Error as defined in RFC YYYY.
     It introduces a new leaf for ACK-on-Error defining the format
     of the SCHC Compound ACK, adding the possibility to send
     several bitmaps in a single SCHC ACK message.";

  revision 2022-02-08 {
    description
      "Initial version for RFC YYYY ";
    reference
      "RFC YYYY: SCHC Compound ACK";
  }

  identity bitmap-format-base-type {
    description
      "Define how the bitmap is formed in ACK messages.";
  }

  identity bitmap-RFC8724 {
    base bitmap-format-base-type;
    description
      "Bitmap by default as defined in RFC8724.";
  }

  identity bitmap-compound-ack {
    base bitmap-format-base-type;
    description
      "Compound ACK.";
  }

  typedef bitmap-format-type {
    type identityref {
      base bitmap-format-base-type;
    }
    description
      "type used in rules";
  }

  augment "/schc:schc/schc:rule/schc:nature/schc:fragmentation/schc:mode/schc:ack-on-error" {
    leaf bitmap-format {
        when "derived-from(../schc:fragmentation-mode, 'schc:fragmentation-mode-ack-on-error')";
        type schc-compound-ack:bitmap-format-type;
        default "schc-compound-ack:bitmap-RFC8724";
        description
           "How the bitmaps are included in the SCHC ACK message.";
    }

        leaf last-bitmap-compression {
        when "derived-from(../schc:fragmentation-mode, 'schc:fragmentation-mode-ack-on-error')";
        type boolean;
        default true;
        description
            "when true ultimate bitmap in the SCHC ACK message
             can be compressed";
        }

    description
      "added to SCHC rules";
  }

}
