module ietf-te-topology-sf-state {
  yang-version 1.1;
  namespace "urn:ietf:params:xml:ns:yang:ietf-te-topology-sf-state";

  prefix "tet-sf-s";

  import ietf-te-topology-sf {
    prefix "tet-sf";
    reference
      "RFC XXXX: SF Aware TE Topology YANG Model";
  }

  import ietf-network-state {
    prefix "nw-s";
    reference
      "RFC 8345: A YANG Data Model for Network Topologies";
  }

  import ietf-network-topology-state {
    prefix "nt-s";
    reference
      "RFC 8345: A YANG Data Model for Network Topologies";
  }

  import ietf-te-topology-state {
    prefix "tet-s";
    reference
      "RFC 8795: YANG Data Model for Traffic Engineering (TE)
       Topologies";
  }

  organization
    "Traffic Engineering Architecture and Signaling (TEAS)
     Working Group";

  contact
    "WG Web:   <http://tools.ietf.org/wg/teas/>
     WG List:  <mailto:teas@ietf.org>

     Editors:  Igor Bryskin
               <mailto:Igor.Bryskin@huawei.com>

               Xufeng Liu
               <mailto:xufeng.liu.ietf@gmail.com>";

  description
    "Network service and function aware aware TE topology operational
     state model for non-NMDA compliant implementations.

     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (http://trustee.ietf.org/license-info).

     This version of this YANG module is part of RFC XXXX; see the
     RFC itself for full legal notices.";

  revision 2021-02-15 {
    description "Initial revision";
    reference "RFC XXXX: SF Aware TE Topology YANG Model";
  }

  /*
   * Augmentations
   */
  /* Augmentations to network-types/te-topology */
  augment "/nw-s:networks/nw-s:network/nw-s:network-types/"
    + "tet-s:te-topology" {
    description
      "Defines the SF aware TE topology type.";
    uses tet-sf:sf-topology-type;
  }

  /* Augmentations to connectivity-matrix */
  augment "/nw-s:networks/nw-s:network/nw-s:node/tet-s:te/"
    + "tet-s:te-node-attributes" {
    description
      "Parameters for SF aware TE topology.";
    uses tet-sf:service-function-node-augmentation;
  }

  augment "/nw-s:networks/nw-s:network/nw-s:node/tet-s:te/"
        + "tet-s:information-source-entry" {
    description
      "Parameters for SF aware TE topology.";
    uses tet-sf:service-function-node-augmentation;
  }

  /* Augmentations to tunnel-termination-point */
  augment "/nw-s:networks/nw-s:network/nw-s:node/tet-s:te/"
    + "tet-s:tunnel-termination-point" {
    description
      "Parameters for SF aware TE topology.";
    uses tet-sf:service-function-ttp-augmentation;
  }

  /* Augmentations to connectivity-matrix */
  augment "/nw-s:networks/nw-s:network/nw-s:node/tet-s:te/"
    + "tet-s:te-node-attributes/tet-sf-s:service-function/"
    + "tet-sf-s:link-terminations/tet-sf-s:link-termination/"
    + "tet-sf-s:from" {
    description
      "Add reference to the link termination point.
       This portion cannot be shared with the state module.";
    leaf tp-ref {
      type leafref {
        path "../../../../../../../nt-s:termination-point/"
          + "nt-s:tp-id";
      }
      description
        "Reference to the link termination point.";
    }
  }
}
