module ietf-queue-policy {
  yang-version 1.1;
  namespace "urn:ietf:params:xml:ns:yang:ietf-queue-policy";
  prefix queue-policy;

  import ietf-traffic-policy {
    prefix policy;
  }
  import ietf-qos-action {
    prefix action;
  }
  import ietf-diffserv {
    prefix diffserv;
  }

  organization
    "IETF Routing Area Working Group";

  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     configuring diffserv specification implementations.

     Copyright (c) 2021 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2022-10-24 {
    description
      "Initial version";
    reference
      "RFC XXXX: YANG Models for Quality of Service (QoS).";
  }

  augment "/policy:policies/policy:policy/policy:classifier" +
          "/policy:inline/policy:filter" {
    when "derived-from-or-self(../../../policy:type, " +
         "'queue-policy:queue-policy-type')" {
      description
        "If policy type is queue policy, this filter can be used.";
    }

    choice filter-params {
      description
        "Choice of action types";
      case traffic-group-name {
        uses diffserv:traffic-group;
        description
          "traffic group name";
      }
    }
    description
      "Augments Queue policy Classifier with common filter types";
  }

  grouping queue-reference {
    container queue-reference {
      leaf queue-name {
        type string;
        mandatory true;
        description
          "This leaf defines name of the  queue template referenced";
      }
      description
        "queue template reference";
    }
    description
      "queue template reference grouping";
  }

  container queue {
    description
      "Queue template";
    leaf name {
      type string;
      description
        "A unique name identifying this queue template";
    }
    uses action:queue;
  }
  augment "/policy:policies/policy:policy/policy:classifier" +
          "/policy:action/policy:action-params" {
    when "derived-from-or-self(../../policy:type,"  +
         "'queue-policy:queue-policy-type')" {
      description
        "queue policy actions.";
    }
    case queue-template-name {
      uses queue-reference;
    }
    case queue-inline {
      uses action:queue;
    }
    description
      "augments queue template reference to queue policy";
  }
}
