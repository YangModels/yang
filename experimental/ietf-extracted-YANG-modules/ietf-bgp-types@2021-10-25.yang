module ietf-bgp-types {
  yang-version 1.1;
  namespace "urn:ietf:params:xml:ns:yang:ietf-bgp-types";
  prefix bt;

  import ietf-inet-types {
    prefix inet;
  }

  // meta

  organization
    "IETF IDR Working Group";
  contact
    "WG Web:   <http://tools.ietf.org/wg/idr>
     WG List:  <idr@ietf.org>

     Authors: Mahesh Jethanandani (mjethanandani at gmail.com),
              Keyur Patel (keyur at arrcus.com),
              Susan Hares (shares at ndzh.com),
              Jeffrey Haas (jhaas at juniper.net).";

  description
    "This module contains general data definitions for use in BGP.
     It can be imported by modules that make use of BGP attributes.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2021-10-25 {
    description
      "Initial Version";
    reference
      "RFC XXX, BGP Model for Service Provider Network.";
  }

  /*
   * Features.
   */

  feature graceful-restart {
    description
      "Graceful restart as defined in RFC 4724 is supported.";
  }

  feature clear-neighbors {
    description
      "Clearing of BGP neighbors is supported.";
  }

  feature clear-statistics {
    description
      "Clearing of BGP statistics is supported.";
  }

  feature send-communities {
    description
      "Enable the propagation of communities.";
  }

  feature ttl-security {
    description
      "BGP Time To Live (TTL) security check support.";
    reference
      "RFC 5082, The Generalized TTL Security Mechanism (GTSM).";
  }

  feature bfd {
    description
      "Support for BFD detection of BGP neighbor reachability.";
    reference
      "RFC 5880, Bidirectional Forward Detection (BFD),
       RFC 5881, Bidirectional Forward Detection for IPv4 and IPv6
                 (Single Hop),
       RFC 5883, Bidirectional Forwarding Detection (BFD) for
                 Multihop Paths.";
  }

  feature damping {
    description
      "Weighted route dampening is supported.";
  }

  feature clear-routes {
    description
      "Clearing of BGP routes is supported.";
  }

  feature add-paths {
    description
      "Advertisement of multiple paths for the same address prefix
       without the new paths implicitly replacing any previous
       ones.";
    reference
      "RFC 7911: Advertisement of Multiple Paths in BGP.";
  }

  feature route-refresh {
    description
      "Support for the BGP Route Refresh capability.";
    reference
      "RFC 2918: Route Refresh Capability for BGP-4.";
  }

  /*
   * Identities.
   */

  identity bgp-capability {
    description
      "Base identity for a BGP capability";
  }

  identity mp-bgp {
    base bgp-capability;
    description
      "Multi-protocol extensions to BGP";
    reference
      "RFC 4760: Multiprotocol Extentions for BGP-4.";
  }

  identity route-refresh {
    base bgp-capability;
    description
      "The BGP route-refresh functionality";
    reference
      "RFC 2918: Route Refresh Capability for BGP-4.";
  }

  identity asn32 {
    base bgp-capability;
    description
      "4-byte (32-bit) AS number functionality";
    reference
      "RFC6793: BGP Support for Four-Octet Autonomous System (AS)
                Number Space.";
  }

  identity graceful-restart {
    if-feature "graceful-restart";
    base bgp-capability;
    description
      "Graceful restart functionality";
    reference
      "RFC 4724: Graceful Restart Mechanism for BGP.";
  }

  identity add-paths {
    if-feature "add-paths";
    base bgp-capability;
    description
      "Advertisement of multiple paths for the same address prefix
       without the new paths implicitly replacing any previous
       ones.";
    reference
      "RFC 7911: Advertisement of Multiple Paths in BGP.";
  }

  identity afi-safi-type {
    description
      "Base identity type for AFI,SAFI tuples for BGP-4";
    reference
      "RFC4760: Multiprotocol Extentions for BGP-4";
  }

  identity ipv4-unicast {
    base afi-safi-type;
    description
      "IPv4 unicast (AFI,SAFI = 1,1)";
    reference
      "RFC4760: Multiprotocol Extentions for BGP-4";
  }

  identity ipv6-unicast {
    base afi-safi-type;
    description
      "IPv6 unicast (AFI,SAFI = 2,1)";
    reference
      "RFC4760: Multiprotocol Extentions for BGP-4";
  }

  identity ipv4-labeled-unicast {
    base afi-safi-type;
    description
      "Labeled IPv4 unicast (AFI,SAFI = 1,4)";
    reference
      "RFC 3107: Carrying Label Information in BGP-4.";
  }

  identity ipv6-labeled-unicast {
    base afi-safi-type;
    description
      "Labeled IPv6 unicast (AFI,SAFI = 2,4)";
    reference
      "RFC 3107: Carrying Label Information in BGP-4.";
  }

  identity l3vpn-ipv4-unicast {
    base afi-safi-type;
    description
      "Unicast IPv4 MPLS L3VPN (AFI,SAFI = 1,128)";
    reference
      "RFC 4364: BGP/MPLS IP Virtual Private Networks (VPNs).";
  }

  identity l3vpn-ipv6-unicast {
    base afi-safi-type;
    description
      "Unicast IPv6 MPLS L3VPN (AFI,SAFI = 2,128)";
    reference
      "RFC 4659: BGP-MPLS IP Virtual Private Network (VPN) Extension
                 for IPv6 VPN.";
  }

  identity l3vpn-ipv4-multicast {
    base afi-safi-type;
    description
      "Multicast IPv4 MPLS L3VPN (AFI,SAFI = 1,129)";
    reference
      "RFC 6514: BGP Encodings and Procedures for Multicast in
                 MPLS/BGP IP VPNs.";
  }

  identity l3vpn-ipv6-multicast {
    base afi-safi-type;
    description
      "Multicast IPv6 MPLS L3VPN (AFI,SAFI = 2,129)";
    reference
      "RFC 6514: BGP Encodings and Procedures for Multicast in
                 MPLS/BGP IP VPNs.";
  }

  identity l2vpn-vpls {
    base afi-safi-type;
    description
      "BGP-signalled VPLS (AFI,SAFI = 25,65)";
    reference
      "RFC 4761: Virtual Private LAN Service (VPLS) Using BGP for
                 Auto-Discovery and Signaling.";
  }

  identity l2vpn-evpn {
    base afi-safi-type;
    description
      "BGP MPLS Based Ethernet VPN (AFI,SAFI = 25,70)";
  }

  identity bgp-well-known-std-community {
    description
      "Base identity for reserved communities within the standard
       community space defined by RFC 1997. These communities must
       fall within the range 0xFFFF0000 to 0xFFFFFFFF";
    reference
      "RFC 1997: BGP Communities Attribute.";
  }

  identity no-export {
    base bgp-well-known-std-community;
    description
      "Do not export NLRI received carrying this community outside
       the bounds of this autonomous system, or this confederation
       (if the local autonomous system is a confederation member AS).
        This community has a value of 0xFFFFFF01.";
    reference
      "RFC 1997: BGP Communities Attribute.";
  }

  identity no-advertise {
    base bgp-well-known-std-community;
    description
      "All NLRI received carrying this community must not be
       advertised to other BGP peers. This community has a value of
       0xFFFFFF02.";
    reference
      "RFC 1997: BGP Communities Attribute.";
  }

  identity no-export-subconfed {
    base bgp-well-known-std-community;
    description
      "All NLRI received carrying this community must not be
       advertised to external BGP peers - including over
       confederation sub-AS boundaries. This community has a value of
       0xFFFFFF03.";
    reference
      "RFC 1997: BGP Communities Attribute.";
  }

  identity no-peer {
    base bgp-well-known-std-community;
    description
      "An autonomous system receiving NLRI tagged with this community
       is advised not to re-advertise the NLRI to external bilateral
       peer autonomous systems. An AS may also filter received NLRI
       from bilateral peer sessions when they are tagged with this
       community value. This community has a value of 0xFFFFFF04.";
    reference
      "RFC 3765: NOPEER Community for BGP.";
  }

  identity as-path-segment-type {
    description
      "Base AS Path Segment Type. In [BGP-4], the path segment type
       is a 1-octet field with the following values defined.";
    reference
      "RFC 4271: A Border Gateway Protocol 4 (BGP-4), Section 4.3.";
  }
  identity as-set {
    base as-path-segment-type;
    description
      "Unordered set of autonomous systems that a route in the UPDATE
       message has traversed.";
    reference
      "RFC 4271: A Border Gateway Protocol 4 (BGP-4), Section 4.3.";
  }

  identity as-sequence {
    base as-path-segment-type;
    description
      "Ordered set of autonomous systems that a route in the UPDATE
       message has traversed.";
    reference
      "RFC 4271: A Border Gateway Protocol 4 (BGP-4), Section 4.3.";
  }

  identity as-confed-sequence {
    base as-path-segment-type;
    description
      "Ordered set of Member Autonomous Systems in the local
       confederation that the UPDATE message has traversed.";
    reference
      "RFC 5065, Autonomous System Configuration for BGP.";
  }

  identity as-confed-set {
    base as-path-segment-type;
    description
      "Unordered set of Member Autonomous Systems in the local
       confederation that the UPDATE message has traversed.";
    reference
      "RFC 5065, Autonomous System Configuration for BGP.";
  }

  /*
   * Typedefs.
   */

  typedef bgp-session-direction {
    type enumeration {
      enum inbound {
        description
          "Refers to all NLRI received from the BGP peer";
      }
      enum oubound {
        description
          "Refers to all NLRI advertised to the BGP peer";
      }
    }
    description
      "Type to describe the direction of NLRI transmission";
  }

  typedef bgp-well-known-community-type {
    type identityref {
      base bgp-well-known-std-community;
    }
    description
      "Type definition for well-known IETF community attribute
       values.";
    reference
      "IANA Border Gateway Protocol (BGP) Well Known Communities";
  }

  typedef bgp-std-community-type {
    type union {
      type uint32;
      type string {
        pattern '([0-9]|[1-9][0-9]{1,3}|[1-5][0-9]{4}|'
              + '6[0-5][0-9]{3}|66[0-4][0-9]{2}|'
              + '665[0-2][0-9]|6653[0-5]):'
              + '([0-9]|[1-9][0-9]{1,3}|[1-5][0-9]{4}|'
              + '6[0-5][0-9]{3}|66[0-4][0-9]{2}|'
              + '665[0-2][0-9]|6653[0-5])';
      }
    }
    description
      "Type definition for standard community attributes.";
    reference
      "RFC 1997 - BGP Communities Attribute";
  }

  typedef bgp-ext-community-type {
    type union {
      type string {
        // Type 1: 2-octet global and 4-octet local
        //         (AS number)        (Integer)
        pattern '(6[0-5][0-5][0-3][0-5]|[1-5][0-9]{4}|'
              + '[1-9][0-9]{1,4}|[0-9]):'
              + '(4[0-2][0-9][0-4][0-9][0-6][0-7][0-2][0-9][0-6]|'
              + '[1-3][0-9]{9}|[1-9]([0-9]{1,7})?[0-9]|[1-9])';
      }

      type string {
        // Type 2: 4-octet global and 2-octet local
        //         (ipv4-address)     (integer)
        pattern '(([0-9]|[1-9][0-9]|1[0-9][0-9]|2[0-4][0-9]|'
              + '25[0-5])\.){3}([0-9]|[1-9][0-9]|1[0-9][0-9]|'
              + '2[0-4][0-9]|25[0-5]):'
              + '(6[0-5][0-5][0-3][0-5]|[1-5][0-9]{4}|'
              + '[1-9][0-9]{1,4}|[0-9])';
      }

      type string {
        // route-target with Type 1
        // route-target:(ASN):(local-part)
        // 2 octets global and 4 octets local.
        pattern 'route\-target:(6[0-5][0-5][0-3][0-5]|'
              + '[1-5][0-9]{4}|[1-9][0-9]{1,4}|[0-9]):'
              + '(4[0-2][0-9][0-4][0-9][0-6][0-7][0-2][0-9][0-6]|'
              + '[1-3][0-9]{9}|[1-9]([0-9]{1,7})?[0-9]|[1-9])';
      }

      type string {
        // route-target with Type 2
        // route-target:(IPv4):(local-part)
        // 4 bytes of IP address, and 2 bytes for local.
        pattern 'route\-target:'
              + '(([0-9]|[1-9][0-9]|1[0-9][0-9]|2[0-4][0-9]|'
              + '25[0-5])\.){3}([0-9]|[1-9][0-9]|1[0-9][0-9]|'
              + '2[0-4][0-9]|25[0-5]):'
              + '(6[0-5][0-5][0-3][0-5]|[1-5][0-9]{4}|'
              + '[1-9][0-9]{1,4}|[0-9])';
      }

      type string {
        // route-origin with Type 1
        // All 6 octets are open.
        pattern 'route\-origin:(6[0-5][0-5][0-3][0-5]|'
              + '[1-5][0-9]{4}|[1-9][0-9]{1,4}|[0-9]):'
              + '(4[0-2][0-9][0-4][0-9][0-6][0-7][0-2][0-9][0-6]|'
              + '[1-3][0-9]{9}|[1-9]([0-9]{1,7})?[0-9]|[1-9])';
      }

      type string {
        // route-origin with Type 2
        // 4 octets of IP address and two octets of local.
        pattern 'route\-origin:'
              + '(([0-9]|[1-9][0-9]|1[0-9][0-9]|2[0-4][0-9]|'
              + '25[0-5])\.){3}([0-9]|[1-9][0-9]|1[0-9][0-9]|'
              + '2[0-4][0-9]|25[0-5]):'
              + '(6[0-5][0-5][0-3][0-5]|[1-5][0-9]{4}|'
              + '[1-9][0-9]{1,4}|[0-9])';
      }
    }
    description
      "Type definition for extended community attributes";
    reference
      "RFC 4360 - BGP Extended Communities Attribute";
  }

  typedef bgp-community-regexp-type {
    type string;
    description
      "Type definition for communities specified as regular
       expression patterns";
  }

  typedef bgp-origin-attr-type {
    type enumeration {
      enum igp {
        description
          "Origin of the NLRI is internal";
      }
      enum egp {
        description
          "Origin of the NLRI is EGP";
      }
      enum incomplete {
        description
          "Origin of the NLRI is neither IGP or EGP";
      }
    }
    description
      "Type definition for standard BGP origin attribute";
    reference
      "RFC 4271 - A Border Gateway Protocol 4 (BGP-4), Sec 4.3";
  }

  typedef peer-type {
    type enumeration {
      enum internal {
        description
          "Internal (IBGP) peer";
      }
      enum external {
        description
          "External (EBGP) peer";
      }
      enum confederation-internal {
        description
          "Confederation Internal (IBGP) peer.";
      }
      enum confederation-external {
        description
          "Confederation External (EBGP) peer.";
      }
    }
    description
      "Labels a peer or peer group as explicitly internal,
       external, or the related confederation type.";
    reference
      "RFC 4271 - A Border Gateway Protocol 4 (BGP-4), Sec 1.1.
       RFC 5065, Autonomous System Configuration for BGP.";
  }

  identity remove-private-as-option {
    description
      "Base identity for options for removing private autonomous
       system numbers from the AS_PATH attribute";
  }

  identity private-as-remove-all {
    base remove-private-as-option;
    description
      "Strip all private autonomous system numbers from the AS_PATH.
       This action is performed regardless of the other content of
       the AS_PATH attribute, and for all instances of private AS
       numbers within that attribute.";
  }

  identity private-as-replace-all {
    base remove-private-as-option;
    description
      "Replace all instances of private autonomous system numbers in
       the AS_PATH with the local BGP speaker's autonomous system
       number. This action is performed regardless of the other
       content of the AS_PATH attribute, and for all instances of
       private AS number within that attribute.";
  }

  typedef remove-private-as-option {
    type identityref {
      base remove-private-as-option;
    }
    description
      "Set of options for configuring how private AS path numbers
       are removed from advertisements";
  }

  typedef rr-cluster-id-type {
    type union {
      type uint32;
      type inet:ipv4-address;
    }
    description
      "Union type for route reflector cluster ids:
       option 1: 4-byte number
       option 2: IP address";
  }

  typedef community-type {
    type bits {
      bit standard {
        position 0;
        description
          "Send standard communities.";
        reference
          "RFC 1997: BGP Communities Attribute.";
      }
      bit extended {
        description
          "Send extended communities.";
        reference
          "RFC 4360: BGP Extended Communities Attribute.";
      }
      bit large {
        description
          "Send large communities.";
        reference
          "RFC 8092: BGP Large Communities Attribute.";
      }
    }
    description
      "Type describing variations of community attributes.
       The community types can be combined and a value of 0
       implies 'none'";
  }
}
