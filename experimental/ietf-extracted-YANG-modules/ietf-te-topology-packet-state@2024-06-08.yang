module ietf-te-topology-packet-state {
  yang-version 1.1;
  namespace
    "urn:ietf:params:xml:ns:yang:ietf-te-topology-packet-state";

  prefix "tet-pkt-s";

  import ietf-te-topology-packet {
    prefix "tet-pkt";
    reference
      "RFC XXXX: YANG Data Models for Layer 3 and Packet TE Topologies";
  }

  import ietf-network-state {
    prefix "nw-s";
    reference
      "RFC 8345: A YANG Data Model for Network Topologies";
  }

  import ietf-network-topology-state {
    prefix "nt-s";
    reference
      "RFC 8345: A YANG Data Model for Network Topologies";
  }

  import ietf-te-topology-state {
    prefix "tet-s";
    reference
      "RFC 8795: YANG Data Model for Traffic Engineering (TE)
       Topologies";
  }
  import ietf-te-types {
    prefix "te-types";
    reference
      "I-D.ietf-teas-rfc8776-update: Common YANG Data Types for
       Traffic Engineering";
  }

  import ietf-te-packet-types {
    prefix "te-packet-types";
    reference
      "I-D.ietf-teas-rfc8776-update: Common YANG Data Types for
       Traffic Engineering";
  }

  organization
    "Traffic Engineering Architecture and Signaling (TEAS)
     Working Group";

  contact
    "WG Web:   <http://tools.ietf.org/wg/teas/>
     WG List:  <mailto:teas@ietf.org>

     Editor:   Xufeng Liu
               <mailto:xufeng.liu.ietf@gmail.com>

     Editor:   Igor Bryskin
               <mailto:Igor.Bryskin@huawei.com>

     Editor:   Vishnu Pavan Beeram
               <mailto:vbeeram@juniper.net>

     Editor:   Tarek Saad
               <mailto:tsaad@cisco.com>

     Editor:   Himanshu Shah
               <mailto:hshah@ciena.com>

     Editor:   Oscar Gonzalez De Dios
               <mailto:oscar.gonzalezdedios@telefonica.com>";

  description

    "YANG data model for representing operational state information
     of PSC (Packet Switching) TE Topologies, when NMDA is not
     supported.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2024-06-08 {
    description
      "Initial revision";
    reference
      "RFC XXXX: YANG Data Models for Layer 3 and Packet TE Topologies";
  }

  /*
   * Augmentations
   */
  /* Augmentations to network-types */
  augment "/nw-s:networks/nw-s:network/nw-s:network-types/"
        + "tet-s:te-topology" {
    description
      "Defines the packet TE topology type.";
    container packet {
      presence
        "Indicates packet TE topology.";
      description
        "Its presence identifies the packet TE topology type.";
    }
  }

  /* Augmentations to connectivity-matrix */
  augment "/nw-s:networks/nw-s:network/nw-s:node/tet-s:te/"
        + "tet-s:te-node-attributes/tet-s:connectivity-matrices" {
    when "../../../../nw-s:network-types/tet-s:te-topology/"
       + "tet-pkt-s:packet" {
      description
        "Augment only for packet TE topology";

    }
    description
      "Parameters for PSC (Packet Switching) TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:te-node-attributes/tet-s:connectivity-matrices/"
        + "tet-s:connectivity-matrix" {
    when "../../../../../nw-s:network-types/tet-s:te-topology/"
       + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:information-source-entry/"
        + "tet-s:connectivity-matrices" {
    when "../../../../nw-s:network-types/tet-s:te-topology/"
       + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }

  }

  augment "/nw-s:networks/nw-s:network/nw-s:node/tet-s:te/"
        + "tet-s:information-source-entry/"
        + "tet-s:connectivity-matrices/"
        + "tet-s:connectivity-matrix" {
    when "../../../../../nw-s:network-types/tet-s:te-topology/"
       + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  /* Augmentations to tunnel-termination-point */
  augment "/nw-s:networks/nw-s:network/nw-s:node/tet-s:te/"
        + "tet-s:tunnel-termination-point/"
        + "tet-s:local-link-connectivities" {
    when "../../../../nw-s:network-types/tet-s:te-topology/"
       + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nw-s:node/tet-s:te/"
        + "tet-s:tunnel-termination-point/"
        + "tet-s:local-link-connectivities/"
        + "tet-s:local-link-connectivity" {
    when "../../../../../nw-s:network-types/tet-s:te-topology/"
       + "tet-pkt-s:packet" {
      description
        "Augment only for packet TE topology";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  /* Augmentations to te-link-attributes */
  augment "/nw-s:networks/tet-s:te/tet-s:templates/"
        + "tet-s:link-template/tet-s:te-link-attributes" {
    when "tet-s:interface-switching-capability "
       + "[tet-s:switching-capability = 'te-types:switching-psc1']" {
      description
        "Valid only for PSC";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nt-s:link/tet-s:te/"
        + "tet-s:te-link-attributes" {
    when "(../../../nw-s:network-types/tet-s:te-topology/"
       + "tet-pkt-s:packet) and "
       + "(tet-s:interface-switching-capability "
       + "[tet-s:switching-capability = "
       + "'te-types:switching-psc1'])" {
      description
        "Valid only for PSC";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  augment "/nw-s:networks/nw-s:network/nt-s:link/tet-s:te/"
        + "tet-s:information-source-entry" {
    when "(../../../nw-s:network-types/tet-s:te-topology/"
       + "tet-pkt-s:packet) and "
       + "(tet-s:interface-switching-capability "
       + "[tet-s:switching-capability = "
       + "'te-types:switching-psc1'])" {
      description
        "Valid only for PSC";
    }
    description
      "Parameters for PSC TE topology.";
    uses te-packet-types:performance-metrics-attributes-packet {
      if-feature tet-pkt:te-performance-metric;
    }
    uses
      te-packet-types:performance-metrics-throttle-container-packet {
      if-feature tet-pkt:te-performance-metric;
    }
  }

  /* Augmentations to interface-switching-capability */
  augment "/nw-s:networks/tet-s:te/tet-s:templates/"
        + "tet-s:link-template/tet-s:te-link-attributes/"
        + "tet-s:interface-switching-capability" {
    when "tet-s:switching-capability = 'te-types:switching-psc1' " {
      description
        "Valid only for PSC";
    }
    description
      "Parameters for PSC TE topology.";
    uses tet-pkt:packet-switch-capable-container;
  }

  augment "/nw-s:networks/nw-s:network/nt-s:link/tet-s:te/"
        + "tet-s:te-link-attributes/"
        + "tet-s:interface-switching-capability" {
    when "(../../../../nw-s:network-types/tet-s:te-topology/"
       + "tet-pkt-s:packet) and "
       + "(tet-s:switching-capability = 'te-types:switching-psc1')" {
      description
        "Valid only for PSC";
    }
    description
      "Parameters for PSC TE topology.";
    uses tet-pkt:packet-switch-capable-container;
  }

  augment "/nw-s:networks/nw-s:network/nt-s:link/tet-s:te/"
        + "tet-s:information-source-entry/"
        + "tet-s:interface-switching-capability" {
    when "(../../../../nw-s:network-types/tet-s:te-topology/"
       + "tet-pkt-s:packet) and "
       + "(tet-s:switching-capability = 'te-types:switching-psc1')" {
      description
        "Valid only for PSC";
    }
    description
      "Parameters for PSC TE topology.";
    uses tet-pkt:packet-switch-capable-container;
  }

  /*
   * Augment TE bandwidth
   */

  augment "/nw-s:networks/nw-s:network/nw-s:node/"
        + "nt-s:termination-point/tet-s:te/"
        + "tet-s:interface-switching-capability/"
        + "tet-s:max-lsp-bandwidth/"
        + "tet-s:te-bandwidth/tet-s:technology" {
    when "../../../../../../nw-s:network-types/tet-s:te-topology/"
       + "tet-pkt-s:packet" {
      description
        "Augmentation parameters apply only for networks with
         Packet TE topology type.";
    }
    description
      "Augment maximum LSP TE bandwidth for the link termination
       point (LTP).";
    case packet {
      uses te-packet-types:te-packet-path-bandwidth;
    }
  }

  augment "/nw-s:networks/nw-s:network/nw-s:node/tet-s:te/"
        + "tet-s:te-node-attributes/tet-s:connectivity-matrices/"
        + "tet-s:path-constraints/tet-s:te-bandwidth/"
        + "tet-s:technology" {
    when "../../../../../../nw-s:network-types/tet-s:te-topology/"
       + "tet-pkt-s:packet" {
      description
        "Augmentation parameters apply only for networks with
         Packet TE topology type.";
    }
    description
      "Augment TE bandwidth path constraints of the TE node
       connectivity matrices.";
    case packet {
      uses te-packet-types:te-packet-link-bandwidth;
    }
  }

  augment "/nw-s:networks/nw-s:network/nw-s:node/tet-s:te/"
        + "tet-s:te-node-attributes/tet-s:connectivity-matrices/"
        + "tet-s:connectivity-matrix/"
        + "tet-s:path-constraints/tet-s:te-bandwidth/"
        + "tet-s:technology" {
    when "../../../../../../../nw-s:network-types/tet-s:te-topology/"
       + "tet-pkt-s:packet" {
      description
        "Augmentation parameters apply only for networks with
         Packet TE topology type.";
    }
    description
      "Augment TE bandwidth path constraints of the
       connectivity matrix entry.";
    case packet {
      uses te-packet-types:te-packet-link-bandwidth;
    }
  }

  augment "/nw-s:networks/nw-s:network/nw-s:node/tet-s:te/"
        + "tet-s:information-source-entry/"
        + "tet-s:connectivity-matrices/tet-s:path-constraints/"
        + "tet-s:te-bandwidth/tet-s:technology" {
    when "../../../../../../nw-s:network-types/tet-s:te-topology/"
       + "tet-pkt-s:packet" {
      description
        "Augmentation parameters apply only for networks with
         Packet TE topology type.";
    }
    description
      "Augment TE bandwidth path constraints of the TE node
       connectivity matrices information source.";
    case packet {
      uses te-packet-types:te-packet-link-bandwidth;
    }
  }

  augment "/nw-s:networks/nw-s:network/nw-s:node/tet-s:te/"
        + "tet-s:information-source-entry/"
        + "tet-s:connectivity-matrices/tet-s:connectivity-matrix/"
        + "tet-s:path-constraints/tet-s:te-bandwidth/"
        + "tet-s:technology" {
    when "../../../../../../../nw-s:network-types/tet-s:te-topology/"
       + "tet-pkt-s:packet" {
      description
        "Augmentation parameters apply only for networks with
         Packet TE topology type.";
    }
    description
      "Augment TE bandwidth path constraints of the
       connectivity matrix entry information source";
    case packet {
      uses te-packet-types:te-packet-link-bandwidth;
    }
  }

  augment "/nw-s:networks/nw-s:network/nw-s:node/tet-s:te/"
        + "tet-s:tunnel-termination-point/"
        + "tet-s:client-layer-adaptation/tet-s:switching-capability/"
        + "tet-s:te-bandwidth/tet-s:technology" {
    when "../../../../../../nw-s:network-types/tet-s:te-topology/"
       + "tet-pkt-s:packet" {
      description
        "Augmentation parameters apply only for networks with
         Packet TE topology type.";
    }
    description
      "Augment client TE bandwidth of the tunnel termination point
       (TTP)";
    case packet {
      uses te-packet-types:te-packet-link-bandwidth;
    }
  }

  augment "/nw-s:networks/nw-s:network/nw-s:node/tet-s:te/"
        + "tet-s:tunnel-termination-point/"
        + "tet-s:local-link-connectivities/tet-s:path-constraints/"
        + "tet-s:te-bandwidth/tet-s:technology" {
    when "../../../../../../nw-s:network-types/tet-s:te-topology/"
       + "tet-pkt-s:packet" {
      description
        "Augmentation parameters apply only for networks with
         Packet TE topology type.";
    }
    description
      "Augment TE bandwidth path constraints for the TTP
       Local Link Connectivities.";
    case packet {
      uses te-packet-types:te-packet-link-bandwidth;
    }
  }

  augment "/nw-s:networks/nw-s:network/nw-s:node/tet-s:te/"
        + "tet-s:tunnel-termination-point/"
        + "tet-s:local-link-connectivities/"
        + "tet-s:local-link-connectivity/tet-s:path-constraints/"
        + "tet-s:te-bandwidth/tet-s:technology" {
    when "../../../../../../../nw-s:network-types/tet-s:te-topology/"
       + "tet-pkt-s:packet" {
      description
        "Augmentation parameters apply only for networks with
         Packet TE topology type.";
    }
    description
      "Augment TE bandwidth path constraints for the TTP
       Local Link Connectivity entry.";
    case packet {
      uses te-packet-types:te-packet-link-bandwidth;
    }
  }

  augment "/nw-s:networks/nw-s:network/nt-s:link/tet-s:te/"
        + "tet-s:te-link-attributes/"
        + "tet-s:interface-switching-capability/"
        + "tet-s:max-lsp-bandwidth/"
        + "tet-s:te-bandwidth/tet-s:technology" {
    when "../../../../../../nw-s:network-types/tet-s:te-topology/"
       + "tet-pkt-s:packet" {
      description
        "Augmentation parameters apply only for networks with
         Packet TE topology type.";
    }
    description
      "Augment maximum LSP TE bandwidth for the TE link.";
    case packet {
      uses te-packet-types:te-packet-path-bandwidth;
    }
  }

  augment "/nw-s:networks/nw-s:network/nt-s:link/tet-s:te/"
        + "tet-s:te-link-attributes/"
        + "tet-s:max-link-bandwidth/"
        + "tet-s:te-bandwidth/tet-s:technology" {
    when "../../../../../nw-s:network-types/tet-s:te-topology/"
       + "tet-pkt-s:packet" {
      description
        "Augmentation parameters apply only for networks with
         Packet TE topology type.";
    }
    description
      "Augment maximum TE bandwidth for the TE link";
    case packet {
      uses te-packet-types:te-packet-link-bandwidth;
    }
  }

  augment "/nw-s:networks/nw-s:network/nt-s:link/tet-s:te/"
        + "tet-s:te-link-attributes/"
        + "tet-s:max-resv-link-bandwidth/"
        + "tet-s:te-bandwidth/tet-s:technology" {
    when "../../../../../nw-s:network-types/tet-s:te-topology/"
       + "tet-pkt-s:packet" {
      description
        "Augmentation parameters apply only for networks with
         Packet TE topology type.";
    }
    description
      "Augment maximum reservable TE bandwidth for the TE link";
    case packet {
      uses te-packet-types:te-packet-link-bandwidth;
    }
  }

  augment "/nw-s:networks/nw-s:network/nt-s:link/tet-s:te/"
        + "tet-s:te-link-attributes/"
        + "tet-s:unreserved-bandwidth/"
        + "tet-s:te-bandwidth/tet-s:technology" {
    when "../../../../../nw-s:network-types/tet-s:te-topology/"
       + "tet-pkt-s:packet" {
      description
        "Augmentation parameters apply only for networks with
         Packet TE topology type.";
    }
    description
      "Augment unreserved TE bandwidth for the TE Link";
    case packet {
      uses te-packet-types:te-packet-link-bandwidth;
    }
  }
  augment "/nw-s:networks/nw-s:network/nt-s:link/tet-s:te/"
        + "tet-s:information-source-entry/"
        + "tet-s:interface-switching-capability/"
        + "tet-s:max-lsp-bandwidth/"
        + "tet-s:te-bandwidth/tet-s:technology" {
    when "../../../../../../nw-s:network-types/tet-s:te-topology/"
       + "tet-pkt-s:packet" {
      description
        "Augmentation parameters apply only for networks with
         Packet TE topology type.";
    }
    description
      "Augment maximum LSP TE bandwidth for the TE link
       information source";
    case packet {
      uses te-packet-types:te-packet-path-bandwidth;
    }
  }

  augment "/nw-s:networks/nw-s:network/nt-s:link/tet-s:te/"
        + "tet-s:information-source-entry/"
        + "tet-s:max-link-bandwidth/"
        + "tet-s:te-bandwidth/tet-s:technology" {
    when "../../../../../nw-s:network-types/tet-s:te-topology/"
       + "tet-pkt-s:packet" {
      description
        "Augmentation parameters apply only for networks with
         Packet TE topology type.";
    }
    description
      "Augment maximum TE bandwidth for the TE link
       information source";
    case packet {
      uses te-packet-types:te-packet-link-bandwidth;
    }
  }

  augment "/nw-s:networks/nw-s:network/nt-s:link/tet-s:te/"
        + "tet-s:information-source-entry/"
        + "tet-s:max-resv-link-bandwidth/"
        + "tet-s:te-bandwidth/tet-s:technology" {
    when "../../../../../nw-s:network-types/tet-s:te-topology/"
       + "tet-pkt-s:packet" {
      description
        "Augmentation parameters apply only for networks with
         Packet TE topology type.";
    }
    description
      "Augment maximum reservable TE bandwidth for the TE link
       information-source";
    case packet {
      uses te-packet-types:te-packet-link-bandwidth;
    }
  }

  augment "/nw-s:networks/nw-s:network/nt-s:link/tet-s:te/"
        + "tet-s:information-source-entry/"
        + "tet-s:unreserved-bandwidth/"
        + "tet-s:te-bandwidth/tet-s:technology" {
    when "../../../../../nw-s:network-types/tet-s:te-topology/"
       + "tet-pkt-s:packet" {
      description
        "Augmentation parameters apply only for networks with
         Packet TE topology type.";
    }
    description
      "Augment unreserved TE bandwidth of the TE link
       information source";
    case packet {
      uses te-packet-types:te-packet-link-bandwidth;
    }
  }

  augment "/nw-s:networks/tet-s:te/tet-s:templates/"
        + "tet-s:link-template/tet-s:te-link-attributes/"
        + "tet-s:interface-switching-capability/"
        + "tet-s:max-lsp-bandwidth/"
        + "tet-s:te-bandwidth/tet-s:technology" {
    description
      "Augment maximum LSP TE bandwidth of the TE link
       template";
    case packet {
      uses te-packet-types:te-packet-path-bandwidth;
    }
  }

  augment "/nw-s:networks/tet-s:te/tet-s:templates/"
        + "tet-s:link-template/tet-s:te-link-attributes/"
        + "tet-s:max-link-bandwidth/"
        + "tet-s:te-bandwidth/tet-s:technology" {
    description
      "Augment maximum TE bandwidth the TE link template";
    case packet {
      uses te-packet-types:te-packet-link-bandwidth;
    }
  }
  augment "/nw-s:networks/tet-s:te/tet-s:templates/"
        + "tet-s:link-template/tet-s:te-link-attributes/"
        + "tet-s:max-resv-link-bandwidth/"
        + "tet-s:te-bandwidth/tet-s:technology" {
    description
      "Augment maximum reservable TE bandwidth for the TE link
       template.";
    case packet {
      uses te-packet-types:te-packet-link-bandwidth;
    }
  }

  augment "/nw-s:networks/tet-s:te/tet-s:templates/"
        + "tet-s:link-template/tet-s:te-link-attributes/"
        + "tet-s:unreserved-bandwidth/"
        + "tet-s:te-bandwidth/tet-s:technology" {
    description
      "Augment unreserved TE bandwidth the TE link template";
    case packet {
      uses te-packet-types:te-packet-link-bandwidth;
    }
  }
}
