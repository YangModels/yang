module ietf-alarms-x733 {
  namespace "urn:ietf:params:xml:ns:yang:ietf-alarms-x733";
  prefix x733;

  import ietf-alarms {
    prefix al;
  }

  organization
    "IETF NETMOD (NETCONF Data Modeling Language) Working Group";

  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     Editor:   Stefan Vallin
               <mailto:svallin@cisco.com>

     Editor:   Martin Bjorklund
               <mailto:mbj@tail-f.com>";

  description
    "This module augments the ietf-alarms module with X.733 mapping
      information. The following is augemented with event type and
      probable cause:
      1) alarm inventory: every candidate alarm.
      2) alarm: every alarm in the system
      3) alarm notification: notifications indicating alarm state
         changes.
      The module also allows (a feature) the alarm management system
      to configure the mapping.";

  reference
    "ITU Recommendation X.733, 'Information Technology - Open
     Systems Interconnection - System Management: Alarm
     Reporting Function', 1992";

  revision 2015-05-04 {
    description
      "Initial revision.";
    reference
      "RFC XXXX: YANG Alarm Module";
  }

  feature configure-x733-mapping {
    description
      "The system can support configurable X733 mapping from
       alarm-type to event-type and probable cause.";
  }

  typedef event-type  {
    type enumeration {
      enum other {
        value 1;
        description
          "";
      }
      enum communicationsAlarm {
        value 2;
        description
          "An alarm of this type is principally associated with the
           procedures and/or processes required to convey
           information from one point to another";
      }
      enum qualityOfServiceAlarm {
        value 3;
        description
          "An alarm of this type is principally associated with a
           degradation in the quality of a service";
      }
      enum processingErrorAlarm {
        value 4;
        description
          "An alarm of this type is principally associated with a
           software or processing fault";
      }
      enum equipmentAlarm {
        value 5;
        description
          "An alarm of this type is principally associated with an
           equipment fault";
      }
      enum environmentalAlarm {
        value 6;
        description
          "An alarm of this type is principally associated with a
          condition relating to an enclosure in which the equipment
          resides.";
      }
      enum integrityViolation {
        value 7;
        description
          "";
      }
      enum operationalViolation {
        value 8;
        description
          "";
      }
      enum physicalViolation {
        value 9;
        description
          "";
      }
      enum securityServiceOrMechanismViolation {
        value 10;
        description
          "";
      }
      enum timeDomainViolation {
        value 11;
        description
          "";
      }
    }
    description
      "The event types as defined by X.733. The use of the term
       'event' is a bit confusing. In an alarm context these are
       top level alarm types.";
    reference
      "ITU Recommendation X.736, 'Information Technology - Open
       Systems Interconnection - System Management: Security
       Alarm Reporting Function', 1992";
  }

  augment "/al:alarms/al:alarm-inventory/al:alarm-type" {
    leaf event-type {
      type event-type;
      description
        "The alarm type has this X.733 event-type.";
    }
    leaf probable-cause {
      type uint32;
      description
        "The alarm type has this X.733 probable cause value.";
    }
    description
      "Augment X.733 mapping information to the alarm inventory.";
  }

  augment "/al:alarms/al:control" {
    description
      "Add X.733 mapping capabilities. ";
    list x733-mapping {
      if-feature configure-x733-mapping;
      key "alarm-type-id alarm-type-qualifier-match";
      description
        "This list allows a management application to control the
         X.733 mapping for all alarm types in the system. Any entry
         in this list will allow the alarm manager to over-ride the
         default X.733 mapping in the system and the final mapping
         will be shown in the alarm-inventory";

      leaf alarm-type-id {
        type al:alarm-type-id;
        description
          "Map the alarm type with this alarm type identifier.";
      }
      leaf alarm-type-qualifier-match {
        type string;
        description
          "A W3C regular expression that is used when mapping an
           alarm type and specific problem to X.733 parameters.";
      }

      leaf event-type {
        type event-type;
        mandatory true;
        description
          "The event type as defined in X.733/X.736.";
      }

      leaf probable-cause {
        type uint32;
        description
          "The probable cause for the alarm originally defined by
           X.733 and subsequent standards.  Due to the history of
           problems in maintaining a standardized probable cause the
           probable cause is not unique. A best effort mapping of
           the alarm to existing probable causes are used.";
      }
    }
  }

  /*
   * Add X.733 parameters to alarm and notification.
   */
  augment "/al:alarms/al:alarm-list/al:alarm" {
    description
      "Augment X.733 information to the alarm.";
    leaf event-type {
      type event-type;
      description
        "The X.733 event type for this alarms.";
    }
    leaf probable-cause {
      type uint32;
      description
        "The X.733 probable cause for this alarm.";
    }
  }

  augment "/al:alarm-notification" {
    description
      "Augment X.733 information to the alarm notification.";
    leaf event-type {
      type event-type;
      description
        "The X.733 event type for this alarms.";
    }
    leaf probable-cause {
      type uint32;
      description
        "The X.733 probable cause for this alarm.";
    }
  }
}
