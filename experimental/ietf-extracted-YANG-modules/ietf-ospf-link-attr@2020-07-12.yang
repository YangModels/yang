module ietf-ospf-link-attr {
  yang-version 1.1;
  namespace "urn:ietf:params:xml:ns:yang:ietf-ospf-link-attr";

  prefix ospf-link-attr;

  import ietf-routing {
    prefix "rt";
    reference "RFC 8349: A YANG Data Model for Routing
               Management (NMDA Version)";
  }

  import ietf-ospf {
    prefix "ospf";
  }

  import ietf-ospfv3-extended-lsa {
    prefix "ospfv3-e-lsa";
  }

  organization
    "IETF LSR - Link State Routing Working Group";

  contact
     "WG Web:   <http://tools.ietf.org/wg/lsr>
      WG List:  <mailto:lsr@ietf.org>

      Author:   Yingzhen Qu
                <mailto:yqu@futurewei.com>
      Author:   Acee Lindem
                <mailto:acee@cisco.com>
      Author:   Stephane Litkowski
                <mailto:slitkows.ietf@gmail.com>";

  description
    "This YANG module defines the configuration and operational
     state for OSPF application specific link attributes feature
     as defined in RFC xxxx.

     This YANG model conforms to the Network Management
     Datastore Architecture (NMDA) as described in RFC 8242.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  reference "RFC XXXX";

  revision 2020-07-12 {
    description
      "Initial version";
    reference
      "RFC XXXX: A YANG Data Model for OSPF application specific
      link attributes.";
  }

  identity sabm-bit {
    description
      "Base identity for sabm bits.";
  }

  identity rsvp-te-bit {
    base sabm-bit;
    description
      "R bit, RSVP-TE.";
  }

  identity sr-policy-bit {
    base sabm-bit;
    description
      "S bit, Segment Routing Policy.";
  }

  identity lfa-bit {
    base sabm-bit;
    description
      "F bit, Loop Free Alternate (LFA). Includes all LFA types.";
  }

  grouping application-specific-link-attributes-sub-tlvs {
    description
      "OSPF Application-Specific Link Attributes (ASLA) sub-TLV.
       The ASLA sub-TLV is a sub-TLV of the OSPFv2 Extended Link
       TLV [RFC7684] and OSPFv3 Router-Link TLV [RFC8362].";

    container application-specific-link-attributes-sub-tlvs {
      description "Application-Specific Link Attributes sub-TLV.";
      list asla-sub-tlvs {
        leaf sabm-length {
          type uint8;
          description
            "Standard Application Identifier Bit Mask Length in
             octets.";
        }
        leaf udabm-length {
          type uint8;
          description
          "User Defined Application Identifier Bit Mask Length
          in octets.";
        }
        container sabm {
          leaf-list sabm-bits {
            type identityref {
              base sabm-bit;
            }
            description
              "SABM bits list. This list will contain
               identities for the bits which are set in the
               SABA bits.";
          }
          description
            "Standard Application Identifier Bit Mask.";
        }
        container udabm {
          description
            "User Defined Application Identifier Bit Mask.
             This container is to be augmented by user defined
             applications.";
        }
        container link-attributes-sub-sub-tlvs {
          uses ospf:unknown-tlvs;
          description
            "Link Attributes sub-sub-TLVs.";
        }
      }
    }
  }

  augment "/rt:routing/rt:control-plane-protocols"
        + "/rt:control-plane-protocol/ospf:ospf" {
    when "../rt:type = 'ospf:ospfv2' or "
       + "../rt:type = 'ospf:ospfv3'" {
      description
        "This augments the OSPF routing protocol when used.";
    }
    description
      "This augments OSPF protocol configuration
       with application-specific link attributes.";

    container ospf-link-attr {
      choice link-attr-op-mode {
        mandatory "true";
        leaf legacy {
          type empty;
          description
            "Only send legacy advertisements.";
        }
        leaf transition {
          type empty;
          description
            "Send both application-specific and legacy advertisements.";
        }
        leaf app-specific{
          type empty;
          description
            "Only send application-specific advertisements.";
        }
        description
          "Link attributes mode";
      }
      description
        "Link attributes operation mode.";
    }
  }

  /* Database */
  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "../../../../../../../../../../../../"
       + "rt:type = 'ospf:ospfv2'" {
      description
        "This augmentation is only valid for OSPFv2.";
    }
    description
      "OSPF Application-Specific Link Attributes (ASLA) sub-TLV is
       a sub-TLV of OSPFv2 Extended Link TLV (RFC7684).";

    uses application-specific-link-attributes-sub-tlvs;
  }

  augment "/rt:routing/"
       + "rt:control-plane-protocols/rt:control-plane-protocol/"
       + "ospf:ospf/ospf:areas/ospf:area/ospf:database/"
       + "ospf:area-scope-lsa-type/ospf:area-scope-lsas/"
       + "ospf:area-scope-lsa/ospf:version/ospf:ospfv3/"
       + "ospf:ospfv3/ospf:body/ospfv3-e-lsa:e-router"
       + "/ospfv3-e-lsa:e-router-tlvs/ospfv3-e-lsa:link-tlv" {
       when "'ospf:../../../../../../../../../"
         + "rt:type' = 'ospf:ospfv3'" {
         description
           "This augmentation is only valid for OSPFv3
            E-Router LSAs";
       }
    description
      "Augment OSPFv3 Area scope router-link TLV.";

    uses application-specific-link-attributes-sub-tlvs;
  }

  augment "/rt:routing/"
       + "rt:control-plane-protocols/rt:control-plane-protocol/"
       + "ospf:ospf/ospf:database/"
       + "ospf:as-scope-lsa-type/ospf:as-scope-lsas/"
       + "ospf:as-scope-lsa/ospf:version/ospf:ospfv3/"
       + "ospf:ospfv3/ospf:body/ospfv3-e-lsa:e-router"
       + "/ospfv3-e-lsa:e-router-tlvs/ospfv3-e-lsa:link-tlv" {
       when "'ospf:../../../../../../../"
         + "rt:type' = 'ospf:ospfv3'" {
         description
           "This augmentation is only valid for OSPFv3
            E-Router LSAs";
       }
    description
      "Augment OSPFv3 AS scope router-link TLV.";

    uses application-specific-link-attributes-sub-tlvs;
  }
}
