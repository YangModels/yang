module ietf-data-node-tags {
  yang-version 1.1;
  namespace "urn:ietf:params:xml:ns:yang:ietf-data-node-tags";
  prefix ntags;

  import ietf-netconf-acm {
    prefix nacm;
    reference
    "RFC 8341: Network Configuration Access Control
               Model";
  }
  import ietf-module-tags {
    prefix tags;
    reference
    "RFC 8819: YANG Module Tags ";
  }

  organization
    "IETF NetMod Working Group (NetMod)";
  contact
   "WG Web:  <https://datatracker.ietf.org/wg/netmod/>
    WG List: <mailto:netmod@ietf.org>

    Editor: Qin Wu
            <mailto:bill.wu@huawei.com>

    Editor: Benoit Claise
            <mailto:benoit.claise@huawei.com>

    Editor: Peng Liu
            <mailto:liupengyjy@chinamobile.com>

    Editor: Zongpeng Du
            <mailto:duzongpeng@chinamobile.com>

    Editor: Mohamed Boucadair
            <mailto:mohamed.boucadair@orange.com>";
   // RFC Ed.: replace XXXX with actual RFC number and
   // remove this note.
  description
    "This module describes a mechanism associating data node
     tags with YANG data node within YANG modules. Tags may be IANA
     assigned or privately defined.

     Copyright (c) 2022 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://datatracker.ietf.org/html/rfcXXXX); see the RFC itself
     for full legal notices.";

   // RFC Ed.: update the date below with the date of RFC publication
   // and RFC number and remove this note.
  revision 2022-02-04 {
    description
      "Initial revision.";
    reference
      "RFC XXXX: data node Tags in YANG Modules";
  }
  identity other-data-property {
   description
     "Base identity for data property type.";
  }
  extension opm-tag {
    argument tag;
    description
      "The argument 'tag' is of type 'tag'. This extension statement
       is used by module authors to indicate the opm tags that should
       be added automatically by the system. 'opm-tag' is used to
       classify operation and management data nodes into the three
       categories, object, property, and metric. A data node
       tagged with 'object' tag can be one of container, leaf-list, or
       list. A data node tagged is with the 'property' tag is a leaf
       node. The data node tagged with the 'metric' tag can be one of
       container, leaf-list, list, or leaf. A data nodes tagged
       with either property tag or metric tag are child nodes
       belonging to a specific root data node. Each data node may
       contain one single 'object' tag, or one single 'property' tag,
       or one single 'metric' tag (these tags are mutually
       exclusive). As such,  the origin of the value for the
       pre-defined tags should be set to 'system'.";
  }

  extension metric-type {
    argument tag;
    description
      "The argument 'tag' is of type 'tag'. The metric type can be
       used to provide metric data node classification
       (e.g., loss, jitter, packet loss, counter, gauge,
       summary, unknown) within a YANG module.The initial values of
       the 'metric-type' tag is defined in section 9.2, additional
       metric-type tag value can be added in the future.";
  }

  extension multi-source-tag {
    argument tag;
    description
      "The argument 'tag' is of type 'tag'. The multi-source-tag can
      be used to identify multi-source aggregation type
      (e.g., aggregated,  non-aggregated) related to a metric
      subobject.

      The 'aggregated' multi-source aggregation type allows a large
      number of measurements on metric subobjects from different
      sources of the same type (e.g., line card, each subinterface of
      an aggregated Ethernet interface) to be combined into
      aggregated statistics and reported as one metric subobject
      value.

      The 'non-aggregated'multi-source aggregation type allows
      measurement from each source of the same type (e.g., line
      card, each subinterface of an aggregated Ethernet interface) to
      be reported separately.";
   }

  augment "/tags:module-tags/tags:module" {
    description
      "Augment the Module Tags module with data node tag
       attributes.";
    container data-node-tags {
      description
        "Contains the list of data nodes and their associated data
         object tags.";
      list data-node {
        key "ni-id";
        description
          "Includes a list of data nodes and their associated data
           object tags.";
        leaf ni-id {
          type nacm:node-instance-identifier;
          mandatory true;
          description
            "The YANG data node name.";
        }
       leaf-list tag {
          type tags:tag;
          description
            "Lists the tags associated with the data node within
             the YANG  module.

             See the IANA 'YANG data node Tag Prefixes' registry
             for reserved prefixes and the IANA 'IETF YANG Data
             Object Tags' registry for IETF tags.

             The 'operational' state view of this list is
             constructed using the following steps:

             1) System tags (i.e., tags of 'system' origin) are
                added.
             2) User configured tags (i.e., tags of 'intended'
                origin) are added.
             3) Any tag that is equal to a masked-tag is removed.";
          reference
            "RFC XXXX: data node Tags in YANG Data
                       Modules, Section 9";
        }
        leaf-list masked-tag {
          type tags:tag;
          description
            "The list of tags that should not be associated with the
             data node within the YANG module. The user can remove
             (mask) tags from the operational state datastore by
             adding them to this list. It is not an error to add tags
             to this list that are not associated with the data
             object within YANG  module, but they have no operational
             effect.";
        }
       leaf extended-tag-type {
         type identityref {
         base other-data-property;
       }
      description
      "Type of the extended tag. The extended tag type doesn't include opm tag,
       metric-type tag and multi-source tag three types defined in
       this document. The specific extended tag type and associated auxiliary data
       are defined in the data node tags extension module.";
       }
      }
    }
  }
}
