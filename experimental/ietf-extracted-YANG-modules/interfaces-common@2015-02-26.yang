module interfaces-common {
  namespace "urn:ietf:params:xml:ns:yang:interfaces-common";
  prefix if-cmn;

  import ietf-interfaces {
    prefix if;
  }

  import iana-if-type {
    prefix ianaift;
  }

  organization
    "Cisco Systems, Inc.
     Customer Service

     Postal: 170 W Tasman Drive
     San Jose, CA 95134

     Tel: +1 1800 553-NETS

     E-mail: cs-yang@cisco.com";

  contact
    "Robert Wilton - rwilton@cisco.com";

  description
    "This module contains common definitions for extending the IETF
     interface YANG model (RFC 7223) with common configurable layer 2
     properties";

  revision 2015-02-26 {
    description "Latest revision";

    reference "Internet-Draft draft-ietf-rwilton-vlan-yang-00.txt";
  }

  /*
   * Various types of interfaces support a configurable layer 2
   * encapsulation, any that are supported by YANG should be
   * listed here.
   *
   * Different encapsulations can hook into the common encaps-type
   * choice statement.
   */
  augment "/if:interfaces/if:interface" {
    when "if:type = 'ianaift:ethernetCsmacd' or
          if:type = 'ianaift:ieee8023adLag' or
          if:type = 'ianaift:l2vlan'"  {
      description "All interface types that can have a configurable
                   L2 encapsulation";
    }
    description "Add encapsulation top level node to interface types
                 that support a configurable L2 encapsulation";

    container encapsulation {
      description
        "Holds the L2 encapsulation associated with an interfaces";
      choice encaps-type {
        description "Extensible choice of L2 encapsulations";
      }
    }
  }

  /*
   * Various types of interfaces support a configurable layer 2
   * MTU, all of them that are supported by YANG should be
   * listed here.
   */
  augment "/if:interfaces/if:interface" {
    when "if:type = 'ianaift:ethernetCsmacd' or
          if:type = 'ianaift:ieee8023adLag' or
          if:type = 'ianaift:l2vlan'"  {
      description "All interface types that can have a configurable
                   layer 2 MTU";
    }
    description "Add configurable layer-2 MTU to all appropriate
                 interface types";

    leaf l2-mtu {
      type uint16 {
        range "64 .. 65535";
      }
      description
        "The maximum size of layer 2 frame that may be transmitted
         or received on the interface (excluding any FCS overhead).
         In the case of Ethernet interfaces it also excludes the
         4-8 byte overhead of any known (i.e. explicitly matched by
         a child sub-interface) 801.1Q VLAN tags.";
    }
  }

  /*
   * Augments the IETF interfaces model with a leaf that indicates
   * whether traffic is to be transported as layer 2 or layer 3.
   *
   * All interface types that explicitly support forwarding frames
   * at layer 2 and that are supported by YANG should be listed here.
   *
   * Different encapsulation can hook into the common encaps-type
   * choice statement.
   */
  augment "/if:interfaces/if:interface" {
    when "if:type = 'ianaift:ethernetCsmacd' or
          if:type = 'ianaift:ieee8023adLag' or
          if:type = 'ianaift:l2vlan'" {
      description "Any interface types that support layer 2 transport
                   services";
    }
    description "Add a top level node to appropriate interfaces to
                 indicate which tranport layer an interface is
                 operating at";

    leaf transport-layer {
      type enumeration {
        enum layer-2 {
          value 2;
          description "Layer 2 transport";
        }
        enum layer-3 {
          value 3;
          description "Layer 3 transport";
        }
      }
      default layer-3;
      description
        "The transport layer at which the interface is operating at";
    }
  }

  /*
   * Add generic support for sub-interfaces.
   *
   * This should be extended to cover all interface types that are
   * child interfaces of other interfaces.
   */
  augment "/if:interfaces/if:interface" {
    when "if:type = 'ianaift:l2vlan'"  {
      description "Any sub-interfaces";
    }
    description "Add a parent interface field to interfaces to model
                 sub-interfaces";
    leaf parent-interface {
      type if:interface-ref;
      /*
       * TODO - How to make this mandatory without using the
       * mandatory keyword.
       * - Current options appear to be:
       *   - Possibly define a feature "parented-sub-interfaces".
       *   - Create a sub-interface container with presence.
       *   - Enforce the constraint with a must statement.
       */
      //mandatory true;
      description
        "This is the mandatory reference to the parent interface of
         this sub-interface.";
    }
  }
}
