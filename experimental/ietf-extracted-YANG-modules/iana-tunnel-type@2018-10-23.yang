module iana-tunnel-type {
  yang-version 1.1;
  namespace "urn:ietf:params:xml:ns:yang:iana-tunnel-type";
  prefix iana-tunnel-type;

  import iana-if-type  {
    prefix ift;
    reference
      "RFC 7224: IANA Interface Type YANG Module";
  }

  organization
    "IANA";
  contact
    "Internet Assigned Numbers Authority

  Postal: ICANN
          12025 Waterfront Drive, Suite 300
          Los Angeles, CA  90094-2536
          United States of America
  Tel:    +1 310 301 5800
  <mailto:iana@iana.org>";

  description
    "This module contains a collection of YANG identities defined
    by IANA and used as interface types for tunnel interfaces.

    Copyright (c) 2018 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of RFC XXXX; see
    the RFC itself for full legal notices.";

  revision 2018-10-23 {
    description
      "Initial revision.";
    reference
      "RFC XXXX: Tunnel Interface Types YANG Module";
  }
  identity other {
    base ift:tunnel;
    description
      "None of the following values.";
    reference
     "RFC 4087: IP Tunnel MIB";
  }
  identity direct {
    base ift:tunnel;
    description
      "No intermediate header.";
    reference
      "RFC 4087: IP Tunnel MIB";
   }
   identity gre {
     base ift:tunnel;
     description
       "GRE encapsulation.";
     reference
      "RFC 4087: IP Tunnel MIB";
  }
  identity minimal {
    base ift:tunnel;
    description
      "Minimal encapsulation.";
    reference
      "RFC 4087: IP Tunnel MIB";
  }
  identity l2tp {
    base ift:tunnel;
    description
      "L2TP encapsulation.";
   reference
     "RFC 4087: IP Tunnel MIB";
  }
  identity pptp {
    base ift:tunnel;
    description
      "PPTP encapsulation.";
    reference
      "RFC 4087: IP Tunnel MIB";
  }
  identity l2f {
    base ift:tunnel;
    description
      "L2F encapsulation.";
    reference
      "RFC 4087: IP Tunnel MIB";
  }
  identity udp {
    base ift:tunnel;
    description
      "UDP encapsulation.";
    reference
      "RFC 4087: IP Tunnel MIB";
  }
  identity atmp {
    base ift:tunnel;
    description
     "ATMP encapsulation.";
    reference
      "RFC 4087: IP Tunnel MIB";
  }
  identity msdp {
    base ift:tunnel;
    description
      "MSDP encapsulation.";
    reference
      "RFC 4087: IP Tunnel MIB";
  }
  identity sixtofour {
    base ift:tunnel;
    description
      "6to4 encapsulation.";
    reference
      "RFC 4087: IP Tunnel MIB";
  }
  identity sixoverfour {
    base ift:tunnel;
    description
      "6over4 encapsulation.";
    reference
      "RFC 4087: IP Tunnel MIB";
  }
  identity isatap {
    base ift:tunnel;
    description
      "ISATAP encapsulation.";
    reference
      "RFC 4087: IP Tunnel MIB";
  }
  identity teredo {
    base ift:tunnel;
    description
      "Teredo encapsulation.";
    reference
      "RFC 4087: IP Tunnel MIB";
  }
  identity iphttps {
    base ift:tunnel;
    description
      "IP over HTTPS (IP-HTTPS) Tunneling Protocol.";
  }
  identity softwiremesh {
    base ift:tunnel;
    description
      "softwire mesh tunnel.";
    reference
      "RFC 7856: Softwire Mesh Management Information Base (MIB)";
  }
  identity dslite {
    base ift:tunnel;
    description
      "DS-Lite tunnel.";
    reference
      "RFC 7870: Dual-Stack Lite (DS-Lite) Management Information
                 Base (MIB) for Address Family Transition Routers
                 (AFTRs)";
  }
  identity  aplusp {
    base ift:tunnel;
    description
      "A+P encapsulation.";
    reference
      "RFC 6346: The Address plus Port (A+P) Approach to the IPv4
                 Address Shortage";
  }
}
