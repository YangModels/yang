module ietf-fault-types {
    yang-version 1;
    namespace "urn:ietf:params:xml:ns:yang:ietf-fault-types";
    prefix flt-types;

    organization
        "IETF NETMOD (NETCONF Data Modeling Language) Working Group";

    contact
        "WG Web: <http://tools.ietf.org/wg/netmod/>
        WG List: <mailto:netmod@ietf.org>

        Editor: Anurag Sharma
                <mailto:AnSharma@infinera.com>

        Editor: Rajan Rao
                <mailto:rrao@infinera.com>

        Editor: Xian Zhang
                <mailto:zhang.xian@huawei.com>";

    description
        "This module contains Fault data type definitions.";

    revision 2016-06-22 {
        description
                "Initial revision.";
        reference
                "TBD";
    }

    identity probable-cause-type {
        description
                "Base identity from which specific probable cause types
                are derived.";
    }

    identity LOS {
        base probable-cause-type;
        description
                "Loss of Signal.";
    }

    identity LOF {
        base probable-cause-type;
        description
                "Loss of Frame.";
    }

    identity framing-error {
        base probable-cause-type;
        description
                "Framing error probable fault cause.";
    }
    identity fault-type {
        description
                "Base identity from which specific fault types are
                derived.";
    }

    identity communication-fault-type {
        base fault-type;
        description
                "A fault of this type is principally associated with the
                procedures and/or processes required to convey
                information from one point to another.";
        reference "ITU Recommendation X.733";
    }

    identity QoS-fault-type {
        base fault-type;
        description
                "A fault of this type is principally associated with a
                degradation in the quality of a service.";
        reference "ITU Recommendation X.733";
    }

    identity processing-fault-type {
        base fault-type;
        description
                "A fault of this type is principally associated with a
                software or processing fault.";
        reference "ITU Recommendation X.733";
    }

    identity equipment-fault-type {
        base fault-type;
        description
                "A fault of this type is principally associated with an
                equipment fault.";
    }

    identity environmental-fault-type {
        base fault-type;
        description
                "A fault of this type is principally associated with a
                condition relating to an enclosure in which the
                equipment resides.";
    }
}
