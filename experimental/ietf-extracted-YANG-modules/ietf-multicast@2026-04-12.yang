module ietf-multicast {
  yang-version 1.1;
  namespace "urn:ietf:params:xml:ns:yang:ietf-multicast";
  prefix ietf-multicast;

  import ietf-inet-types {
    prefix inet;
    reference
      "RFC 9911: Common YANG Data Types";
  }
  import ietf-routing-types {
    prefix rt-types;
    reference
      "RFC 8294: Common YANG Data Types for the Routing Area";
  }

  organization
    " IETF MBONED (MBONE Deployment) Working Group";
  contact
    "WG Web:   https://datatracker.ietf.org/wg/mboned/
     WG List:  <mailto:mboned@ietf.org>

     Editor:   Zheng Zhang
               <mailto:zhang.zheng@zte.com.cn>
     Editor:   Cui Wang
               <mailto:lindawangjoy@gmail.com>
     Editor:   Ying Cheng
               <mailto:chengying10@chinaunicom.cn>
     Editor:   Xufeng Liu
               <mailto:xufeng.liu.ietf@gmail.com>
     Editor:   Mahesh Sivakumar
               <mailto:sivakumar.mahesh@gmail.com>
    ";

  // RFC Ed.: replace XXXX with actual RFC number and remove
  // this note

  description
    "The module defines the YANG definitions for multicast service
     management. This model can be used to send multicast flow
     information to or retrieve multicast flow information from
     devices, including upstream and downstream node information,
     possible signaling protocols, and the multicast transmission
     protocol that actually carries the multicast flow.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-04-12 {
    description
      "Initial revision.";
    reference
      "RFC XXXX: A YANG Data Model for multicast service management
       YANG.";
  }

  /*
   *feature
   */

  feature bier {
    description
      "Cooperation with BIER technology.";
    reference
      "RFC 8279: Multicast Using Bit Index Explicit Replication
         (BIER)";
  }

  feature bier-te {
    description
      "Cooperation with BIER-TE technology.";
    reference
      "RFC 9262: Tree Engineering for Bit Index Explicit Replication
         (BIER-TE)";
  }

  feature sr-p2mp {
    description
      "Cooperation with multipoint Segment Routing replication
       technology.";
    reference
      "RFC 9524: Segment Routing Replication for Multipoint
         Service Delivery";
  }

  feature ir-tunnel {
    description
      "Cooperation with Ingress Replication tunnel technology.";
    reference
      "RFC 7988: Ingress Replication Tunnels in Multicast VPN";
  }

  feature mldp {
    description
      "Cooperation with MLDP technology.";
    reference
      "RFC 6388: Label Distribution Protocol Extensions
         for Point-to-Multipoint and Multipoint-to-Multipoint
         Label Switched Paths";
  }

  feature p2mp-te {
    description
      "Cooperation with RSVP TE P2MP technology.";
    reference
      "RFC 4875: Extensions to Resource Reservation Protocol -
        Traffic Engineering (RSVP-TE) for Point-to-Multipoint TE
        Label Switched Paths (LSPs)";
  }

  feature pim {
    description
      "Cooperation with PIM technology.";
    reference
      "RFC 7761: Protocol Independent Multicast - Sparse Mode
       (PIM-SM): Protocol Specification (Revised)";
  }

  feature bidir {
    description
      "Cooperation with BIDIR-PIM technology.";
    reference
      "RFC 5015: Bidirectional Protocol Independent Multicast
       (BIDIR-PIM)";
  }

  /*
   *typedef
   */

  typedef ip-multicast-source-address {
    type union {
      type enumeration {
        enum * {
          description
            "Any source address.";
        }
      }
      type inet:ipv4-address;
      type inet:ipv6-address;
    }
    description
      "Multicast source IP address type.";
  }

  /*
   * Identities
   */

  identity dynamic-signaling-type {
    description
      "Base identity for the dynamic signaling type of multicast
       service technology.";
  }

  identity transport-type {
    description
      "Identity for the multicast transport technology.";
  }

  identity tunnel-encap-type {
    description
      "Base identity for the type of multicast flow tunnel
       encapsulation.";
  }

  identity tunnel-encap-vxlan {
    base tunnel-encap-type;
    description
      "The VXLAN encapsulation is used for flow encapsulation.";
    reference
      "RFC 7348: Virtual eXtensible Local Area Network (VXLAN):
        A Framework for Overlaying Virtualized Layer 2 Networks
        over Layer 3 Networks";
  }

  identity tunnel-encap-nvgre {
    base tunnel-encap-type;
    description
      "The NVGRE encapsulation is used for flow encapsulation.";
    reference
      "RFC 7637: NVGRE: Network Virtualization Using Generic
        Routing Encapsulation";
  }

  identity tunnel-encap-geneve {
    base tunnel-encap-type;
    description
      "The GENEVE encapsulation is used for flow encapsulation.";
    reference
      "RFC 8926: Geneve: Generic Network Virtualization
        Encapsulation";
  }

  identity bier-encapsulation{
    description
      "Base identity for BIER encapsulation.";
  }
  identity bier-encap-mpls {
    base bier-encapsulation;
    description
      "This identity represents MPLS encapsulation for bier.";
  }
  identity bier-encap-ipv6 {
    base bier-encapsulation;
    description
      "This identity represents ipv6 encapsulation for bier.";
  }
  identity bier-encap-ethernet {
    base bier-encapsulation;
    description
      "This identity represents ethernet encapsulation for bier.";
  }

  identity signaling-pim {
    base dynamic-signaling-type;
    description
      "Using PIM as multicast service signaling technology.
       This signaling protocol needs to be used in conjunction
       with the transport protocol set to BIER.";
    reference
      "I-D.ietf-bier-pim-signaling: PIM Signaling Through BIER
        Core";
  }

  identity mld {
    base dynamic-signaling-type;
    description
      "Using MLD as multicast service signaling technology.
       This signaling protocol needs to be used in conjunction
       with the transport protocol set to BIER.";
    reference
      "I-D.ietf-bier-mld: BIER Ingress Multicast Flow Overlay
        using Multicast Listener Discovery Protocols";
  }

  identity mld-snooping {
    base dynamic-signaling-type;
    description
      "Using MLD-snooping as multicast service signaling
       technology.";
    reference
      "RFC 4541: Considerations for Internet Group Management
        Protocol (IGMP) and Multicast Listener
        Discovery (MLD) Snooping Switches";
  }

  identity evpn {
    base dynamic-signaling-type;
    description
      "Using EVPN as multicast service signaling technology.";
    reference
      "RFC 7432: BGP MPLS-Based Ethernet VPN
       RFC 9572: Updates on EVPN BUM Procedures
       RFC 9624: EVPN Broadcast, Unknown Unicast, or Multicast
        (BUM) Using Bit Index Explicit Replication (BIER)";
  }

  identity mvpn {
    base dynamic-signaling-type;
    description
      "Using MVPN as multicast service signaling technology.";
    reference
      "RFC 6513: Multicast in MPLS/BGP IP VPNs
       RFC 7716: Global Table Multicast with BGP Multicast VPN
        (BGP-MVPN) Procedures
       RFC 8556: Multicast VPN Using Bit Index Explicit
        Replication (BIER)";
  }

  identity bier {
    base transport-type;
    description
      "Using BIER as multicast transport technology.";
    reference
      "RFC 8279: Multicast Using Bit Index Explicit Replication
        (BIER)";
  }

  identity bier-te {
    base transport-type;
    description
      "Using BIER-TE as multicast transport technology.";
    reference
      "RFC 9262: Traffic Engineering for Bit Index Explicit
        Replication (BIER-TE)";
  }

  identity mldp {
    base transport-type;
    description
      "Using mLDP as multicast transport technology.";
    reference
      "RFC 6388: Label Distribution Protocol Extensions
        for Point-to-Multipoint and Multipoint-to-Multipoint
        Label Switched Paths";
  }

  identity rsvp-te-p2mp {
    base transport-type;
    description
      "Using P2MP TE as multicast transport technology.";
    reference
      "RFC 4875: Extensions to Resource Reservation Protocol
        - Traffic Engineering (RSVP-TE) for Point-to-Multipoint
        TE Label Switched Paths (LSPs)";
  }

  identity sr-p2mp {
    base transport-type;
    description
      "Using Segment Routing  as multicast transport technology.";
    reference
      "I-D.ietf-pim-sr-p2mp-policy:
         Segment Routing Point-to-Multipoint Policy";
  }

  identity pim {
    base transport-type;
    description
      "Using PIM as multicast transport technology.";
    reference
      "RFC 7761: Protocol Independent Multicast - Sparse Mode
        (PIM-SM): Protocol Specification (Revised)";
  }

  identity bidir {
    base transport-type;
    description
      "Using BIDIR-PIM as multicast transport technology.";
    reference
      "RFC 5015: Bidirectional Protocol Independent Multicast
        (BIDIR-PIM)";
  }
  identity event-type {
    description
      "The events of the multicast service.";
  }

  identity service-up {
    base event-type;
    description
      "The multicast service works.";
  }

  identity service-down {
    base event-type;
    description
      "There is something wrong with upstream or downstream node,
       and node can't work properlay.";
  }

  identity protocol-enabled {
    base event-type;
    description
      "The protocol that is used for multicast flows have been
       enabled.";
  }

  identity protocol-disabled {
    base event-type;
    description
      "The protocol that is used by multicast flows have been
       disabled.";
  }

  grouping general-multicast-key {
    description
      "The general multicast keys. They are used to differentiate
       multicast service.";
    leaf vpn-rd {
      type rt-types:route-distinguisher;
      description
        "A Route Distinguisher is used to differentiate
         routes from different MVPNs.
         When the value is set to 0, it indicates that it is
         Global Table Multicast as described in RFC7716.";
      reference
        "RFC 8294: Common YANG Data Types for the Routing Area
         RFC 6513: Multicast in MPLS/BGP IP VPNs
         RFC 7716: Global Table Multicast with BGP Multicast VPN
           (BGP-MVPN) Procedures";
    }
    leaf source-address {
      type ip-multicast-source-address;
      description
        "The IP source address of the multicast flow. The
         value set to * means that the receiver interests
         in all source that relevant to one given group.";
    }
    leaf group-address {
      type rt-types:ip-multicast-group-address;
      mandatory true;
      description
        "The IP group address of multicast flow. This
         type represents a version-neutral IP multicast group
         address. The format of the textual representation
         implies the IP version.";
      reference
        "RFC 8294: Common YANG Data Types for the Routing Area";
    }
  }

  // multicast-key

  grouping bier-key {
    description
      "The key parameters set for BIER/BIER TE forwarding.";
    reference
      "RFC 8279: Multicast Using Bit Index Explicit Replication
        (BIER).";
    leaf sub-domain {
      type uint16;
      description
        "The subdomain ID that the multicast flow belongs to.";
    }
    list tad {
      key "mt-id fa-number data-plane";
      description
        "The associated Multi-Topology ID, Flex Algo number and
         data plane type.";
      leaf mt-id {
        type uint16;
        description
          "The multi-topology ID that the multicast flow belongs
           to.";
        reference
          "RFC 4915: Multi-Topology (MT) Routing in OSPF
           RFC 5120: M-ISIS: Multi Topology (MT) Routing in
             Intermediate System to Intermediate Systems (IS-ISs)";
      }
      leaf fa-number {
        type uint8;
        description
          "Flex-algo number, value between 128 and 255 inclusive.";
        reference
          "RFC 9350: IGP Flexible Algorithm";
      }
      leaf data-plane {
        type uint8;
        description
          "Data plane type used for prefix calculation.";
        reference
          "RFC 9502: IGP Flexible Algorithm in IP Networks
           I-D.ietf-lsr-flex-soft-dataplane: IGP Flex Soft
            Dataplane";
      }
    }
    leaf bitstringlength {
      type uint16;
      description
        "The bitstringlength used by BIER forwarding.";
    }
    leaf bier-encap-type {
      type identityref {
        base bier-encapsulation;
      }
      description
        "The BIER encapsulation that can be used in either MPLS
         networks or non-MPLS networks.";
    }
  }

  grouping transport-tech {
    description
      "The transport technology selected for the multicast service.
       For one specific multicast flow.
       The same multicast flow may be forwarded using multiple
       transport technologies as needed for management purposes.";
    leaf transport {
      type identityref {
        base transport-type;
      }
      description
        "The type of transport technology";
    }
    choice transport-tech-type {
      description
        "The type of transport technology";
      case bier {
        if-feature "bier";
        list bier {
          key "sub-domain";
          description
            "Using BIER as the transport technology.
             The BIER technology is introduced in RFC8279.";
          reference
            "RFC 8296: Encapsulation for Bit Index Explicit
               Replication (BIER) in MPLS and Non-MPLS Networks";
          uses bier-key;
        }
      }
      case bier-te {
        if-feature "bier-te";
        description
          "Using BIER-TE as the transport technology.
           The BIER-TE technology is introduced in RFC9262.";
        reference
          "RFC 9262: Tree Engineering for Bit Index Explicit
             Replication (BIER-TE)";
        list bitstring {
          key "name";
          leaf name {
            type string;
            description
              "The name of the bitstring";
          }
          list bier-te-adj {
            key "adj-id";
            leaf adj-id {
              type uint16;
              description
                "The link adjacency ID used for BIER TE
                 forwarding.";
            }
            description
              "The adjacencies ID used for BIER TE bitstring
               encapsulation.";
          }
          description
            "The bitstring name and detail used for BIER TE
             forwarding encapsulation. One or more bitstring
             can be used for backup path.";
        }
      }
      case mldp {
        if-feature "mldp";
        description
          "Using MLDP as the transport technology.";
        reference
          "RFC 6388: Label Distribution Protocol Extensions
            for Point-to-Multipoint and Multipoint-to-Multipoint
            Label Switched Paths
           RFC 9658:
            Multipoint LDP Extensions for Multi-Topology Routing";
        leaf mt-id {
          type uint16;
          description
            "The multi-topology ID that the multicast flow
             belongs to.";
          reference
            "RFC 4915: Multi-Topology (MT) Routing in OSPF
             RFC 5120: M-ISIS: Multi Topology (MT) Routing in
             Intermediate System to Intermediate Systems (IS-ISs)";
        }
        leaf fa-number {
          type uint8;
          description
            "Flex-algo number, value between 128 and 255
             inclusive.";
          reference
            "RFC 9350: IGP Flexible Algorithm";
        }
      }
      case rsvp-te-p2mp {
        if-feature "p2mp-te";
        description
          "Using RSVP TE P2MP as the transport technology.";
        reference
          "RFC 4875: Extensions to Resource Reservation Protocol -
             Traffic Engineering (RSVP-TE) for Point-to-Multipoint
             TE Label Switched Paths (LSPs)";

        leaf tunnel-name {
          type string;
          description
            "The P2MP TE tunnel name.";
        }
      }
      case pim {
        if-feature "pim";
        description
          "Using PIM as the transport technology.
           By setting the corresponding TAD (Multi-Topology ID,
           FA number, and data plane type), constraint-based
           multicast path establishment can be achieved.";
        reference
          "RFC 7761: Protocol Independent Multicast - Sparse Mode
           (PIM-SM): Protocol Specification (Revised)
           I-D: ietf-pim-flex-algo: Multi-Topology in PIM";
        leaf source-address {
          type ip-multicast-source-address;
          description
            "The IP source address of the multicast flow. The
             value set to * means that the receiver interests
             in all source that relevant to one given group.";
        }
        leaf group-address {
          type rt-types:ip-multicast-group-address;
          mandatory true;
          description
            "The IP group address of multicast flow. This
             type represents a version-neutral IP multicast group
             address. The format of the textual representation
             implies the IP version.";
        }
        leaf bidir {
          if-feature "bidir";
          type boolean;
          description
            "Using BIDIR-PIM as the transport technology.
             When using the bidir technique, only the group address
             needs to be considered.";
          reference
            "RFC 5015: Bidirectional Protocol Independent Multicast
             (BIDIR-PIM)";
        }
        list tad {
          key "mt-id fa-number data-plane";
          description
            "The Multi-Topology ID, Flex Algo number and data plane
             type are used to construct the logical topology,
             which enables constraint-based forwarding.";
          leaf mt-id {
            type uint16;
            description
              "The multi-topology ID.";
            reference
              "RFC 4915: Multi-Topology (MT) Routing in OSPF
               RFC 5120: M-ISIS: Multi Topology (MT) Routing in
                 Intermediate System to Intermediate Systems
                 (IS-ISs)";
          }
          leaf fa-number {
            type uint8;
            description
              "Flex-algo number, value between 128 and 255
               inclusive.";
            reference
              "RFC 9350: IGP Flexible Algorithm";
          }
          leaf data-plane {
            type uint8;
            description
              "Data plane type used for prefix calculation.";
            reference
              "RFC 9502: IGP Flexible Algorithm in IP Networks
               I-D.ietf-lsr-flex-soft-dataplane:
                 IGP Flex Soft Dataplane";
          }
        }
      }
      case ir-tunnel {
        if-feature "ir-tunnel";
        description
          "Using IR (Ingress Replication) P-tunnel for MVPN as the
           transport technology.";
        reference
          "RFC 7988: Ingress Replication Tunnels in Multicast VPN
           RFC 6514: BGP Encodings and Procedures for Multicast
             in MPLS/BGP IP VPNs";
        leaf ir-tunnel-type {
          type uint8;
          description
            "The tunnel type used by MVPN ingress replication.";
        }
      }
      case sr-p2mp {
        if-feature "sr-p2mp";
        description
          "Using SR P2MP as the transport technology.
           The ingress replication and the SR P2MP
           function should not be used at the same time.";
        reference
          "RFC 9524: Segment Routing Replication for Multipoint
             Service Delivery
           I-D.ietf-pim-sr-p2mp-policy: Segment Routing
             Point-to-Multipoint Policy";
      }
      // sr-p2mp
      case native {
        description
          "When this type is set, it indicates that it is a
           normal multicast and no additional transport
           forwarding is required.";
      }
    }
  }

  // transport
  /*signaling*/

  grouping signaling-tech {
    leaf signaling {
      type identityref {
        base dynamic-signaling-type;
      }
      description
        "The type of signaling technology.";
    }
    choice protocol-type {
      description
        "The type of dynamic signaling technology.
         This is only used to indicate the corresponding dynamic
         signaling protocol type.
         The corresponding dynamic signaling protocol information
         can be obtained from the YANG model of each protocol.";
      case evpn {
        description
          "EVPN technology is used for multicast service
           signaling.
           When BIER is used as a transport technology, there is
           specific draft listed below that explain how to
           perform signaling.";
        reference
          "RFC 7432: BGP MPLS-Based Ethernet VPN
           RFC 9624: EVPN Broadcast, Unknown Unicast, or
           Multicast (BUM) Using Bit Index Explicit Replication
           (BIER)";
      }
      case mld {
        description
          "MLD/IGMP can be used as multicast service signaling.
           When BIER is used as a transport technology, there is
           specific draft listed below that explain how to
           perform signaling.";
        reference
          "I-D:ietf-bier-mld: BIER Ingress Multicast Flow Overlay
           using Multicast Listener Discovery Protocols";
      }
      case mld-snooping {
        description
          "MLD/IGMP snooping can be used as multicast service
           signaling.";
        reference
          "RFC 4541:Considerations for Internet Group Management
            Protocol (IGMP) and Multicast Listener Discovery (MLD)
            Snooping Switches";
      }
      case mvpn {
        description
          "MVPN technology is used for multicast service signaling.
           When BIER is used as a transport technology, there is
           specific draft listed below that explain how to
           perform signaling.";
        reference
          "RFC 6513: Multicast in MPLS/BGP IP VPNs
           RFC 7716: Global Table Multicast with BGP Multicast VPN
            (BGP-MVPN) Procedures
           RFC 8556: Multicast VPN Using Bit Index Explicit
            Replication (BIER)";
      }
      case pim {
        description
          "PIM can be used as multicast service signaling.
           When BIER is used as a transport technology, there is
           specific draft listed below that explain how to
           perform signaling.";
        reference
          "RFC 7761: Protocol Independent Multicast - Sparse Mode
            (PIM-SM): Protocol Specification (Revised)
           I-D.ietf-bier-pim-signaling: PIM Signaling Through BIER
            Core";
      }
    }
    description
      "The dynamic signaling protocols.";
  }

  // signaling-tech

  container multicast-service {
    description
      "Multicast service YANG data model. Includes the flow's
       key value, upstream and downstream neighbors,
       and related information.";
    list multicast-flow {
      key "vpn-rd source-address group-address";
      description
        "Multicast flow information, including keys, upstream and
         downstream nodes, possible signaling protocols, and
         transport protocols.";
      uses general-multicast-key;
      container upstream {
        description
          "Upstream node neighbor information and the signaling
           protocol used in the multicast flow.";
        list neighbor {
          key "neighbor-address";
          description
            "The IP address of the upstream node for the multicast
             flow. It can be the ingress node for MVPN, EVPN, and
             BIER.
             In MVPN and EVPN, this is the address of the ingress
             PE; in BIER, it is the BFR prefix of the BFIR.
             To achieve redundant ingress node protection, two or
             more ingress nodes can exist.";
          leaf neighbor-address {
            type inet:ip-address;
            description
              "The IP address of the neighbor.";
          }
          leaf vni-type {
            type identityref {
              base tunnel-encap-type;
            }
            description
              "The encapsulated type for the multicast flow.";
          }
          uses signaling-tech;
        }
      }
      // upstream

      list downstream {
        key "signaling transport";
        description
          "Downstream node neighbor information, the signaling
           protocol and transport protocol used by the multicast
           flow. For different downstream neighbor, different
           signaling and transport technology may be used.";

        list neighbor {
          key "neighbor-address";
          description
            "The IP address of the downstream node for the multicast
             flow. It can be the egress node for MVPN, EVPN, and
             BIER.
             In MVPN and EVPN, this is the address of the egress PE;
             in BIER, it is the BFR prefix of the BFER.";
          leaf neighbor-address {
            type inet:ip-address;
            description
              "The IP address of the neighbor.";
          }
        }
        uses signaling-tech;
        uses transport-tech;
      }
      // downstream
    }
    // multicast-flow
  }

  /*Notifications*/

  notification ingress-egress-event {
    leaf event-type {
      type identityref {
        base event-type;
      }
      description
        "The event type.";
    }
    list multicast-flow {
      key "vpn-rd source-address group-address";
      description
        "Multicast flow information, including keys, upstream and
         downstream nodes, possible signaling protocols, and
         transport protocols.";

      uses general-multicast-key;

      container upstream {
        description
          "Upstream node neighbor information and the signaling
           protocol used in the multicast flow.";

        leaf neighbor-address {
          type inet:ip-address;
          description
            "The IP address of the neighbor.";
        }
        leaf signaling {
          type identityref {
            base dynamic-signaling-type;
          }
          description
            "The type of signaling technology";
        }
      }
      // upstream
      list downstream {
        key "signaling transport";
        description
          "Downstream node neighbor information, the signaling
           protocol and transport protocol used by the multicast
           flow. For different downstream neighbor, different
           signaling and transport technology may be used.";

        leaf neighbor-address {
          type inet:ip-address;
          description
            "The IP address of the neighbor.";
        }
        leaf signaling {
          type identityref {
            base dynamic-signaling-type;
          }
          description
            "The type of signaling technology";
        }
        leaf transport {
          type identityref {
            base transport-type;
          }
          description
            "The type of transport technology";
        }
      }
      // downstream
    }
    // multicast-flow
    description
      "Notification events for the upstream or downstream nodes.
       Like node failure, signaling/ transport module
       loading/ unloading. And the potential failure about some
       multicast flows and associated
       signaling/ transport technologies.";
  }
}
