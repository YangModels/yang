module ietf-mpted-jct {
  yang-version 1.1;
  namespace "urn:ietf:params:xml:ns:yang:ietf-mpted-jct";
  prefix mpted-jct;

  import ietf-te {
    prefix te;
    reference
      "draft-ietf-teas-yang-te: A YANG Data Model for Traffic
       Engineering Tunnels, Label Switched Paths, and Interfaces";
  }
  import ietf-inet-types {
    prefix inet;

    reference
      "RFC6991: Common YANG Data Types";
  }
  import ietf-routing-types {
    prefix rt-types;
    reference
      "RFC8294: Common YANG Data Types for the Routing Area";
  }
  import ietf-mpted {
    prefix mpted;
    reference
      "RFC XXXX: A YANG Data Model for Multipath Traffic
       Engineering Directed Acyclic Graph (MPTED) Tunnels and
       Junctions";
  }

  organization
    "IETF Traffic Engineering Architecture and Signaling (TEAS)
     Working Group.";
  contact
    "WG Web:   <https://datatracker.ietf.org/wg/teas/>
     WG List:  <mailto:teas@ietf.org>

     Editor:   Vishnu Pavan Beeram
               <mailto:vishnupavan.ietf@gmail.com>

     Editor:   Kireeti Kompella
               <mailto:kireeti.ietf@gmail.com>";
  description
    "This module defines a YANG data model for Multipath Traffic
     Engineering Directed Acyclic Graph (MPTED) junctions.  It is
     intended to be used as part of the IETF TEAS framework to
     enable the configuration and management of MPTED junctions on
     an MPTED junction node.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX
     (https://www.rfc-editor.org/info/rfcXXXX); see the RFC
     itself for full legal notices.";

  revision 2026-11-02 {
    description
      "Initial revision.
       This revision introduces the YANG data model for
       Multipath Traffic Engineering Directed Acyclic Graph
       (MPTED) junctions.";

    reference
      "RFC XXXX: A YANG Data Model for Multipath Traffic
       Engineering Directed Acyclic Graph (MPTED) Tunnels and
       Junctions";
  }

  grouping mpted-jct-info {
    description
      "Grouping for junction information.";
    leaf current-jct-instance {
      type uint32;
      description
        "Current instance identifier of the MPTED tunnel
         junction.";
    }
    leaf bandwidth-requested {
      type uint64;
      units "bytes per second";
      description
        "Bandwidth to be reserved for the junction.  A value of
         zero means that no bandwidth is reserved.";
    }
  }

  grouping mpted-jct-status-info {
    description
      "Grouping for junction status information.";
    uses mpted-jct-info;
    leaf mtu {
      type uint16;
      config false;
      description
        "MTU at the junction node.  This is the smallest MTU value
         among the MTUs received from all JCT-NHOPs.";
    }
    leaf status {
      type identityref {
        base mpted:mpted-junction-status;
      }
      config false;
      description
        "Status of the JUNCTION.";
    }
  }

  grouping mpted-jct-hop-info {
    description
      "Grouping for MPTED junction hop information.";
    leaf hop-address {
      type inet:ip-address;
      description
        "IP-address of the peer.";
    }
    leaf hop-index {
      type uint32;
      description
        "Index of the peer interface.";
    }
    leaf hop-version {
      type uint32;
      description
        "Version of the Hop.";
    }
  }

  grouping mpted-jct-nhop-info {
    description
      "Grouping for MPTED junction next-hop information.";
    uses mpted-jct-hop-info;
    leaf backup {
      type boolean;
      description
        "Indicates that the JCT-NHOP is a backup next-hop.";
    }
    leaf load-share {
      type uint16;
      config false;
      description
        "Effective relative load share of the JCT-NHOP.  It is
         derived from the bandwidth-requested values of the
         JCT-NHOPs of the junction.  It is zero for a JCT-NHOP that
         is not active, and it is the same for all active
         JCT-NHOPs if their bandwidth-requested values are all
         zero.";
    }
    leaf bandwidth-requested {
      type uint64;
      units "bytes per second";
      description
        "Bandwidth value of the JCT-NHOP, which determines its
         load share.  Only the ratio of these values across the
         JCT-NHOPs of a junction is used.  It does not by itself
         cause a bandwidth reservation.";
    }
  }

  augment "/te:te" {
    description
      "Augmentation for MPTED junctions.";
    container mpted-junctions {
      description
        "Container for MPTED junctions.";
      list junction {
        key "node-id originator tnl-id tnl-instance-id sig-src";
        unique "name";
        description
          "MPTED junction entry.";
        leaf node-id {

          type inet:ip-address;
          description
            "IP-address of the junction node.";
        }
        leaf originator {
          type inet:ip-address;
          description
            "IP address of the associated MPTED tunnel
             originator.";
        }
        leaf tnl-id {
          type uint32;
          description
            "Identifier of the associated MPTED tunnel.";
        }
        leaf tnl-instance-id {
          type uint32;
          description
            "Instance ID of the associated MPTED tunnel.";
        }
        leaf sig-src {
          type inet:ip-address;
          description
            "IP-address of the MPTED tunnel signaling source.";
        }
        leaf name {
          type string;
          description
            "Name of the associated MPTED tunnel.";
        }
        leaf-list ingress {
          type inet:ip-address;
          description
            "List of ingress nodes of the associated MPTED
             tunnel.";
        }
        leaf-list egress {
          type inet:ip-address;
          description
            "List of egress nodes of the associated MPTED
             tunnel.";
        }
        leaf type {
          type identityref {
            base mpted:mpted-tunnel-type;
          }
          description
            "Type of associated tunnel.";

        }
        leaf setup-priority {
          type uint8 {
            range "0..7";
          }
          default "7";
          description
            "The priority of the associated MPTED tunnel with
             respect to taking resources, in the range of 0 to 7.
             The value 0 is the highest priority.";
        }
        leaf hold-priority {
          type uint8 {
            range "0..7";
          }
          default "7";
          description
            "The priority of the associated MPTED tunnel with
             respect to holding resources, in the range of 0 to 7.
             The value 0 is the highest priority.";
        }
        uses mpted-jct-status-info;
        container phops {
          description
            "Container for associated JCT-PHOPs.";
          list phop {
            key "hop-address hop-index hop-version";
            uses mpted-jct-hop-info;
            description
              "JCT-PHOP entry.";
            leaf in-label {
              type rt-types:mpls-label;
              config false;
              description
                "Label used by incoming packets
                 on the JCT-PHOP.";
            }
            leaf status {
              type identityref {
                base mpted:mpted-jct-phop-status;
              }
              config false;
              description
                "Status of the JCT-PHOP.";
            }
          }
        }
        container nhops {

          description
            "Container for associated JCT-NHOPs.";
          list nhop {
            key "hop-address hop-index hop-version";
            description
              "JCT-NHOP entry.";
            uses mpted-jct-nhop-info;
            leaf bandwidth-reserved {
              type uint64;
              units "bytes per second";
              config false;
              description
                "Amount of bandwidth reserved on the TE link
                 associated with the JCT-NHOP.  It is zero if the
                 bandwidth of the junction is zero.  It is also
                 zero for a backup JCT-NHOP, because the RSVP-TE
                 signaling for MPTED tunnels
                 (draft-kbr-teas-mptersvp) does not reserve
                 bandwidth toward backup next-hops.";
            }
            leaf out-label {
              type rt-types:mpls-label;
              config false;
              description
                "Label used by outgoing packets
                 on the JCT-NHOP.";
            }
            leaf status {
              type identityref {
                base mpted:mpted-jct-nhop-status;
              }
              config false;
              description
                "Status of the JCT-NHOP.";
            }
          }
        }
      }
    }
  }
}
