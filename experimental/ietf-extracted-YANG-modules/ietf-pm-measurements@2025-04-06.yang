module ietf-pm-measurements {
    yang-version 1.1;
    namespace "urn:ietf:params:xml:ns:yang:ietf-pm-measurements";
    prefix pm-meas;

    /*
     * Import YANG Type
     */
    import ietf-yang-types {
        prefix yang;
        reference
          "RFC 6991: Common YANG Data Types";
    }

    import ietf-pm-parameters {
        prefix pm-param;
        reference
          "draft-ietf-ccamp-pm-parameters-yang";
    }

    organization
      "IETF Common Control and Measurement Plane (ccamp) 
       Working Group";

    contact
      "WG Web:    <https://datatracker.ietf.org/wg/ccamp/>
       Editor:    Bin Yeong Yoon
                  <mailto:byyun@etri.re.kr>";

    description
      "This YANG module defines a data model for performance 
       management measurements, based on ITU-T G.7710 for 
       equipment. It specifies measurement methods and event 
       notifications.";

    revision 2025-04-06 {
        description
          "Initial version.";
        reference
          "draft-ietf-ccamp-pm-measurements-yang";
    }

    /*
     * TYPEDEFs
     */
    typedef parameter-units {
        type string;
        description
          "Unit of measurement for performance management 
           parameters defined by network elements (servers).";
    }

    typedef parameter-name {
        type identityref {
            base pm-param:performance-parameter;
        }
        description
          "Name of the performance parameter being measured.";
    }

    /*
     * GROUPINGS
     */
    grouping out-of-range-config {
        description
          "An out-of-range (OOR) event is triggered to indicate 
           an overflow or underflow condition when a measured 
           metric exceeds a configured high threshold or falls below a 
           configured low threshold. These events apply to count (transient), 
           snapshot, and tidemark measurements.";
        leaf high-oor-threshold {
            type uint32;
            description
              "High out-of-range threshold.";
        }
        leaf low-oor-threshold {
            type uint32;
            description
              "Low out-of-range threshold.";
        }
    }

    grouping event-state-info {
        description
          "Contains information about the occurrence and timing of an event.";
        leaf event-occurred {
            type boolean;
            description
              "Indicates whether an event has occurred.";
        }
        leaf event-time {
            type yang:date-and-time;
            description
              "Timestamp of when the event occurred.";
        }
    }

    grouping oor-event-type {
        description
          "Defines the type of out-of-range event that occurred, indicating whether 
           a high or low threshold was reached.";
        leaf event-type {
            type enumeration {
                enum High-OOR-event {
                    description
                      "High OOR threshold reached";
                }
                enum Low-OOR-event {
                    description
                      "Low OOR threshold reached";
                }
            }
            description
              "Indicates whether the high or low OOR threshold was reached.";
        }
    }

    grouping triggered-oor-event-info {
        description
          "Combines threshold event type and event details for a triggered OOR event, 
           providing complete information about when and what type of threshold was crossed.";
        uses oor-event-type;
        uses event-state-info;
    }

    grouping count-measurement-gr {
        description
          "Counts are cumulative measurements tracking the total occurrences of 
           specific network events or activities over a time interval (e.g., 15 minutes). 
           Counts are reset at regular intervals to start new measurements.";
        container count-measurement {
            description
              "Contains the count value and its units, as well as configuration for 
               transient and standing out-of-range conditions.";
            leaf count-value {
                type uint32;
                config false;
                description
                  "Actual count value of the measurement.";
            }
            leaf count-units {
                type parameter-units;
                config false;
                description
                  "Units of measurement for the count-value.";
            }

            container transient-condition-config {
                description
                  "Configuration for transient out-of-range conditions, defining 
                   thresholds that trigger immediate events when crossed.";
                uses out-of-range-config;
            }
            container standing-condition-config {
                description
                  "Configuration of the standing condition 
                   event for count measurements.";
                leaf standing-threshold {
                    type uint32;
                    description
                      "Standing threshold value.";
                }
                leaf standing-reset-threshold {
                    type uint32;
                    description
                      "Reset threshold value.";
                }
            }
        }
    }

    grouping snapshot-measurement-gr {
        description
          "Defines the structure for snapshot measurements, which capture instantaneous 
           values of performance parameters at specific points in time. These measurements 
           provide a momentary view of network conditions and are typically collected 
           at uniform intervals.";
        container snapshot-measurement {
            description
              "Snapshots are instantaneous measurements taken at specific points 
               in time, providing a momentary view of network conditions. Snapshots 
               are collected at uniform intervals (e.g., 15 minutes or 24 hours).";
            leaf uniform-time {
                type uint32;
                units "seconds";
                description
                  "Interval between snapshot measurements.";
            }
            leaf snapshot-value {
                type uint32;
                config false;
                description
                  "Actual snapshot value of the measurement.";
            }
            leaf snapshot-units {
                type parameter-units;
                config false;
                description
                  "Units of measurement for the snapsho.";
            }
            uses out-of-range-config;
        }
    }

    grouping tidemark-measurement-gr {
        description
          "Tidemarks record the highest (maximum) and lowest (minimum) values 
           of a specific performance metric over a defined period (e.g., 15 minutes 
           or 24 hours). They capture extreme values reflecting significant performance peaks.";

        container tidemark-measurement {
            description
              "Contains the high and low tide values and their units, as well as 
               configuration for out-of-range conditions.";
            leaf high-tide-value {
                type uint32;
                config false;
                description
                  "Actual high tide value of the measurement.";
            }
            leaf high-tide-units {
                type parameter-units;
                config false;
                description
                  "Units of measurement for the high tide value.";
            }
            leaf low-tide-value {
                type uint32;
                config false;
                description
                  "Actual low tide value of the measurement.";
            }
            leaf low-tide-units {
                type parameter-units;
                config false;
                description
                  "Units of measurement for the low tide value.";
            }
            uses out-of-range-config;
        }
    }

    grouping count-transient-event-gr {
        description
          "A Threshold Report (TR) is generated for a counter when its value 
           reaches or crosses the configured threshold.";
        container count-transient-event {
            description
              "Contains information about transient threshold events for count measurements, 
               indicating when a count value crosses configured thresholds.";
            uses triggered-oor-event-info;
        }
    }

    grouping count-standing-event-gr {
        description
          "A Threshold Report (TR) is generated when the set threshold is exceeded. 
           A Reset Threshold Report (RTR) is issued at the end of the period if the 
           value falls below or equals the reset threshold.";
        container count-standing-event {
            description
              "Contains information about standing threshold events for count measurements, 
               tracking when values exceed thresholds and when they return below reset thresholds.";
            leaf event-type {
                type enumeration {
                    enum Threshold-Report {
                        description
                          "High OOR threshold reached";
                    }
                    enum Reset-Threshold-Report {
                        description
                          "Low OOR threshold reached";
                    }
                }
                description
                  "Indicates whether a TR or RTR was generated.";
            }
            uses event-state-info;
        }
    }

    grouping snapshot-events-gr {
        description
          "Groups together event-related information for snapshot measurements, 
           including threshold crossing events and their timing.";
        container snapshot-event {
            description
              "High (or low) snapshot event triggered when the snapshot-value reaches 
               or crosses a high (or low) OOR threshold.";
            uses triggered-oor-event-info;
        }
    }

    grouping tidemark-events-gr {
        description
          "Groups together event-related information for tidemark measurements, 
           including threshold crossing events and their timing.";
        container tidemark-event {
            description
              "High (or low) tidemark event triggered when the tidemark-value reaches 
               or crosses a high (or low) OOR threshold.";
            uses triggered-oor-event-info;
        }
    }

    grouping event-parameters-gr {
        description
          "Groups together various non-periodic event parameters including 
           availability events (BUT, EUT) and error-related events (CSES).";
        container BUT-event {
            description
              "Begin Unavailable Time (BUT) event marking the start of a period when a 
               network element or connection becomes unavailable.";
            uses event-state-info;
        }
        container EUT-event {
            description
              "End Unavailable Time (EUT) event marking the end of a period when a 
               network element or connection was unavailable.";
            leaf event-occurred {
                type boolean;
                description
                  "Indicates whether an EUT event was generated.";
            }
            leaf event-time {
                type yang:date-and-time;
                description
                  "Timestamp of the EUT event.";
            }
            leaf total-unavailable-time {
                type uint32;
                units "seconds";
                description
                  "Total duration of unavailability.";
            }
        }
        container CSES-event {
            description
              "Consecutive Severely Errored Seconds (CSES) event detected within a specified time frame.";
            leaf event-occurred {
                type boolean;
                description
                  "Indicates whether a CSES event was generated.";
            }
            leaf begin-time {
                type yang:date-and-time;
                description
                  "Timestamp indicating when the CSES period began.";
            }
            leaf end-time {
                type yang:date-and-time;
                description
                  "Timestamp indicating when the CSES period ended.";
            }
            leaf duration {
                type uint32;
                units "seconds";
                description
                  "Duration of the CSES period.";
            }
            leaf error-count {
                type uint32;
                description
                  "Number of errors during the CSES period.";
            }
        }
    }

    grouping pm-parameter-entry {
        description
          "Defines the basic structure for identifying a performance parameter being measured.";
        leaf parameter-name {
            type parameter-name;
            description
              "Name of the performance parameter being measured.";
        }
    }

    grouping pm-threshold-events-gr {
        description
          "Groups together all threshold-related events for performance parameters, 
           including both periodic and non-periodic threshold events.";
        container periodic-threshold-events {
            description
              "Threshold crossing events for periodic measurements (counts, snapshots, tidemarks).";
            list pm-parameter {
                key "parameter-name";
                description
                  "List of performance parameters for which periodic threshold events are reported.";
                uses pm-parameter-entry;
                uses count-transient-event-gr;
                uses count-standing-event-gr;
                uses snapshot-events-gr {
                    refine "snapshot-event/event-occurred" {
                        description
                          "Indicates whether the snapshot-value reached a high or low OOR threshold.";
                    }
                    refine "snapshot-event/event-time" {
                        description
                          "Timestamp when the snapshot-value crossed the high or low OOR threshold.";
                    }
                }
                uses tidemark-events-gr {
                    refine "tidemark-event/event-occurred" {
                        description
                          "Indicates whether the tidemark-value reached a high or low OOR threshold.";
                    }
                    refine "tidemark-event/event-time" {
                        description
                          "Timestamp when the tidemark-value crossed the high or low OOR threshold.";
                    }
                }
            }
        }
        container non-periodic-threshold-events {
            description
              "Contains non-periodic threshold events such as BUT, EUT, and CSES events.";
            uses event-parameters-gr;
        }
    }

    grouping pm-periodic-measurement-gr {
        description
          "Defines the structure for periodic performance measurements, including 
           count, snapshot, and tidemark measurements for various parameters.";
        list pm-parameter {
            key "parameter-name";
            description
              "List of performance parameters being measured periodically.";
            uses pm-parameter-entry;
            uses count-measurement-gr;
            uses snapshot-measurement-gr;
            uses tidemark-measurement-gr;
        }
    }

    /*
     * MAIN CONTAINER
     */
    container pm-periodic-measurement {
        description
          "Contains periodic performance measurements (count, snapshot, tidemark) 
           for maintenance and QoS monitoring. Measurements are typically taken 
           over 15-minute and 24-hour intervals and categorized by purpose (maintenance or QoS).";
        uses pm-periodic-measurement-gr;
    }

    /*
     * NOTIFICATIONS
     */
    notification pm-threshold-events {
        description
          "Threshold crossing events for performance parameters.";
        uses pm-threshold-events-gr;
    }
}
