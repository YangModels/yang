module ietf-isis {
  namespace "urn:ietf:params:xml:ns:yang:ietf-isis";

  prefix isis;

  import ietf-routing {
    prefix "rt";
  }

  import ietf-inet-types {
    prefix inet;
  }
  import ietf-yang-types {
    prefix yang;
  }

  import ietf-interfaces {
    prefix "if";
  }

  import ietf-key-chain {
    prefix "key-chain";
  }

  import ietf-routing-types {
    prefix "rt-types";
  }

  import iana-routing-types {
    prefix "iana-rt-types";
  }

  organization
   "IETF ISIS Working Group";

  contact
    "WG List:  &lt;mailto:isis-wg@ietf.org&gt;

    Editor:    Stephane Litkowski
          &lt;mailto:stephane.litkowski@orange.com&gt;

        Derek Yeung
          &lt;mailto:derek@arrcus.com&gt;
        Acee Lindem
          &lt;mailto:acee@cisco.com&gt;
        Jeffrey Zhang
          &lt;mailto:zzhang@juniper.net&gt;
        Ladislav Lhotka
          &lt;mailto:llhotka@nic.cz&gt;
        Yi Yang
          &lt;mailto:yiya@cisco.com&gt;
        Dean Bogdanovic
          &lt;mailto:deanb@juniper.net&gt;
        Kiran Agrahara Sreenivasa
          &lt;mailto:kkoushik@brocade.com&gt;
        Yingzhen Qu
          &lt;mailto:yiqu@cisco.com&gt;
        Jeff Tantsura
          &lt;mailto:jefftant.ietf@gmail.com&gt;

    ";

  description
    "The YANG module defines a generic configuration model for
    ISIS common across all of the vendor implementations.";

  revision 2017-07-25 {
    description
     "Initial revision.";
     reference "RFC XXXX";
  }

 /* Identities */

  identity isis {
    base rt:routing-protocol;
    description "Identity for the ISIS routing protocol.";
  }

  identity isis-adjacency-change {
    description "Identity for the ISIS routing protocol
      adjacency state.";
  }

  identity clear-isis-database {
    description "Identity for the ISIS routing protocol
      database reset action.";
  }

  identity clear-isis-adjacency {
    description "Identity for the ISIS routing protocol
      adjacency reset action.";
  }

  identity lsp-log-reason {
    description "Base identity for an LSP change
            log reason.";
  }

  identity refresh {
    base lsp-log-reason;
    description
     "Identity used when the LSP log reason is
     a refresh LSP received.";
  }

  identity content-change {
    base lsp-log-reason;
    description
     "Identity used when the LSP log reason is
     a change in the content of the LSP.";
  }

  /* Feature definitions */

  feature ietf-spf-delay {
    description
     "Support of IETF SPF delay algorithm.";
  }
  feature bfd {
    description
     "Support of BFD for IS-IS links.";
  }
  feature key-chain {
    description
      "Support of keychain for authentication.";
  }
  feature segment-routing {
    description
     "Support of segment-routing.";
  }
  feature node-flag {
    description
     "Support of node-flag advertisement
     as prefix attribute";
  }
  feature node-tag {
    description
      "Support of node tag.";
  }
  feature ldp-igp-sync {
    description
      "Support of RFC5443.";
  }
  feature fast-reroute {
    description
      "Support of IPFRR.";
  }
  feature nsr {
    description
     "Support of
        Non Stop Routing.";
  }
  feature  lfa {
    description
      "Support of Loop Free Alternates.";
  }
  feature remote-lfa {
    description
      "Support of remote Loop Free Alternates.";
  }

  feature overload-max-metric {
    description
      "Support of overload by setting
       all links to max metric.";
  }
  feature prefix-tag {
    description
      "Add 32bit tag to prefixes";
  }
  feature prefix-tag64 {
    description
      "Add 64bit tag to prefixes";
  }
  feature auto-cost {
    description
      "Use an automated assignment of metrics.";
  }
  feature ipv4-router-id {
    description
     "Support of IPv4 router ID configuration under ISIS.";
  }

  feature ipv6-router-id {
    description
     "Support of IPv6 router ID configuration under ISIS.";
  }

  feature multi-topology {
    description
     "Multitopology routing support.";
  }
  feature nlpid-control {
    description
     "This feature controls the advertisement
      of support NLPID within ISIS configuration.";
  }
  feature graceful-restart {
    description
      "Graceful restart support as per RFC5306.";
  }

  feature lsp-refresh {
    description
      "Configuration of LSP refresh interval.";
  }

  feature maximum-area-addresses {
    description
      "Support of maximum-area-addresses config.";
  }

  feature admin-control {
    description
     "Control administrative state of ISIS.";
  }

  /* Type definitions */

  typedef instance-state-ref {
    type leafref {
      path "/rt:routing-state/"
      +"rt:control-plane-protocols/rt:control-plane-protocol/"
      +"rt:name";
    }
    description
       "This type is used for leaves that reference state data of
        an ISIS protocol instance.";
  }

  typedef circuit-id {
    type uint8;
    description
     "This type defines the circuit ID
     associated with an interface.";
  }

  typedef extended-circuit-id {
    type uint32;
    description
     "This type defines the extended circuit ID
     associated with an interface.";
  }

  typedef interface-type {
    type enumeration {
      enum broadcast {
        description
        "Broadcast interface type.";
      }
      enum point-to-point {
        description
         "Point to point interface type.";
      }
    }
    description
     "This type defines the type of adjacency
     to be established on the interface.
     This is affecting the type of hello
     message that would be used.";

  }

  typedef level {
    type enumeration {
      enum "level-1" {
        description
         "This enum describes L1 only capability.";
      }
      enum "level-2" {
        description
         "This enum describes L2 only capability.";
      }
      enum "level-all" {
        description
         "This enum describes both levels capability.";
      }
    }
    default "level-all";
    description
     "This type defines ISIS level of an object.";

  }

  typedef adj-state-type {
     type enumeration {
        enum "Up" {
          description
           "This state describes that
            adjacency is established.";
        }
        enum "Down" {
          description
           "This state describes that
            adjacency is NOT established.";
        }
        enum "Init" {
          description
           "This state describes that
            adjacency is establishing.";
        }
        enum "Failed" {
          description
           "This state describes that
            adjacency is failed.";
        }
      }
      description
      "This type defines states of an adjacency";
  }

  typedef if-state-type {
     type enumeration {
        enum "Up" {
          description
           "Up state.";

        }
        enum "Down" {
          description
           "Down state";
        }
      }
      description
      "This type defines states of an interface";
  }

  typedef level-number {
    type uint8 {
      range "1 .. 2";
    }
    description
     "This type defines a current ISIS level.";
  }

  typedef lsp-id {
    type string {
      pattern
       '[0-9A-Fa-f]{4}\.[0-9A-Fa-f]{4}\.[0-9A-Fa-f]'
             +'{4}\.[0-9][0-9]-[0-9][0-9]';
    }
    description
     "This type defines ISIS LSP ID using pattern,
      system id looks like : 0143.0438.AeF0.02-01";
  }
  typedef area-address {
    type string {
      pattern '[0-9A-Fa-f]{2}\.([0-9A-Fa-f]{4}\.){0,3}';
    }
    description
     "This type defines the area address format.";
  }

  typedef snpa {
    type string {
      length "0 .. 20";
    }
    description
     "This type defines Subnetwork Point
      of Attachement format.";
  }

  typedef system-id {
    type string {
      pattern
       '[0-9A-Fa-f]{4}\.[0-9A-Fa-f]{4}\.[0-9A-Fa-f]{4}';
    }
    description
     "This type defines ISIS system id using pattern,
      system id looks like : 0143.0438.AeF0";
  }

  typedef wide-metric {
    type uint32 {
      range "0 .. 16777215";
    }
    description
     "This type defines wide style format
      of ISIS metric.";
  }

  typedef std-metric {
    type uint8 {
      range "0 .. 63";
    }
    description
     "This type defines old style format
      of ISIS metric.";
  }

  typedef mesh-group-state {
    type enumeration {
      enum "meshInactive" {
        description
         "Interface is not part of a mesh group.";
      }
      enum "meshSet" {
        description
         "Interface is part of a mesh group.";
      }
      enum "meshBlocked" {
        description
         "LSPs must not be flooded over that interface.";
      }
    }
    description
     "This type describes meshgroup state of an interface";
  }

  /* Grouping definitions for configuration and ops state */

  grouping adjacency-state {
   container adjacencies {
      config false;
      list adjacency {
        leaf neighbor-systype {
          type level;
          description
           "Type of neighboring system";
        }
        leaf neighbor-sysid {
          type system-id;
          description
           "The system-id of the neighbor";
        }
        leaf neighbor-extended-circuit-id {
          type extended-circuit-id;
          description
           "Circuit ID of the neighbor";
        }
        leaf neighbor-snpa {
          type snpa;
          description
           "SNPA of the neighbor";
        }
        leaf usage {
          type level;
          description
          "How is the adjacency used ?
          On a p2p link this might be level 1 and 2,
          but on a LAN, the usage will be level 1
          between peers at L1 or level 2 between
          peers at L2.";
        }
        leaf hold-timer {
          type rt-types:timer-value-seconds16;
          units seconds;
          description
           "The holding time in seconds for this
            adjacency. This value is based on
            received hello PDUs and the elapsed
            time since receipt.";
        }
        leaf neighbor-priority {
          type uint8 {
            range "0 .. 127";
          }
          description
           "Priority of the neighboring IS for becoming
            the DIS.";
        }
        leaf lastuptime {
          type yang:timestamp;
          description
           "When the adjacency most recently entered
            state 'up', measured in hundredths of a
            second since the last reinitialization of
            the network management subsystem.
            The value is 0 if the adjacency has never
            been in state 'up'.";
        }
        leaf state {
          type adj-state-type;
          description
           "This leaf describes the state of the
           interface.";
        }

        description
         "List of operational adjacencies.";
      }
      description
       "This container lists the adjacencies of
       the local node.";
    }
    description
     "Adjacency state";
  }

  grouping fast-reroute-global-state {
      container protected-routes {
        config false;
        list af-stats {
          key "af prefix alternate";

          leaf af {
            type identityref {
              base iana-rt-types:address-family;
            }
            description
             "Address-family";
          }
          leaf prefix {
            type string;
            description
             "Protected prefix.";
          }
          leaf alternate {
            type string;
            description
             "Alternate nexthop for the prefix.";
          }
          leaf alternate-type {
            type enumeration {
              enum equalcost {
                description
                 "ECMP alternate.";
              }
              enum lfa {
                description
                 "LFA alternate.";
              }
              enum remote-lfa {
                description
                 "Remote LFA alternate.";
              }
              enum tunnel {
                description
                 "Tunnel based alternate
                 (like RSVP-TE or GRE).";
              }
              enum ti-lfa {
                description
                 "TI LFA alternate.";
              }
              enum mrt {
                description
                 "MRT alternate.";
              }
              enum other {
                description
                 "Unknown alternate type.";
              }
            }
            description
             "Type of alternate.";
          }
          leaf best {
            type boolean;
            description
             "describes if the alternate is the best one.";
          }
          leaf non-best-reason {
            type string;
            description
             "Information field to describe why the alternate
             is not best.";
          }
          leaf protection-available {
            type bits {
              bit nodeprotect {
                position 0;
                description
                "Node protection available.";
              }
              bit linkprotect {
                position 1;
                description
                "Link protection available.";
              }
              bit srlgprotect {
                position 2;
                description
                "SRLG protection available.";
              }
              bit downstreamprotect {
                position 3;
                description
                "Downstream protection available.";
              }
              bit other {
                position 4;
                description
                "Other protection available.";
              }
            }
            description
            "Describes protection provided by the alternate.";
          }
          leaf alternate-metric1 {
            type uint32;
            description
             "Metric from PLR to destination
              through the alternate path.";
          }
          leaf alternate-metric2 {
            type uint32;
            description
             "Metric from PLR to the alternate node";
          }
          leaf alternate-metric3 {
            type uint32;
            description
             "Metric from alternate node to the destination";
          }
          description
           "Per AF statistics.";
        }
        description
         "List of prefixes that are protected.";
      }

      container nonprotected-routes {
         config false;
         list af-stats {
          key "af prefix";

          leaf af {
            type identityref {
              base iana-rt-types:address-family;
            }
            description
             "Address-family";
          }
          leaf prefix {
            type string;
            description
             "Protected prefix.";
          }
          description
           "Per AF statistics.";
        }
        description
         "List of prefixes that are not protected.";
      }

      list protection-statistics {
        key frr-protection-method;
        config false;
        leaf frr-protection-method {
          type string;
          description
           "Protection method used.";
        }
        list af-stats {
          key af;

          leaf af {
            type identityref {
              base iana-rt-types:address-family;
            }
            description
             "Address-family";
          }
          leaf total-routes {
            type uint32;
            description
             "Total prefixes.";
          }
          leaf unprotected-routes {
            type uint32;
            description
              "Total of prefixes who are
              not protected.";
          }
          leaf protected-routes {
            type uint32;
            description
              "Total of prefixes who are
              protected.";
          }
          leaf linkprotected-routes {
            type uint32;
            description
              "Total of prefixes who are
              link protected.";
          }
          leaf nodeprotected-routes {
            type uint32;
            description
              "Total of prefixes who are
              node protected.";
          }
          description
           "Per AF statistics.";
        }

        description
         "Global protection statistics.";
      }
      description
       "IPFRR states.";
  }

  grouping notification-instance-hdr {
    description
     "This group describes common instance specific
      data for notifications.";
    leaf routing-instance {
      type string;
      description
       "Describes the name of the routing-instance instance.";
    }
    leaf routing-protocol-name {
      type string;
      description
       "Describes the name of the ISIS instance.";
    }
    leaf isis-level {
      type level;
      description
       "Describes the ISIS level of the instance.";
    }
  }

  grouping notification-interface-hdr {
    description
     "This group describes common interface specific
      data for notifications.";
    leaf interface-name {
      type string;
      description
       "Describes the name of the ISIS interface.";
    }
    leaf interface-level {
      type level;
      description
       "Describes the ISIS level of the interface.";
    }
    leaf extended-circuit-id {
      type extended-circuit-id;
      description
       "Describes the extended circuit-id of the interface.";
    }
  }

  grouping route-content {
    description
     "This group add isis-specific route properties.";
    leaf metric {
      type uint32;
      description
       "This leaf describes ISIS metric of a route.";
    }
    leaf-list tag {
      type uint64;
      description
       "This leaf describes list of tags associated
        with the route. The leaf describes both
        32bits and 64bits tags.";
    }
    leaf route-type {
      type enumeration {
        enum l2-up-internal {
          description "Level 2 internal route
           and not leaked to a lower level";
        }
        enum l1-up-internal {
          description "Level 1 internal route
           and not leaked to a lower level";
        }
        enum l2-up-external {
          description "Level 2 external route
           and not leaked to a lower level";
        }
        enum l1-up-external {
          description "Level 1 external route
           and not leaked to a lower level";
        }
        enum l2-down-internal {
          description "Level 2 internal route
           and leaked to a lower level";
        }
        enum l1-down-internal {
          description "Level 1 internal route
           and leaked to a lower level";
        }
        enum l2-down-external {
          description "Level 2 external route
           and leaked to a lower level";
        }
        enum l1-down-external {
          description "Level 1 external route
           and leaked to a lower level";
        }
      }
      description
       "This leaf describes the type of ISIS route.";
    }
  }

  grouping admin-control {
    leaf enable {
        if-feature admin-control;
        type boolean;
        default true;
        description
             "Control the administrative
             state.";
    }
    description
     "Grouping for admin control.";
  }

  grouping fast-reroute-global-cfg {
    description
     "This group defines global
     configuration of IPFRR.";
    container lfa {
      if-feature lfa;
      description
        "This container may be
        augmented with global parameters
        for LFA.
        Creating the container has no effect on
        LFA activation.";
    }
  }

  grouping fast-reroute-if-cfg {
    description
     "This group defines interface
     configuration of IPFRR.";
      container lfa {
        if-feature lfa;
        uses lfa-if-cfg;
        container level-1 {
            uses lfa-if-cfg;
            description
             "LFA level 1 config";
        }
        container level-2 {
            uses lfa-if-cfg;
            description
             "LFA level 2 config";
        }
        description
            "LFA config";
      }
  }

  grouping ietf-spf-delay-cfg {
    leaf initial-delay {
        type rt-types:timer-value-milliseconds;
        units msec;
        description
         "Delay used while in QUIET state.";
    }
    leaf short-delay {
        type rt-types:timer-value-milliseconds;
        units msec;
        description
         "Delay used while in SHORT_WAIT state.";
    }
    leaf long-delay {
        type rt-types:timer-value-milliseconds;
        units msec;
        description
         "Delay used while in LONG_WAIT state.";
    }

    leaf hold-down {
        type rt-types:timer-value-milliseconds;
        units msec;
        description
         "Timer used to consider an IGP stability period.";
    }
    leaf time-to-learn {
        type rt-types:timer-value-milliseconds;
        units msec;
        description
         "Duration used to learn all the IGP events
         related to a single component failure.";
    }

    description
     "Grouping for IETF SPF delay configuration.";
  }

  grouping ietf-spf-delay-state {
    leaf current-state {
        type enumeration {
            enum "QUIET" {
                description "QUIET state";
            }
            enum "SHORT_WAIT" {
                description "SHORT_WAIT state";
            }
            enum "LONG_WAIT" {
                description "LONG_WAIT state";
            }
        }
        config false;
        description
         "Current state of the algorithm.";
    }
    leaf remaining-time-to-learn {
        type rt-types:timer-value-milliseconds;
        units "msec";
        config false;
        description
         "Remaining time until time-to-learn timer fires.";
    }
    leaf remaining-hold-down {
        type rt-types:timer-value-milliseconds;
        units "msec";
        config false;
        description
         "Remaining time until hold-down timer fires.";
    }
    leaf last-event-received {
        type yang:timestamp;
        config false;
        description
         "Time of last IGP event received";
    }
    leaf next-spf-time {
        type yang:timestamp;
        config false;
        description
         "Time when next SPF has been scheduled.";
    }
    leaf last-spf-time {
        type yang:timestamp;
        config false;
        description
         "Time of last SPF computation.";
    }
    description
     "Grouping for IETF SPF delay operational states.";
  }

   grouping local-rib {
    description "Local-rib grouping.";
    container local-rib {
      config false;
      description "Local-rib.";
      list route {
        key "prefix";
        description "Routes";
        leaf prefix {
          type inet:ip-prefix;
          description "Destination prefix.";
        }
        container next-hops {
          description "All next hops for the route.";
          list next-hop {
            key "next-hop";
            description "List of next hop for the route";
            leaf outgoing-interface {
              type if:interface-ref;
              description
                "Name of the outgoing interface.";
            }
            leaf next-hop {
             type inet:ip-address;
             description "Nexthop address.";
            }
          }
        }
        leaf metric {
          type uint32;
          description "Metric for this route.";
        }
        leaf level {
          type level-number;
          description "Level number for this route.";
        }
        leaf route-tag {
          type uint32;
          description "Route tag for this route.";
        }
      }
    }
  }

  grouping isis-node-tag-cfg {
    description
     "ISIS node tag config.";
    container node-tags {
        if-feature node-tag;
        list node-tag {
          key tag;
          leaf tag {
            type uint32;
            description
             "Node tag value.";
          }
          description
           "List of tags.";
        }
        description
          "Container for node tags.";
      }
  }

  grouping authentication-global-cfg {
    choice authentication-type {
        case key-chain {
          if-feature key-chain;
          leaf key-chain {
            type key-chain:key-chain-ref;
            description
              "Reference to a key-chain.";
          }
        }
        case password {
          leaf key {
            type string;
            description
             "This leaf describes the
               authentication key.";
          }
          leaf crypto-algorithm {
            type identityref {
                base key-chain:crypto-algorithm;
            }
            description
              "Cryptographic algorithm associated with key.";
          }
        }
        description
           "Choice of authentication.";
      }
     description
      "Grouping for global auth config.";
  }

  grouping metric-type-global-cfg {
    leaf value {
        type enumeration {
          enum wide-only {
            description
             "Advertise new metric style only
             (RFC5305)";
          }
          enum old-only {
            description
             "Advertise old metric style only
             (RFC1195)";
          }
          enum both {
            description "Advertise both metric
            styles";
          }
        }
        default wide-only;
        description
         "This leaf describes the type of metric
         to be generated.
         Wide-only means only new metric style
         is generated,
         old-only means that only old style metric
         is generated,
         and both means that both are advertised.
         This leaf is only affecting IPv4 metrics.";
      }
       description
      "Grouping for global metric style config.";
  }

  grouping default-metric-global-cfg {
    leaf value {
        type wide-metric;
        default "10";
        description
          "Value of the metric";
    }
    description
          "Grouping for global default metric config.";
  }

  grouping overload-global-cfg {
    leaf status {
        type boolean;
        default false;
        description
         "This leaf defines the overload status.";
    }
          description
      "Grouping for overload bit config.";
  }

  grouping overload-max-metric-global-cfg {
    leaf timeout {
        type rt-types:timer-value-seconds16;
        units "seconds";
        description
         "This leaf defines the timeout in seconds
          of the overload condition.";
      }
      description
      "Grouping for overload-max-metric config.";
  }

  grouping route-preference-global-cfg {
    choice granularity {
            case detail {
              leaf internal {
                type uint8;
                description
                  "This leaf defines the protocol
                   preference for internal routes.";
              }
              leaf external {
                type uint8;
                description
                  "This leaf defines the protocol
                   preference for external routes.";
              }
            }
            case coarse {
              leaf default {
                type uint8;
                description
                  "This leaf defines the protocol
                   preference for all ISIS routes.";
              }
            }
            description
             "Choice for implementation of route preference.";
          }
    description
     "This grouping defines how route preference is configured.";
  }

  grouping hello-authentication-cfg {
    choice authentication-type {
        case key-chain {
          if-feature key-chain;
          leaf key-chain {
            type key-chain:key-chain-ref;
            description
              "Reference to a key-chain.";
          }
        }
        case password {
          leaf key {
            type string;
            description
             "This leaf describes the
               authentication key.";
          }
          leaf crypto-algorithm {
            type identityref {
                base key-chain:crypto-algorithm;
            }
            description
              "Cryptographic algorithm associated with key.";
          }
        }
        description
           "Choice of authentication.";
      }
      description
       "Grouping for hello authentication.";
  }

  grouping hello-interval-cfg {
    leaf value {
    type rt-types:timer-value-seconds16;
    units "seconds";
    default 10;
    description
     "This leaf defines the interval of
     hello messages.";
    }

    description
     "Interval between
     hello messages.";
  }

  grouping hello-multiplier-cfg {
    leaf value {
    type uint16;
    default 3;
    description
     "This leaf defines the number of
     hello failed to be received before
     declaring the adjacency down.";
    }
    description
     "This grouping defines the number of
      hello failed to be received before
      declaring the adjacency down.";
  }

  grouping priority-cfg {
    leaf value {
        type uint8 {
          range "0 .. 127";
    }
    default 64;
    description
     "This leaf describes the priority of
     the interface
     for DIS election.";
    }

    description
     "This grouping leaf describes the
     priority of
     the interface
     for DIS election.";
  }
  grouping metric-cfg {
      leaf value {
        type wide-metric;
        default "10";
        description
         "Metric value.";
      }
      description
       "Grouping for interface metric";
  }

  grouping lfa-if-cfg {
    leaf candidate-disabled {
      type boolean;
      default false;
      description
       "Prevent the interface to be used as backup.";
    }
    leaf enable {
      type boolean;
      default false;
      description
       "Activates LFA.
       This model assumes activation
       of per-prefix LFA.";
    }

    container remote-lfa {
      if-feature remote-lfa;
      leaf enable {
        type boolean;
        default false;
        description
        "Activates rLFA.";
      }
      description
       "remote LFA configuration.";
    }
    description
     "Grouping for LFA
     interface configuration";
  }

  grouping isis-global-cfg {
    description
     "Defines the ISIS global configuration.";

        uses admin-control;
        leaf level-type {
          type level;
          default "level-all";
          description
           "This leaf describes the type of ISIS node.
           A node can be level-1-only, level-2-only
           or level-1-2.
           ";
        }

        leaf system-id {
          type system-id;
          description
           "This leaf defines the system-id of the node.";
        }

        leaf maximum-area-addresses {
          if-feature maximum-area-addresses;
          type uint8;
          default 3;
          description
           "Defines the maximum areas supported.";
        }

        leaf-list area-address {
          type area-address;
          description
           "List of areas supported by the
           protocol instance.";
        }

        container mpls {
          leaf ipv4-router-id {
            if-feature ipv4-router-id;
            type inet:ipv4-address;
            description
             "Router ID value that would be used in
             TLV 134.";
          }
          leaf ipv6-router-id {
            if-feature ipv6-router-id;
            type inet:ipv6-address;
            description
             "Router ID value that would be used in
             TLV 140.";
          }
          container ldp {
            container igp-sync {
                if-feature ldp-igp-sync;
                description
                "This container may be augmented
                with global parameters for igp-ldp-sync.";
            }
            description
             "LDP related configuration.";
          }
          description
            "This container handles mpls config.";
        }
        container auto-cost {
            if-feature auto-cost;
            leaf reference-bandwidth {
              type uint32;
              units "bps";
              description
               "This leaf defines the bandwidth for calculating
                metric.";
            }
            leaf enable {
                type boolean;
                default false;
                description
                "Enable/disable auto-cost.";
            }
            description
             "This container defines the auto-cost configuration.";
        }
        leaf lsp-mtu {
          type uint16;
          units "bytes";
          default 1492;
          description
           "This leaf describes the maximum size of a
            LSP PDU in bytes.";
        }
        leaf lsp-lifetime {
          type uint16 {
            range "1..65535";
            }
          units "seconds";
          description
           "This leaf describes the lifetime of the router
            LSP in seconds.";
        }
        leaf lsp-refresh {
          if-feature lsp-refresh;
          type rt-types:timer-value-seconds16;
          units "seconds";
          description
           "This leaf describes the refresh interval of the
            router LSP in seconds.";
        }
        container graceful-restart {
          if-feature graceful-restart;
          leaf enable {
            type boolean;
            default false;
            description
             "Control enabling the feature.";
          }
          leaf restart-interval {
            type rt-types:timer-value-seconds16;
            units "seconds";
            description
            "Interval in seconds to attempt graceful restart prior
           to failing";
          }
          leaf helper-enable {
            type boolean;
            default true;
            description
            "If enabled, the local router can act as restart helper.";
          }
          description
           "This container activates graceful restart.";
        }

        container nsr {
            if-feature nsr;
            description
            "Non-Stop Routing (NSR) config state.";
            leaf enable {
                type boolean;
                default false;
                description
                 "Enable/Disable NSR.";
            }
        }

        uses isis-node-tag-cfg;

        container authentication {
            uses authentication-global-cfg;

            container level-1 {
                uses authentication-global-cfg;
                description "level-1 specific cfg";
            }
            container level-2 {
                uses authentication-global-cfg;
                description "level-2 specific cfg";
            }
            description "authentication global cfg.
            It covers both LSPs and SNPs.";
        }

        container metric-type {
            uses metric-type-global-cfg;
            container level-1 {
                uses metric-type-global-cfg;
                description "level-1 specific cfg";
            }
            container level-2 {
                uses metric-type-global-cfg;
                description "level-2 specific cfg";
            }
            description "Metric style global cfg.";
        }

        container default-metric {
            uses default-metric-global-cfg;
            container level-1 {
                uses default-metric-global-cfg;
                description "level-1 specific cfg";
            }
            container level-2 {
                uses default-metric-global-cfg;
                description "level-2 specific cfg";
            }
            description "Default metric global cfg.";
        }

        container afs {
            if-feature nlpid-control;
            list af {
              key af;
              leaf af {
                type identityref {
                  base iana-rt-types:address-family;
                }
                description
                 "Address-family";
              }
              leaf enable {
                type boolean;
                description
                  "Describes the activation state of the
                   AF.";
              }
              description
               "This list permits activation
               of new address families.";
            }
            description
             "Container for address-families";
        }

        container preference {
            uses route-preference-global-cfg;
            description
             "This container defines the protocol preference.";
        }

        container overload {
            uses overload-global-cfg;
            description
           "This container describes if the router is
            set to overload state.";
        }

        container overload-max-metric {
            if-feature overload-max-metric;
            uses overload-max-metric-global-cfg;
            description
           "This container describes if the router is
            set to overload state using max-metric
            advertisement.";
        }
  }

  grouping isis-global-topologies-cfg {
   description
    "Per topology config.";
    container default-metric {
        uses default-metric-global-cfg;
        container level-1 {
            uses default-metric-global-cfg;
            description "level-1 specific cfg";
        }
        container level-2 {
            uses default-metric-global-cfg;
            description "level-2 specific cfg";
        }
        description "Default metric per
        topology cfg.";
    }
    uses isis-node-tag-cfg;
  }

  grouping isis-if-cfg {
    description
     "Grouping for interface cfg.";

    leaf level-type {
      type level;
      default "level-all";
      description
       "This leaf defines the associated ISIS
       level of the interface.";
    }
    leaf lsp-pacing-interval {
      type rt-types:timer-value-milliseconds;
      units "milliseconds";
      default 33;
      description
       "This leaf defines the interval between
        LSP transmissions in milli-seconds";
    }
    leaf lsp-retransmit-interval {
      type rt-types:timer-value-seconds16;
      units "seconds";
      description
       "This leaf defines the interval between
       retransmission of LSP";
    }
    leaf passive {
      type boolean;
      default "false";
      description
       "This leaf defines if interface is in
        passive mode (ISIS not running,
        but network is advertised).";
    }
    leaf csnp-interval {
      type rt-types:timer-value-seconds16;
      units "seconds";
      default 10;
      description
       "This leaf defines the interval of CSNP
        messages.";
    }
    container hello-padding {
      leaf enable {
        type boolean;
        default "true";
        description
         "Status of Hello-padding activation.
          By default, the implementation shall
          pad HELLOs.";
      }
      description
       "This container handles ISIS hello padding
        configuration.";
    }
    leaf mesh-group-enable {
      type mesh-group-state;
      description
       "Describes the mesh group state of
        the interface.";
    }
    leaf mesh-group {
      when "../mesh-group-enable = 'meshSet'" {
        description
         "Only valid when mesh-group-enable
          equals meshSet";
      }
      type uint8;
      description
       "Describes the mesh group ID of
        the interface.";
    }
    leaf interface-type {
      type interface-type;
      default "broadcast";
      description
       "This leaf defines the type of adjacency
       to be established on the interface.
       This is affecting the type of hello
       message that would be used.";
    }

    uses admin-control;

    leaf-list tag {
      if-feature prefix-tag;
      type uint32;
      description
       "This leaf defines list of tags associated
        with the interface.";
    }
    leaf-list tag64 {
      if-feature prefix-tag64;
      type uint64;
      description
       "This leaf defines list of 64bits tags
       associated with the interface.";
    }
    leaf node-flag {
        if-feature node-flag;
        type boolean;
        default false;
        description
         "Set prefix as a node
         representative prefix.";
    }
    container hello-authentication {
        uses hello-authentication-cfg;
        container level-1 {
            uses hello-authentication-cfg;
            description "level-1 specific cfg";
        }
        container level-2 {
            uses hello-authentication-cfg;
            description "level-2 specific cfg";
        }
        description "Authentication type
       to be used in hello messages.";
    }
    container hello-interval {
        uses hello-interval-cfg;
        container level-1 {
            uses hello-interval-cfg;
            description "level-1 specific cfg";
        }
        container level-2 {
            uses hello-interval-cfg;
            description "level-2 specific cfg";
        }
        description "Interval between
         hello messages.";
    }
    container hello-multiplier {
        uses hello-multiplier-cfg;
        container level-1 {
            uses hello-multiplier-cfg;
            description "level-1 specific cfg";
        }
        container level-2 {
            uses hello-multiplier-cfg;
            description "level-2 specific cfg";
        }
        description "Hello multiplier
        configuration.";
    }
    container priority {
        must '../interface-type = "broadcast"' {
            error-message
             "Priority only applies to broadcast
             interfaces.";
            description
             "Check for broadcast interface.";
        }
        uses priority-cfg;
        container level-1 {
            uses priority-cfg;
            description "level-1 specific cfg";
        }
        container level-2 {
            uses priority-cfg;
            description "level-2 specific cfg";
        }
        description "Priority for DIS election.";
    }
    container metric {
        uses metric-cfg;
        container level-1 {
            uses metric-cfg;
            description "level-1 specific cfg";
        }
        container level-2 {
            uses metric-cfg;
            description "level-2 specific cfg";
        }
        description "Metric configuration.";
    }
    container bfd {
        if-feature bfd;
        leaf enable {
            type boolean;
            default false;
            description "
                Enables BFD on the interface
            ";
        }
        description
         "BFD configuration.";
    }
    container afs {
        if-feature nlpid-control;
        list af {
          key af;
          leaf af {
            type identityref {
              base iana-rt-types:address-family;
            }
            description
              "Address-family";
          }
          description
           "List of AFs.";
        }
        description
             "Container for address-families";
    }
    container mpls {
      container ldp {
        leaf igp-sync {
            if-feature ldp-igp-sync;
            type boolean;
            default false;
            description
             "Enables IGP/LDP sync.";
        }
        description
         "LDP protocol related configurations.";
      }
      description
       "Container for MPLS specific configuration
       for ISIS.";
    }
  }

  grouping isis-if-topologies-cfg {
    description
     "ISIS interface topology cfg.";
    container metric {
        uses metric-cfg;
        container level-1 {
            uses metric-cfg;
            description "level-1 specific cfg";
        }
        container level-2 {
            uses metric-cfg;
            description "level-2 specific cfg";
        }
        description "Metric configuration.";
    }
  }

  grouping system-counters {
   container system-counters {
      config false;
      list level {
        key level;

        leaf level {
          type level-number;
          description
           "This leaf describes the ISIS level.";
        }
        leaf corrupted-lsps {
          type uint32;
          description
           "Number of corrupted in-memory LSPs detected.
           LSPs received from the wire with a bad
           checksum are silently dropped and not counted.
           LSPs received from the wire with parse errors
           are counted by lsp-errors.";
        }
        leaf authentication-type-fails {
          type uint32;
          description
           "Number of authentication type mismatches.";
        }
        leaf authentication-fails {
          type uint32;
          description
           "Number of authentication key failures.";
        }
        leaf database-overload {
          type uint32;
          description
           "Number of times the database has become
           overloaded.";
        }
        leaf own-lsp-purge {
          type uint32;
          description
           "Number of times a zero-aged copy of the
           system's own LSP is received from some
           other node.";
        }
        leaf manual-address-drop-from-area {
          type uint32;
          description
           "Number of times a manual address
            has been dropped from the area.";
        }
        leaf max-sequence {
          type uint32;
          description
           "Number of times the system has attempted
            to exceed the maximum sequence number.";
        }
        leaf sequence-number-skipped {
          type uint32;
          description
           "Number of times a sequence number skip has
           occured.";
        }
        leaf id-len-mismatch {
          type uint32;
          description
           "Number of times a PDU is received with
            a different value for ID field length
            from that of the receiving system.";
        }
        leaf partition-changes {
          type uint32;
          description
           "Number of partition changes detected.";
        }
        leaf lsp-errors {
          type uint32;
          description
           "Number of LSPs with errors we have
           received.";
        }
        leaf spf-runs {
          type uint32;
          description
           "Number of times we ran SPF at this level.";
        }
        description
         "List of supported levels.";
      }
      description
       "The container defines a list of counters
        for the IS.";
    }
    description
     "Grouping for system counters.";
  }

  grouping event-counters {
      container event-counters {
          config false;
          leaf adjacency-changes {
            type uint32;
            description
             "The number of times an adjacency state
              change has occured on this interface.";
          }
          leaf adjacency-number {
            type uint32;
            description
             "The number of adjacencies on this
              interface.";
          }
          leaf init-fails {
            type uint32;
            description
             "The number of times initialization of
              this interface has failed. This counts
              events such as PPP NCP failures.
              Failures to form an adjacency are counted
              by adjacency-rejects.";
          }
          leaf adjacency-rejects {
            type uint32;
            description
             "The number of times an adjacency has been
              rejected on this interface.";
          }
          leaf id-len-mismatch {
            type uint32;
            description
             "The number of times an IS-IS PDU with an ID
              field length different from that for this
              system has been received on this interface.";
          }
          leaf max-area-addresses-mismatch {
            type uint32;
            description
             "The number of times an IS-IS PDU with
              according max area address field
              differs from that for
              this system has been received on this
              interface.";
          }
          leaf authentication-type-fails {
            type uint32;
            description
             "Number of authentication type mismatches.";
          }
          leaf authentication-fails {
            type uint32;
            description
             "Number of authentication key failures.";
          }
          leaf lan-dis-changes {
            type uint32;
            description
             "The number of times the DIS has changed
              on this interface at this level.
              If the interface type is point to point,
              the count is zero.";
          }
          description
           "Provides protocol event counters.";
      }
      description
       "Grouping for event counters";
  }

  grouping packet-counters {
    container packet-counters {
      config false;
      list level {
        key level;

        leaf level {
          type level-number;
          description
           "This leaf describes the ISIS level.";
        }
        container iih {
          leaf in {
            type uint32;
            description
             "Received PDUs.";
          }
          leaf out {
            type uint32;
            description
             "Sent PDUs.";
          }
          description
           "The number of IIH PDUs received/sent.";
        }
        container ish {
          leaf in {
            type uint32;
            description
             "Received PDUs.";
          }
          leaf out {
            type uint32;
            description
             "Sent PDUs.";
          }
          description
           "The number of ISH PDUs received/sent.";
        }
        container esh {
          leaf in {
            type uint32;
            description
             "Received PDUs.";
          }
          leaf out {
            type uint32;
            description
             "Sent PDUs.";
          }
          description
           "The number of ESH PDUs received/sent.";
        }
        container lsp {
          leaf in {
            type uint32;
            description
             "Received PDUs.";
          }
          leaf out {
            type uint32;
            description
             "Sent PDUs.";
          }
          description
           "The number of LSP PDUs received/sent.";
        }
        container psnp {
          leaf in {
            type uint32;
            description
             "Received PDUs.";
          }
          leaf out {
            type uint32;
            description
             "Sent PDUs.";
          }
          description
           "The number of PSNP PDUs received/sent.";
        }
        container csnp {
          leaf in {
            type uint32;
            description
             "Received PDUs.";
          }
          leaf out {
            type uint32;
            description
             "Sent PDUs.";
          }
          description
           "The number of CSNP PDUs received/sent.";
        }
        container unknown {
          leaf in {
            type uint32;
            description
             "Received PDUs.";
          }
          leaf out {
            type uint32;
            description
             "Sent PDUs.";
          }
          description
           "The number of unknown PDUs received/sent.";
        }
        description
         "List of supported levels.";
      }
      description
       "Provides packet counters per level.";
    }
    description
     "Grouping for packet counters.";
  }

  grouping spf-log {
    container spf-log {
      config false;
      list event {
        key id;

        leaf id {
          type uint32;
          description
           "This leaf defines the event identifier.
            This is a purely internal value.";
        }
        leaf spf-type {
          type enumeration {
            enum full {
              description
               "Computation done is a Full SPF.";
            }
            enum route-only {
              description
               "Computation done is a
                reachability computation
                only.";
            }
          }
          description
           "This leaf describes the type of computation
           used.";
        }
        leaf level {
          type level-number;
          description
           "This leaf describes the level affected by the
           the computation.";
        }
        leaf schedule-timestamp {
          type yang:timestamp;
          description
           "This leaf describes the timestamp
            when the computation was scheduled.";
        }
        leaf start-timestamp {
          type yang:timestamp;
          description
           "This leaf describes the timestamp
            when the computation was started.";
        }
        leaf end-timestamp {
          type yang:timestamp;
          description
           "This leaf describes the timestamp
            when the computation was ended.";
        }
        list trigger-lsp {
          key "lsp";
          leaf lsp {
            type lsp-id;
            description
             "This leaf describes the LSPID
              of the LSP.";
          }
          leaf sequence {
            type uint32;
            description
             "This leaf describes the sequence
              number of the LSP.";
          }
          description
           "This leaf describes list of LSPs
            that triggered the computation.";
        }
        description
         "List of computation events.
         It is used as a wrapping buffer.";
      }

      description
       "This container lists the SPF computation events.";
    }
    description
     "Grouping for spf-log events.";
  }

  grouping lsp-log {
    container lsp-log {
      config false;
      list event {
        key id;

        leaf id {
          type uint32;
          description
           "This leaf defines the event identifier.
            This is a purely internal value.";
        }
        leaf level {
          type level-number;
          description
           "This leaf describes the level affected by the
           the computation.";
        }
        container lsp {
          leaf lsp {

            type lsp-id;
            description
             "This leaf describes the LSPID
              of the LSP.";
          }
          leaf sequence {
            type uint32;
            description
             "This leaf describes the sequence
              number of the LSP.";
          }
          description
           "This container describes the received LSP
           , in case of local LSP update the local
           LSP ID is referenced.";
        }

        leaf received-timestamp {
          type yang:timestamp;

          description
           "This leaf describes the timestamp
           when the LSP was received. In case of
           local LSP update, the timestamp refers
           to the local LSP update time.";
        }

        leaf change {
          type identityref {
            base lsp-log-reason;
          }
          description
           "This leaf describes the type of change
           in the LSP.";
        }

        description
         "List of LSP events.
         It is used as a wrapping buffer.";
      }

      description
       "This container lists the LSP reception events.
       Local LSP modification are also contained in the
       list.";
    }
    description
     "Grouping for LSP log.";
  }

  grouping hostname-db {
    container hostnames {
      config false;
      list hostname {
        key system-id;
        leaf system-id {
          type system-id;
          description
           "This leaf describes the system-id
           associated with the hostname.";
        }
        leaf hostname {
          type string;
          description
           "This leaf describes the hostname
            associated with the system ID.";
        }
        description
         "List of system-id/hostname associations";
      }
      description
       "This container describes the list
       of binding between system-id and
       hostnames.";
    }
    description
     "Grouping for hostname to systemid mapping database.";
  }

  /* Groupings for the LSDB description */

  grouping prefix-reachability-attributes {
    description
     "This group defines extended reachability attributes of an
      IPv4 or IPv6 prefix.";

    leaf external-prefix-flag {
        type boolean;
        description
         "External prefix flag.";
    }
    leaf readvertisement-flag {
        type boolean;
        description
         "Readvertisement flag.";
    }
    leaf node-flag {
        type boolean;
        description
         "Node flag.";
    }
  }

  grouping prefix-ipv4-source-router-id {
    description
     "This group defines the IPv4 source router ID of
     a prefix advertisement.";

    leaf ipv4-source-router-id {
        type inet:ipv4-address;
        description
         "IPv4 Source router ID address.";
    }
  }

  grouping prefix-ipv6-source-router-id {
    description
     "This group defines the IPv6 source router ID of
     a prefix advertisement.";

    leaf ipv6-source-router-id {
        type inet:ipv6-address;
        description
         "IPv6 Source router ID address.";
    }
  }

  grouping prefix-attributes-extension {
    description
     "Prefix extended attributes.";
    uses prefix-reachability-attributes;
    uses prefix-ipv4-source-router-id;
    uses prefix-ipv6-source-router-id;
  }

  grouping prefix-ipv4-std {
    description
     "This group defines attributes of an
      IPv4 standard prefix.";
    leaf up-down {
      type boolean;
      description
       "This leaf expresses the value of up/down bit.";
    }
    leaf i-e {
      type boolean;
      description
       "This leaf expresses the value of I/E bit.";
    }
    leaf ip-prefix {
      type inet:ipv4-address;
      description
       "This leaf describes the IPv4 prefix";
    }
    leaf prefix-len {
      type uint8;
      description
       "This leaf describes the IPv4 prefix len in bits";
    }
    leaf default-metric {
      type std-metric;
      description
       "This leaf describes the ISIS default metric value";
    }
    container delay-metric {
      leaf metric {
        type std-metric;
        description
         "This leaf describes the ISIS delay metric value";
      }
      leaf supported {
        type boolean;
        default "false";
        description
         "This leaf describes if the metric is supported.";
      }

      description
       "This container defines the ISIS delay metric.";
    }
    container expense-metric {
      leaf metric {
        type std-metric;
        description
         "This leaf describes the ISIS expense metric value";
      }
      leaf supported {
        type boolean;
        default "false";
        description
         "This leaf describes if the metric is supported.";
      }
      description
       "This container defines the ISIS expense metric.";
    }
    container error-metric {
      leaf metric {
        type std-metric;
        description
         "This leaf describes the ISIS error metric value";
      }
      leaf supported {
        type boolean;
        default "false";
        description
         "This leaf describes if the metric is supported.";
      }

      description
       "This container defines the ISIS error metric.";
    }
  }

  grouping prefix-ipv4-extended {
    description
     "This group defines attributes of an
      IPv4 extended prefix.";
    leaf up-down {
      type boolean;
      description
       "This leaf expresses the value of up/down bit.";
    }
    leaf ip-prefix {
      type inet:ipv4-address;
      description
       "This leaf describes the IPv4 prefix";
    }
    leaf prefix-len {
      type uint8;
      description
       "This leaf describes the IPv4 prefix len in bits";
    }

    leaf metric {
      type wide-metric;
      description
       "This leaf describes the ISIS metric value";
    }
    leaf-list tag {
      type uint32;
      description
       "This leaf describes a list of tags associated with
       the prefix.";
    }
    leaf-list tag64 {
      type uint64;
      description
       "This leaf describes a list of 64-bit tags associated with
       the prefix.";
    }
    uses prefix-attributes-extension;
  }

  grouping prefix-ipv6-extended {
    description
     "This group defines attributes of an
      IPv6 prefix.";
    leaf up-down {
      type boolean;
      description
       "This leaf expresses the value of up/down bit.";
    }
    leaf ip-prefix {
      type inet:ipv6-address;
      description
       "This leaf describes the IPv6 prefix";
    }
    leaf prefix-len {
      type uint8;
      description
       "This leaf describes the IPv4 prefix len in bits";
    }
    leaf metric {
      type wide-metric;
      description
       "This leaf describes the ISIS metric value";
    }
    leaf-list tag {
      type uint32;
      description
       "This leaf describes a list of tags associated with
       the prefix.";
    }
    leaf-list tag64 {
      type uint64;
      description
       "This leaf describes a list of 64-bit tags associated with
       the prefix.";
    }
    uses prefix-attributes-extension;
  }

  grouping neighbor-extended {
    description
     "This group defines attributes of an
      ISIS extended neighbor.";
    leaf neighbor-id {
      type system-id;
      description
       "This leaf describes the system-id of the neighbor.";
    }
    leaf metric {
      type wide-metric;
      description
       "This leaf describes the ISIS metric value";
    }
  }

  grouping neighbor {
    description
     "This group defines attributes of an
      ISIS standard neighbor.";
    leaf neighbor-id {
      type system-id;
      description
       "This leaf describes the system-id of the neighbor.";
    }
    leaf i-e {
      type boolean;
      description
       "This leaf expresses the value of I/E bit.";
    }
    leaf default-metric {
      type std-metric;
      description
       "This leaf describes the ISIS default metric value";
    }
    container delay-metric {
      leaf metric {
        type std-metric;
        description
         "This leaf describes the ISIS delay metric value";
      }
      leaf supported {
        type boolean;
        default "false";
        description
         "This leaf describes if the metric is supported.";
      }
      description
       "This container defines the ISIS delay metric.";
    }
    container expense-metric {
      leaf metric {
        type std-metric;
        description
         "This leaf describes the ISIS delay expense value";
      }
      leaf supported {
        type boolean;
        default "false";
        description
         "This leaf describes if the metric is supported.";
      }
      description
       "This container defines the ISIS expense metric.";
    }
    container error-metric {
      leaf metric {
        type std-metric;
        description
         "This leaf describes the ISIS error metric value";
      }
      leaf supported {
        type boolean;
        default "false";
        description
         "This leaf describes if the metric is supported.";
      }
      description
       "This container defines the ISIS error metric.";
    }
  }

  grouping lsp-entry {
   description
     "This group defines attributes of an
      ISIS LSP database entry.";

    leaf decoded-completed {
      type boolean;
      description
        "The IS-IS body is fully decoded.";
    }
    leaf raw-data {
      type yang:hex-string;
      description
        "The complete LSP in network byte
         order hexadecimal as received or originated.";
    }
    leaf lsp-id {
      type lsp-id;
      description
       "This leaf describes the LSP ID of the LSP.";
    }
    leaf checksum {
      type uint16;
      description
       "This leaf describes the checksum of the LSP.";
    }
    leaf remaining-lifetime {
      type uint16;
      units "seconds";
      description
       "This leaf describes the remaining lifetime
        in seconds before the LSP expiration.";
    }
    leaf sequence {
      type uint32;
      description
       "This leaf describes the sequence number of the LSP.";
    }
    leaf attributes {
      type bits {
        bit PARTITIONNED {
          description
           "If set, the originator supports partition
            repair.";
        }
        bit ATTACHED-ERROR {
          description
           "If set, the originator is attached to
            another area using the referred metric.";
        }
        bit ATTACHED-EXPENSE {
          description
           "If set, the originator is attached to
            another area using the referred metric.";
        }
        bit ATTACHED-DELAY {
          description
           "If set, the originator is attached to
            another area using the referred metric.";
        }
        bit ATTACHED-DEFAULT {
          description
           "If set, the originator is attached to
            another area using the referred metric.";
        }
        bit OVERLOAD {
          description
           "If set, the originator is overloaded,
            and must be avoided in path calculation.";
        }
      }
      description
       "This leaf describes attributes of the LSP.";
    }

    leaf-list ipv4-addresses {
      type inet:ipv4-address;
      description
        "This leaf describes the IPv4 addresses of the node.
        ISIS reference is TLV 132.";
    }

    leaf-list ipv6-addresses {
      type inet:ipv6-address;
      description
       "This leaf describes the IPv6 interface
       addresses of the node.
       ISIS reference is TLV 232.";
    }

    leaf ipv4-te-routerid {
      type inet:ipv4-address;
      description
        "This leaf describes the IPv4 Traffic Engineering
        router ID of the node.
        ISIS reference is TLV 134.";
    }

    leaf ipv6-te-routerid {
      type inet:ipv6-address;
      description
       "This leaf describes the IPv6 Traffic Engineering
        router ID of the node.
        ISIS reference is TLV 140.";
    }

    leaf-list protocol-supported {
      type uint8;
      description
       "This leaf describes the list of
       supported protocols.
       ISIS reference is TLV 129.";
    }

    leaf dynamic-hostname {
      type string;
      description
       "This leaf describes the name of the node.
       ISIS reference is TLV 137.";
    }

    container authentication {
      leaf authentication-type {
        type string;
        description
         "This leaf describes the authentication type
          to be used.";
      }
      leaf authentication-key {
        type string;
        description
         "This leaf describes the authentication key
          to be used. For security reason, the
          authentication key MUST NOT be presented
          in plaintext format. Authors recommends
          to use MD5 hash to present the authentication-key.";
      }
      description "This container describes authentication
      information of the node. ISIS reference is TLV 10.";
    }
    container mt-entries {
      list topology {

        leaf MT-ID {
          type uint16 {
            range "0 .. 4095";
          }
          description
           "This leaf defines the identifier
            of a topology.";
        }

        leaf attributes {
          type bits {
            bit OVERLOAD {
              description
               "If set, the originator is overloaded,
                and must be avoided in path
                calculation.";
            }
            bit ATTACHED {
              description
               "If set, the originator is attached to
                another area using the referred metric.";
            }
          }
          description
           "This leaf describes attributes of the LSP
            for the associated topology.";
        }
        description
         "List of topologies supported.";
      }
      description
       "This container describes the topology supported.
       ISIS reference is TLV 229.";
    }

    list router-capabilities {
      leaf flags {
        type bits {
          bit flooding {
            position 0;
            description
             "If the S bit is set(1),
             the IS-IS Router CAPABILITY TLV
            MUST be flooded across the entire routing domain.
            If the S bit is
            not set(0), the TLV MUST NOT be leaked between levels.
            This bit MUST NOT be altered during the TLV leaking.";
          }
          bit down {
            position 1;
            description
            "When the IS-IS Router CAPABILITY TLV is
            leaked from level-2 to level-1, the D bit
            MUST be set.  Otherwise, this bit MUST
            be clear.  IS-IS Router capability TLVs
            with the D bit set MUST NOT
            be leaked from level-1 to level-2.
            This is to prevent TLV looping.
            ";
          }
        }
        description
         "Flags associated with router capability.";
      }
      container node-tags {
        if-feature node-tag;
        list node-tag {
          leaf tag {
            type uint32;
            description
             "Node tag value.";
          }
          description
           "List of tags.";
        }
        description
         "Container for node tags.";
      }

      leaf binary {
        type binary;
        description
         "This leaf describes the capability of the node.
         Format is binary according to the protocol encoding.";
      }
      description
       "This container describes the capabilities of the node.
       This container may be extended with detailed
       information.
       ISIS reference is TLV 242.";
    }

    container is-neighbor {
      list neighbor {
        uses neighbor;
        description
         "List of neighbors.";
      }
      description
       "This leaf describes list of ISIS neighbors.
       ISIS reference is TLV 2.";
    }

    container extended-is-neighbor {
      list neighbor {
        uses neighbor-extended;
        description
         "List of neighbors.";
      }
      description
       "This container describes list of ISIS extended
       neighbors.
       ISIS reference is TLV 22.";
    }

    container ipv4-internal-reachability {
      list prefixes {
        uses prefix-ipv4-std;
        description
         "List of prefixes.";
      }
      description
       "This container describes list of IPv4 internal
       reachability information.
       ISIS reference is TLV 128.";
    }

    container ipv4-external-reachability {
      list prefixes {
        uses prefix-ipv4-std;
        description
         "List of prefixes.";
      }
      description
       "This container describes list of IPv4 external
       reachability information.
       ISIS reference is TLV 130.";
    }

    container extended-ipv4-reachability {
      list prefixes {
        uses prefix-ipv4-extended;
        description
         "List of prefixes.";
      }
      description
       "This container describes list of IPv4 extended
       reachability information.
       ISIS reference is TLV 135.";
    }

    container mt-is-neighbor {
      list neighbor {
        leaf MT-ID {
          type uint16 {
            range "0 .. 4095";
          }
          description
           "This leaf defines the identifier
            of a topology.";
        }
        uses neighbor-extended;
        description
         "List of neighbors.";
      }
      description
       "This container describes list of ISIS multi-topology
        neighbors.
        ISIS reference is TLV 223.";
    }

    container mt-extended-ipv4-reachability {
      list prefixes {
        leaf MT-ID {
          type uint16 {
            range "0 .. 4095";
          }
          description
           "This leaf defines the identifier
            of a topology.";
        }
        uses prefix-ipv4-extended;
        description
         "List of prefixes.";

      }
      description
       "This container describes list of IPv4
       reachability information in multi-topology
       environment.
       ISIS reference is TLV 235.";
    }

    container mt-ipv6-reachability {
      list prefixes {
        leaf MT-ID {
          type uint16 {
            range "0 .. 4095";
          }
          description
           "This leaf defines the identifier
            of a topology.";
        }
        uses prefix-ipv6-extended;
        description
         "List of prefixes.";
      }
      description
       "This container describes list of IPv6
       reachability information in multi-topology
       environment.
       ISIS reference is TLV 237.";
    }

    container ipv6-reachability {
      list prefixes {
        uses prefix-ipv6-extended;
        description
         "List of prefixes.";
      }
      description
       "This container describes list of IPv6
       reachability information.
       ISIS reference is TLV 236.";
    }
  }

  grouping lsdb {
    container database {
      config false;
      list level-db {
        key level;

        leaf level {
          type level-number;
          description
           "Current level number";
        }
        list lsp {
          key lsp-id;
          uses lsp-entry;
          description
           "List of LSPs in LSDB.";
        }
        description
         "This container describes the list of LSPs
         in the level x database.";
      }
      description
       "This container describes ISIS Link State
        databases.";
    }
    description
     "Grouping for LSDB description.";
  }

  /* Augmentations */

  augment "/rt:routing-state/"
    +"rt:ribs/rt:rib/rt:routes/rt:route" {
    when "rt:source-protocol = 'isis:isis'" {
      description "ISIS-specific route attributes.";
    }
    uses route-content;
    description
     "This augments route object in RIB with ISIS-specific
      attributes.";
  }

  augment "/if:interfaces/if:interface" {
    leaf clns-mtu {
      type uint16;
      description
       "Defines CLNS MTU of the interface.";
    }
    description "ISO interface config.";
  }

  augment "/rt:routing/rt:control-plane-protocols/"
      +"rt:control-plane-protocol" {
    when "rt:type = 'isis:isis'" {
      description
       "This augment is only valid when routing protocol
        instance type is isis.";
    }
    description
     "This augments a routing protocol instance with ISIS
      specific parameters.";
    container isis {
        must "count(area-address) > 0" {
          error-message "At least one area-address
          must be configured.";
          description
           "Enforce configuration of at least one area.";
        }

        uses isis-global-cfg;
        container fast-reroute {
         if-feature fast-reroute;
         uses fast-reroute-global-cfg;
         uses fast-reroute-global-state;
         description
              "IPFRR.";
        }
        container spf-control {
            container ietf-spf-delay {
                if-feature ietf-spf-delay;
                uses ietf-spf-delay-cfg;
                uses ietf-spf-delay-state;
                description
                 "IETF spf delay algorithm configuration.";
            }
            description
             "Container for all SPF computation related
             operations.";
        }
        container topologies {
            if-feature multi-topology;
            list topology {
              key "name";
              leaf enable {
                type boolean;
                description
                 "Control enabling of topologies";
              }
              leaf name {
                type leafref {
                   path "../../../../../../rt:ribs/rt:rib/rt:name";
                 }
                description "RIB";
              }

              uses isis-global-topologies-cfg;

              description
                "List of topologies";
            }
            description
             "Container for multi-topology";
        }
        container interfaces {
          list interface {
            key "name";
            leaf name {
              type if:interface-ref;

              description
               "Reference to the interface within
                the routing-instance.";
          }
          uses isis-if-cfg;
          container fast-reroute {
            if-feature fast-reroute;
            uses fast-reroute-if-cfg;
            description
              "IPFRR.";
          }
          container topologies {
              if-feature multi-topology;
              list topology {
                  key name;

                  leaf name {
                    type leafref {
                        path "../../../../../../../../"+
                        "rt:ribs/rt:rib/rt:name";
                    }

                    description
                     "Name of RIB.";
                  }
                  uses isis-if-topologies-cfg;
                  description
                   "List of topologies.";
              }
            description
             "Container for multi-topology";
          }
          uses adjacency-state;
          uses event-counters;
          uses packet-counters;
          description
            "List of ISIS interfaces.";
          }
          description
           "This container defines ISIS interface specific
           configuration objects.";
       }
       uses spf-log;
       uses lsp-log;
       uses hostname-db;
       uses lsdb;
       uses local-rib;
       uses system-counters;

       description
        "This container defines ISIS specific configuration
         objects.";
    }
  }

  /* RPC methods */

  rpc clear-adjacency {
    description
     "This RPC request clears a particular
      set of ISIS adjacencies. If the operation
      fails for ISIS internal reason, then
      error-tag and error-app-tag should be set
      to a meaningful value.";
    input {

      leaf routing-protocol-instance-name {
        type instance-state-ref;
        mandatory "true";
        description
         "Name of the ISIS protocol instance whose ISIS
          information is being queried.

          If the ISIS instance with name equal to the
          value of this parameter doesn't exist, then this
          operation SHALL fail with error-tag 'data-missing'
          and error-app-tag
          'routing-protocol-instance-not-found'.";
      }
      leaf level {
        type level;
        description
         "ISIS level of the adjacency to be cleared.
         If ISIS level is level-1-2, both level 1 and level 2
         adjacencies would be cleared.

         If the value provided is different from the one
         authorized in the enum type, then this
          operation SHALL fail with error-tag 'data-missing'
          and error-app-tag
          'bad-isis-level'.
         ";
      }
      leaf interface {
        type string;
        description
         "Name of the ISIS interface.

          If the ISIS interface with name equal to the
          value of this parameter doesn't exist, then this
          operation SHALL fail with error-tag 'data-missing'
          and error-app-tag
          'isis-interface-not-found'.";
      }
    }
  }

  rpc clear-database {
    description
     "This RPC request clears a particular
      ISIS database. If the operation
      fails for ISIS internal reason, then
      error-tag and error-app-tag should be set
      to a meaningful value.";
    input {
      leaf routing-protocol-instance-name {
        type instance-state-ref;
        mandatory "true";
        description
         "Name of the ISIS protocol instance whose ISIS
          information is being queried.

          If the ISIS instance with name equal to the
          value of this parameter doesn't exist, then this
          operation SHALL fail with error-tag 'data-missing'
          and error-app-tag
          'routing-protocol-instance-not-found'.";
      }
      leaf level {
        type level;
        description
         "ISIS level of the adjacency to be cleared.
         If ISIS level is level-1-2, both level 1 and level 2
         adjacencies would be cleared.

         If the value provided is different from the one
         authorized in the enum type, then this
          operation SHALL fail with error-tag 'data-missing'
          and error-app-tag
          'bad-isis-level'.
         ";
      }
    }
  }

  /* Notifications */

  notification database-overload {
    uses notification-instance-hdr;

    leaf overload {
      type enumeration {
        enum "off" {
          description
           "The system has left overload condition.";
        }
        enum "on" {
          description
           "The system is in overload condition.";
        }

      }
      description
         "Describes the new overload state of the instance.";
    }
    description
      "This notification is sent when an ISIS instance
       overload condition changes.";
  }

  notification lsp-too-large {
    uses notification-instance-hdr;
    uses notification-interface-hdr;
    leaf pdu-size {
      type uint32;
      description
       "Size of the PDU";
    }
    leaf lsp-id {
      type lsp-id;
      description
       "LSP ID.";
    }
    description
      "This notification is sent when we attempt
       to propagate an LSP that is larger than the
       dataLinkBlockSize for the circuit.
       The notification generation must be throttled
       with at least a 5 second gap.
       ";
  }

  notification if-state-change {
    uses notification-instance-hdr;
    uses notification-interface-hdr;

    leaf state {
      type if-state-type;
      description "Interface state.";
    }
    description
      "This notification is sent when an interface
      state change is detected.";
  }

  notification corrupted-lsp-detected {
    uses notification-instance-hdr;
    leaf lsp-id {
      type lsp-id;
      description
       "LSP ID.";
    }
    description
      "This notification is sent when we find
       that an LSP that was stored in memory has
       become corrupted.
       ";
  }

  notification attempt-to-exceed-max-sequence {
    uses notification-instance-hdr;
    leaf lsp-id {
      type lsp-id;
      description
       "LSP ID.";
    }
    description
      "This notification is sent when the system
      wraps the 32-bit sequence counter of an LSP.
       ";
  }

  notification id-len-mismatch {
    uses notification-instance-hdr;
    uses notification-interface-hdr;

    leaf pdu-field-len {
      type uint8;
      description
       "Size of the ID length in the received PDU";
    }
    leaf raw-pdu {
      type binary;
      description
       "Received raw PDU.";
    }
    description
      "This notification is sent when we receive a PDU
      with a different value for the System ID length.
      The notification generation must be throttled
      with at least a 5 second gap.
       ";
  }

  notification max-area-addresses-mismatch {
    uses notification-instance-hdr;
    uses notification-interface-hdr;

    leaf max-area-addresses {
      type uint8;
      description
       "Received number of supported areas";
    }
    leaf raw-pdu {
      type binary;
      description
       "Received raw PDU.";
    }
    description
      "This notification is sent when we receive a PDU
      with a different value for the Maximum Area Addresses.
      The notification generation must be throttled
      with at least a 5 second gap.
       ";
  }

  notification own-lsp-purge {
    uses notification-instance-hdr;
    uses notification-interface-hdr;
    leaf lsp-id {
      type lsp-id;
      description
       "LSP ID.";
    }
    description
      "This notification is sent when the system
      receives a PDU with its own system ID and zero age.
       ";
  }

  notification sequence-number-skipped {
    uses notification-instance-hdr;
    uses notification-interface-hdr;
    leaf lsp-id {
      type lsp-id;
      description
       "LSP ID.";
    }
    description
      "This notification is sent when the system
      receives a PDU with its own system ID and
      different contents. The system has to reissue
      the LSP with a higher sequence number.
       ";
  }

  notification authentication-type-failure {
    uses notification-instance-hdr;
    uses notification-interface-hdr;
    leaf raw-pdu {
      type binary;
      description
       "Received raw PDU.";
    }
    description
      "This notification is sent when the system
      receives a PDU with the wrong authentication type
      field.
      The notification generation must be throttled with
      at least a 5 second gap.
       ";
  }

  notification authentication-failure {
    uses notification-instance-hdr;
    uses notification-interface-hdr;
    leaf raw-pdu {
      type binary;
      description
       "Received raw PDU.";
    }
    description
      "This notification is sent when the system
      receives a PDU with the wrong authentication
      information.
      The notification generation must be throttled with
      at least a 5 second gap.
       ";
  }

  notification version-skew {
    uses notification-instance-hdr;
    uses notification-interface-hdr;
    leaf protocol-version {
      type uint8;
      description
       "Protocol version received in the PDU.";
    }
    leaf raw-pdu {
      type binary;
      description
       "Received raw PDU.";
    }
    description
      "This notification is sent when the system
      receives a PDU with a different protocol version
      number.
      The notification generation must be throttled with at least
       a 5 second gap.
       ";
  }

  notification area-mismatch {
    uses notification-instance-hdr;
    uses notification-interface-hdr;
    leaf raw-pdu {
      type binary;
      description
       "Received raw PDU.";
    }
    description
      "This notification is sent when the system
      receives a Hello PDU from an IS that does
      not share any area address.
      The notification generation must be throttled with at least
       a 5 second gap.
       ";
  }

  notification rejected-adjacency {
    uses notification-instance-hdr;
    uses notification-interface-hdr;
    leaf raw-pdu {
      type binary;
      description
       "Received raw PDU.";
    }
    leaf reason {
      type string;
      description
       "The system may provide a reason to reject the
        adjacency. If the reason is not available,
        the system use an empty string.";
    }
    description
      "This notification is sent when the system
      receives a Hello PDU from an IS but does not
      establish an adjacency for some reason.
      The notification generation must be throttled with at least
       a 5 second gap.
       ";
  }

  notification protocols-supported-mismatch {
    uses notification-instance-hdr;
    uses notification-interface-hdr;
    leaf raw-pdu {
      type binary;
      description
       "Received raw PDU.";
    }
    leaf-list protocols {
      type uint8;
      description
       "The list of protocols supported by the
        remote system.";
    }
    description
      "This notification is sent when the system
      receives a non pseudonode LSP that has no matching
      protocol supported.
      The notification generation must be throttled with at least
       a 5 second gap.
       ";
  }

  notification lsp-error-detected {
    uses notification-instance-hdr;
    uses notification-interface-hdr;
    leaf lsp-id {
      type lsp-id;
      description
       "LSP ID.";
    }
    leaf raw-pdu {
      type binary;
      description
       "Received raw PDU.";
    }
    leaf error-offset {
      type uint32;
      description
       "If the problem is a malformed TLV,
       the error-offset points to the start of the TLV.
       If the problem is with the LSP header,
       the error-offset points to the suspicious byte";
    }
    leaf tlv-type {
      type uint8;
      description
       "if the problem is a malformed TLV, the tlv-type is set
       to the type value of the suspicious TLV.
       Otherwise this leaf is not present.";
    }
    description
      "This notification is sent when the system
      receives a  LSP with a parse error.
      The notification generation must be throttled with at least
       a 5 second gap.
       ";
  }

  notification adjacency-state-change {
    uses notification-instance-hdr;
    uses notification-interface-hdr;
    leaf neighbor {
      type string;
      description
       "Describes the name of the neighbor. If the
       name of the neighbor is not available, the
       field would be empty.";
    }
    leaf neighbor-system-id {
      type system-id;
      description
       "Describes the system-id of the neighbor.";
    }
    leaf state {
      type adj-state-type;

      description
       "This leaf describes the new state of the
        ISIS adjacency.";
    }
    leaf reason {
      type string;
      description
       "If the adjacency is going to DOWN,
       this leaf provides a reason for the adjacency
       going down. The reason is provided as a text.
       If the adjacency is going to UP, no reason is
       provided.";
    }
    description
      "This notification is sent when an ISIS adjacency
       moves to Up state or to Down state.";
  }

  notification lsp-received {
    uses notification-instance-hdr;
    uses notification-interface-hdr;

    leaf lsp-id {
      type lsp-id;
      description
       "LSP ID.";
    }
    leaf sequence {
      type uint32;
      description
       "Sequence number of the received LSP.";
    }
    leaf received-timestamp {
      type yang:timestamp;

      description
       "This leaf describes the timestamp
       when the LSP was received. ";
    }
    leaf neighbor-system-id {
      type system-id;
      description
       "Describes the system-id of the neighbor
       that sent the LSP.";
    }
    description
      "This notification is sent when a LSP
      is received.
      The notification generation must be throttled with at least
       a 5 second gap. ";
  }

  notification lsp-generation {
    uses notification-instance-hdr;

    leaf lsp-id {
      type lsp-id;
      description
       "LSP ID.";
    }
    leaf sequence {
      type uint32;
      description
       "Sequence number of the received LSP.";
    }
    leaf send-timestamp {
      type yang:timestamp;

      description
       "This leaf describes the timestamp
       when our LSP was regenerated. ";
    }
    description
      "This notification is sent when a LSP
      is regenerated.
      The notification generation must be throttled with at least
       a 5 second gap. ";
  }
}
