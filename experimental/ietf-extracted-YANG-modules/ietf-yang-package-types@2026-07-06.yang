module ietf-yang-package-types {
  yang-version 1.1;
  namespace "urn:ietf:params:xml:ns:yang:ietf-yang-package-types";
  prefix "pkg-types";

  import ietf-yang-revisions {
    prefix rev;
    reference "RFC XXXX: Updated YANG Module Revision Handling";
  }

  import ietf-yang-semver  {
    prefix ys;
    reference "RFC XXXX: YANG Semantic Versioning";
  }

  import ietf-yang-types {
    prefix yang;
    rev:recommended-min-date 2025-12-22;
    reference "RFC 9911: Common YANG Data Types.";
  }

  import ietf-inet-types {
    prefix inet;
    rev:recommended-min-date 2025-12-22;
    reference "RFC 9911: Common YANG Data Types.";
  }

  organization
    "IETF NETMOD (Network Modeling) Working Group";

  contact
    "WG Web:   <https://datatracker.ietf.org/wg/netmod/>
     WG List:  <mailto:netmod@ietf.org>

     Editor:   Robert Wilton
               <mailto:rwilton@cisco.com>";

  description
    "This module provides type and grouping definitions for YANG
     packages.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  revision 2026-07-06 {
    ys:version 0.10.0;
    description
      "Initial revision";
    reference
      "RFC XXXX: YANG Packages";
  }

  /*
   * Typedefs
   */

  typedef pkg-name {
    type yang:yang-identifier;
    description
      "Package names are typed as YANG identifiers.";
  }

  typedef pkg-version {
    type ys:version;
    description
      "Packages are versioned using YANG Semver version labels.";
  }

  typedef pkg-reference {
    type string {
      pattern '[a-zA-Z_][a-zA-Z0-9\-_.]*@'
            + '[0-9]+[.][0-9]+[.][0-9]+(_(non_)?compatible)?'
            + '(-[A-Za-z0-9.-]+)?([+][A-Za-z0-9.-]+)?';
      pattern '[^@]+@.{5,128}';
    }
    description
      "Identifies an exact package version as
       '<package-name>@<version>'.
       The name MUST conform to pkg-name and the version MUST conform
       to pkg-version. Exactly one '@' separates the two components.
       The reference does not include a filename extension
       or location.";
  }

  typedef module-name {
    type yang:yang-identifier;
    description
      "Module names are typed as YANG identifiers.";
  }

  typedef version-or-rev-date {
    type union {
      type rev:revision-date;
      type ys:version;
    }
    description
      "Identifies a module by YANG semantic version or revision
       date";
  }

  typedef scoped-feature {
    type string {
      pattern '[a-zA-Z_][a-zA-Z0-9\-_.]*:[a-zA-Z_][a-zA-Z0-9\-_.]*';
    }
    description
      "Represents a feature name scoped to a particular module,
       identified as the '<module-name>:<feature-name>', where both
       <module-name> and <feature-name> are YANG identifier strings,
       as defined by Section 12 of RFC 6020.";
    reference
      "RFC XXXX: YANG Packages";
  }

  typedef pkg-ypath {
    type string;

    description
      "A Ypath, as defined in draft-jgc-netmod-yang-path, that
       identifies a set of data nodes in the schema tree.

       TODO - Check whether any further constraints on the Ypath
       definition are required for use in YANG packages.";
    reference
      "draft-jgc-netmod-yang-path: YANG path format (ypath)";
  }

  /*
   * Groupings
   */
  grouping yang-pkg-identification-leafs {
    description
      "Parameters for identifying a specific version of a YANG
       package";

    leaf name {
      type pkg-name;
      mandatory true;
      description
        "The YANG package name.";
    }

    leaf version {
      type pkg-version;
      mandatory true;
      description
        "Uniquely identifies a particular version of a YANG package.

         Follows the definition of YANG Semver version identifiers.";
      reference
        "RFC XXXX: YANG Semantic Versioning, Section 4.3";
    }
  }

  grouping yang-pkg-exclusions {
    description
      "Parameters for excluding modules and packages from a YANG
       package definition";

    container excludes {
      description
        "Contains parameters for excluding modules and packages
         from a YANG package definition";

      leaf-list module {
        type module-name;
        must "not(. = ../../includes/module/name)" {
          error-message
            "A module cannot be both included and excluded.";
        }
        description
          "Lists implemented modules, of any version, that may
           have been brought in by included packages, but are
           explicitly excluded from this package definition.

           Excluding a module can affect the compliance and
           correctness of any included packages that expect that
           module to be implemented.

           Excluding a module also implicitly excludes any submodules
           and enabled features defined in the excluded module.

           It is an error to list a module in both this list and the
           'includes/module' list.";
      }

      list import-only-module {
        must
          "not(../../includes/import-only-module"
        + "[name = current()/name]"
        + "[version = current()/version])" {
          error-message
            "An import-only module cannot be included and excluded"
          + " with the same name and version values.";
        }
        must
          "version or not(../../includes/import-only-module"
        + "[name = current()/name])" {
          error-message
            "An exclusion of all versions conflicts with an included"
          + " import-only module with the same name.";
        }
        key "name";
        description
          "Lists import-only modules that may have been brought
           in by included packages, but are explicitly excluded from
           this package definition.

           It is an error to list the same module version in both
           this list and the 'includes/import-only-module' list.  If
           no versions are listed for an entry in this list, then
           that entry excludes all versions of the import-only
           module and it is an error to list the same module name in
           the 'includes/import-only-module' list.";

        leaf name {
          type module-name;
          mandatory true;
          description
            "The name of the import-only module to exclude some
             versions of.";
        }

        leaf-list version {
          type version-or-rev-date;
          description
            "Lists specific versions of the import-only module being
              excluded.  If no versions are listed, all versions of
              the import-only module are excluded.

              If required, the YANG Semantic Version SHOULD be used
              to identify the module version, otherwise the YANG
              module revision date is used.";
        }
      }

      leaf-list feature {
        type scoped-feature;
        must "not(. = ../../includes/feature)" {
          error-message
            "A feature cannot be both included and excluded.";
        }
        description
          "Lists features from the 'includes/feature' leaf-list
          exported by an included package that are reclassified as
          being OPTIONAL to support by any server implementing the
          package, overriding the behavior specified by the included
          package.

          It is an error to list a feature in both this leaf-list and
          the 'includes/feature' leaf-list.";
      }
    }
  }

  grouping yang-pkg-location {
    description
      "Parameters for locating a YANG package instance";

    leaf-list location {
      type inet:uri;
      ordered-by user;
      description
        "Contains a URL that represents where a YANG package file
         (.ypkg) for this YANG package can be found.

         This leaf will only be present if there is a URL available
         for retrieval of the schema for this entry.

         If a canonical location for this package is provided,
         it MUST be the first entry in the leaf-list.";
    }
  }

  grouping submodule-identification-leafs {
    description
      "Defines the data nodes for representing a submodule reference
       in a YANG package definition.";

    list submodule {
      key "name";
      description
        "Each entry represents one submodule within the
          parent module.";
      leaf name {
        type module-name;
        mandatory true;
        description
          "The YANG submodule name.";
      }

      leaf version {
        type version-or-rev-date;
        mandatory true;
        description
          "The YANG submodule revision date or YANG Semantic
           version.

          If the parent module include statement for this submodule
          includes a revision date then it MUST match the revision
          date specified here or it MUST match the revision-date
          associated with the version specified here.";
      }

      leaf-list location {
        type inet:uri;
        ordered-by user;
        description
          "Contains a URL from where the YANG schema resource for
          this submodule can be retrieved.

          If a canonical location for this submodule is provided,
          it MUST be the first entry in the leaf-list.";
      }
    }
  }

  grouping module-and-submodule-identification-leafs {
    description
      "Defines the data nodes for representing a module reference
       with its associated submodules.";

    leaf name {
      type module-name;
      mandatory true;
      description
        "The YANG module name.";
    }

    leaf version {
      type version-or-rev-date;
      mandatory true;
      description
        "Identifies the module version.  If available, the YANG
         Semantic Version SHOULD be used, otherwise the YANG module
         revision date is used.";
    }

    leaf-list location {
      type inet:uri;
      ordered-by user;
      description
        "Contains a URL that represents the YANG schema resource
         for this module.

         This leaf will only be present if there is a URL available
         for retrieval of the schema for this entry.

         If a canonical location for this module is provided,
         it MUST be the first entry in the leaf-list.";
    }

    uses submodule-identification-leafs;
  }

  grouping yang-pkg-instance {
    description
      "Specifies the data node for a full YANG package instance
       represented either on a server or in a YANG package file.";
    uses yang-pkg-identification-leafs;

    leaf version-description {
      type string;
      description
        "An optional description of the package version. E.g.,
         perhaps tying it to a software release or a description
         of what key changes have occurred compared to the
         previous version.";
    }

    leaf timestamp {
      type yang:date-and-time;
      description
        "An optional timestamp for when this package was created.
         This does not need to be unique across all versions of a
         package.";
    }

    leaf organization {
      type string;
      description "Organization responsible for this package";
    }

    leaf contact {
      type string;
      description
        "Contact information for the person or organization to whom
         queries concerning this package should be sent.";
    }

    leaf description {
      type string;
      description "Provides a description of the package";
    }

    leaf reference {
      type string;
      description "Allows for a reference for the package";
    }

    leaf complete {
      type boolean;
      default true;
      description
        "Indicates whether this package's resolved schema is
         referentially complete.  I.e. all module imports can be
         resolved to a module version in the resolved package
         schema.";
      reference
        "RFC XXXX: YANG Packages, Section 3.3";
    }

    container includes {
      description
        "Lists package and modules that are included in the package
         definition.";

      list package {
        key "name version";
        ordered-by user;
        description
          "An entry in this list represents a package that is
           included as part of the package definition.

           A package MAY directly include multiple versions of the
           same package, but normally only a single package version
           is expected.  Multiple package versions can be listed,
           for example, to update location information for package
           versions included through other packages.";
        reference
          "RFC XXXX: YANG Packages, Section 4";

        uses yang-pkg-identification-leafs;
        uses yang-pkg-location;
      }

      list module {
        key "name";
        description
          "An entry in this list represents a module that MUST be
          implemented by a server implementing this package, as per
          RFC 7950 section 5.6.5.

          An entry in this list overrides any module version
          'implemented' by an included package.";
        reference
          "RFC 7950: The YANG 1.1 Data Modeling Language.";

        uses module-and-submodule-identification-leafs;
      }

      list import-only-module {
        key "name version";
        description
          "An entry in this list indicates that the server imports
           reusable definitions from the specified version of the
           module, but does not implement any protocol accessible
           objects from this version.

           This entry overrides any import-only module definition
           with the same module name and version from an included
           package.

           Multiple entries for the same module name MAY exist.
           This can occur if multiple modules import the same
           module, but specify different revision-dates in the
           import statements.";

        uses module-and-submodule-identification-leafs;
      }

      leaf-list feature {
        type scoped-feature;
        description
          "Lists features that MUST be supported by any server
           implementing the package.  Each feature MUST be defined
           by the selected implemented version of its named module
           in the resolved package schema, including any selected
           submodules.

           Enabled features specified by any directly included
           packages MUST also be supported by server
           implementations, unless excluded by an entry in the
           'excludes/feature' leaf-list, and do not need to be
           repeated in this leaf-list.

           All other features defined in modules included in the
           package are OPTIONAL to implement.";
      }
    }

    uses yang-pkg-exclusions;

    container depends-on {
      description
        "Provides metadata identifying packages that
         this package depends on, but that do not form part of the
         resolved package schema.

         Dependency metadata is not inherited from included packages,
         so dependencies applicable to this package must be stated
         explicitly in this list.

         For an incomplete package definition, this list can help a
         client resolve a complete schema in a machine readable
         way.";
      reference
        "RFC XXXX: YANG Packages, Section 3.2";

      list package {
        key "name version";
        description
          "An entry in this list represents a package that is
           depended on by this package definition.";

        uses yang-pkg-identification-leafs;
        uses yang-pkg-location;
      }
    }

    list mount {
      key "mount-path";
      description
        "An entry in this list represents additions to the schema
         found at the specified mount point, or, if
         'inherit-mounted-schema' is 'false', replacement of the
         inherited schema found at the specified mount point.";

      leaf mount-path {
        type pkg-ypath;
        mandatory true;
        description
          "A Ypath, as defined in draft-jgc-netmod-yang-path, that
           identifies a mount point within the package schema.  If
           this package is itself mounted, the path is interpreted
           within that mounted schema, with its mount point as the
           root, as specified in RFC 8528, Sections 3.4 and 4.

           Mount paths MUST only be used for schema mount points
           defined in the package schema.";
        reference
          "RFC XXXX: YANG Packages, Section 4;
           draft-jgc-netmod-yang-path: YANG path format (ypath);
           RFC 8528: YANG Schema Mount";
      }

      leaf inherit-mounted-schema {
        type boolean;
        default true;
        description
          "Indicates whether the mounted schema and all its
           properties are inherited from mounts at the same
           mount-path in 'includes/package' entries.

           If set to true (the default), the schema is defined
           as the union of the resolved package schema at the mount
           point by any packages in the 'includes/package' list
           combined with the resolved package schema of all packages
           listed in the 'package' list, plus any additional
           features and parent-references defined for the same
           mount point.  Read-only status and mount mode are also
           inherited.

           If set to false, then the mounted schema starts from a
           blank slate and only packages, additional features, and
           parent-references listed in this 'mount' entry are
           included.  If no packages are listed, no schema is mounted
           at this mount point.  This allows the definitions in the
           mounted packages to be modified (e.g., remove or change
           module versions).  To help conformance, the packages
           listed here SHOULD include all the packages that would
           have been automatically included.
          ";
      }

      leaf read-only {
        type boolean;
        description
          "If true, all data nodes in the mounted schema are
           read-only.  An explicit false value is a schema resolution
           error if the inherited mount is read-only.  If no value is
           inherited or specified, the mount is read-write, subject
           to the configuration restrictions of RFC 8528.

           See 'inherit-mounted-schema' for inheritance behavior.";
        reference
          "RFC XXXX: YANG Packages, Sections 3.5 and 4;
           RFC 8528: YANG Schema Mount, Section 3.3";
      }

      leaf mount-mode {
        type enumeration {
          enum inline {
            description
              "Mount instances may use different schemas, as defined
               by the 'inline' case in RFC 8528.";
          }
          enum shared-schema {
            description
              "All instances of the mount point use the same schema,
               as defined by the 'shared-schema' case in RFC 8528.";
          }
        }
        description
          "The Schema Mount mode for this mount point.  An explicit
           value that conflicts with an inherited mode is a schema
           resolution error.  If no mode is inherited or specified,
           'shared-schema' is used.

           See 'inherit-mounted-schema' for inheritance behavior.";
        reference
          "RFC XXXX: YANG Packages, Section 4;
           RFC 8528: YANG Schema Mount, Section 3.3";
      }

      list package {
        key "name version";
        ordered-by user;
        description
          "The packages that will be mounted at the specified mount
          path.

          A mount point MAY directly list multiple versions of the
          same package, but normally only a single package version
          is expected.  Multiple package versions can be listed,
          for example, to update location information for package
          versions inherited from included packages.

          With mounted-package inheritance enabled (the default),
          these packages are mounted in addition to the mounted
          packages from the 'includes/package' list.

          With mounted-package inheritance disabled, these packages,
          together with any additional features and parent-references
          in the same 'mount' entry, define the mounted package
          schema at this mount point.

          Also see the 'inherit-mounted-schema' leaf.";
        reference
          "RFC XXXX: YANG Packages, Section 4";
        uses yang-pkg-identification-leafs;
        uses yang-pkg-location;
      }

      leaf-list feature {
        type scoped-feature;
        description
          "Features listed here are enabled at the mount point in
           addition to those enabled by the resolved mounted packages
           and, when 'inherit-mounted-schema' is true, by inherited
           'mount/feature' entries.

           This list does not identify the complete set of supported
           features but features already enabled by the resolved
           inherited mounts MAY be listed.

           The features listed here MUST be defined by implemented
           modules in the resolved mounted package schema.

           Features are identified using
           <module-name>:<feature-name>.
           ";
      }

      leaf-list parent-reference {
        type pkg-ypath;
        description
          "A Ypath, as defined in draft-jgc-netmod-yang-path, that
           identifies data nodes in the schema containing the mount
           point, accessible from the mounted schema for the
           evaluation of XPath expressions.

           Parent-references apply only to shared-schema mounts.

           See parent-reference in Schema Mount (RFC 8528) for a
           more detailed description of the accessible data nodes.";
        reference
          "draft-jgc-netmod-yang-path: YANG path format (ypath);
           RFC 8528: YANG Schema Mount";
      }
    }
  }
}
