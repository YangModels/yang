module ietf-fabric-topology-state {

yang-version 1.1;
namespace "urn:ietf:params:xml:ns:yang:ietf-fabric-topology-state";
prefix sfabric;

    import ietf-network-state { prefix nws;  }
import ietf-fabric-types { prefix fabrictype; revision-date "2016-09-29"; }
    import ietf-fabric-topology {prefix fabric;}
    organization
"IETF I2RS (Interface to the Routing System) Working Group";

    contact
    "WG Web:    <http://tools.ietf.org/wg/i2rs/ >
 WG List:   <mailto:i2rs@ietf.org>

 WG Chair:  Susan Hares
            <mailto:shares@ndzh.com>

 WG Chair:  Russ White
            <mailto:russ@riw.us>

 Editor:    Yan Zhuang
            <mailto:zhuangyan.zhuang@huawei.com>

 Editor:    Danian Shi
            <mailto:shidanian@huawei.com>";

description
    "This module contains a collection of YANG definitions for Fabric topology state for non NMDA.

            Copyright (c) 2016 IETF Trust and the persons identified as
            authors of the code.  All rights reserved.

            Redistribution and use in source and binary forms, with or
            without modification, is permitted pursuant to, and subject
            to the license terms contained in, the Simplified BSD License
            set forth in Section 4.c of the IETF Trust's Legal Provisions
            Relating to IETF Documents
            (http://trustee.ietf.org/license-info).

            This version of this YANG module is part of
            draft-zhuang-i2rs-yang-dc-fabric-network-topology;
            see the RFC itself for full legal notices.";

    revision "2017-11-21"{
            description
                    "fix warnings.";
            reference
                    "draft-ietf-i2rs-yang-dc-fabric-network-topology-01";
    }

revision "2017-06-29"{
            description
                    "update to NMDA compliant format";
            reference
                    "draft-zhuang-i2rs-yang-dc-fabric-network-topology-04";
    }

    //grouping statements
    grouping fabric-network-type {
  description "Identify the topology type to be fabric.";
  container fabric-network {
    presence "indicates fabric Network";
    description
    "The presence of the container node indicates
     fabric Topology";
  }
}

grouping fabric-options {
            description "options for a fabric";

    leaf gateway-mode {
        type enumeration {
            enum centralized {
                description "centerilized gateway";
            }
            enum distributed {
                description "distributed gateway";
            }
        }
        default "distributed";
                    description "gateway mode";
    }

    leaf traffic-behavior {
        type enumeration {
            enum normal {
                description "normal";
            }
            enum policy-driven {
                description "policy driven";
            }
        }
        default "normal";
                    description "traffic behavior of the fabric";
    }

    leaf-list capability-supported {
        type fabrictype:service-capabilities;
                    description
                            "supported services of the fabric";
    }
}

grouping device-attributes {
            description "device attributes";
    leaf device-ref {
        type fabrictype:node-ref;
                    description
                            "the device it includes to";
    }
    leaf role {
        type fabrictype:device-role;
        default "LEAF";
                    description
                            "role of the node";
    }
}

grouping link-attributes {
            description "link attributes";
    leaf link-ref {
        type fabrictype:link-ref;
                    description
                            "the link it includes";
    }
}

    grouping port-attributes {
            description "port attributes";
    leaf port-ref {
        type fabrictype:tp-ref;
                    description
                            "port reference";
    }
    leaf port-type {
        type enumeration {
            enum ETH {
                                    description "ETH";
                            }
            enum SERIAL {
                                    description "Serial";
                            }
        }
                    description
                            "port type: ethernet or serial";
    }
    leaf bandwith {
        type enumeration {
            enum 1G {
                                    description "1G";
                            }
            enum 10G {
                                    description "10G";
                            }
            enum 40G {
                                    description "40G";
                            }
            enum 100G {
                                    description "100G";
                            }
            enum 10M {
                                    description "10M";
                            }
            enum 100M {
                                    description "100M";
                            }
            enum 1M {
                                    description "1M";
                            }
        }
                    description
                            "bandwidth on the port";
    }
}

grouping fabric-attributes {
            description "attributes of a fabric";

            leaf fabric-id {
            type fabric:fabric-id;
                            description
                                    "fabric id";
    }

    leaf name {
        type string;
                    description
                            "name of the fabric";
    }

    leaf type {
        type fabrictype:underlayer-network-type;
        description
                            "The type of physical network that implements this fabric.Examples are vlan, and trill.";
    }

            container vni-capacity {
        description "number of vnis the fabric has";
        leaf min {
            type int32;
                            description
                                    "vni min capacity";
        }

        leaf max {
            type int32;
                            description
                                    "vni max capacity";
        }
    }

    leaf description {
        type string;
                    description
                            "description of the fabric";
    }

    container options {
                    description "options of the fabric";
        uses fabric-options;
    }

    list device-nodes {
                    key device-ref;
                    description "include device nodes in the fabric";
        uses device-attributes;
    }

    list device-links {
                    key link-ref;
                    description "include device links within the fabric";
        uses link-attributes;
    }

            list device-ports {
        key port-ref;
                    description "include device ports within the fabric";
        uses port-attributes;
    }

}

    // augment statements

    augment "/nws:networks/nws:network/nws:network-types" {
description
  "Introduce new network type for Fabric-based logical topology";

            uses fabric-network-type;
    }

augment "/nws:networks/nws:network/nws:node" {
    when "/nws:networks/nws:network/nws:network-types/sfabric:fabric-network" {
    description
      "Augmentation parameters apply only for networks
       with fabric topology.";
  }
    description "Augmentation for fabric nodes.";

    container fabric-attribute-state {
                    config false;
                    description
                    "attributes for a fabric network";

        uses fabric-attributes;
    }
}
}
