module sd-onos-service-types { 
    namespace "urn:onos:service-types"; 
    prefix service-types ; 

    import ietf-inet-types {prefix inet; } 
    import sd-onos-common-types {prefix  types; revision-date 
	"2015-10-14";}     

  organization ""; 
  contact ""; 
  revision "2015-10-14" {description "revised revision.";} 

    typedef exp { 
        type enumeration { 
            enum BE { 
                value 0 ; 
                description "BE." ; 
            } 
            enum AF1 { 
                value 1 ; 
                description "AF1." ; 
            } 
            enum AF2 { 
                value 2 ; 
                description "AF2." ; 
            } 
            enum AF3 { 
                value 3 ; 
                description "AF3." ; 
            } 
            enum AF4 { 
                value 4 ; 
                description "AF4." ; 
            } 
            enum EF { 
                value 5 ; 
                description "EF." ; 
            } 
            enum CS6 { 
                value 6 ; 
                description "CS6." ; 
            } 
            enum CS7 { 
                value 7 ; 
                description "CS7." ; 
            } 
        } 
        default CS7; 
    } 

    typedef pw-role{ 
        type enumeration { 
            enum normal{ 
                value 0 ; 
                description "normal." ; 
            } 
            enum master { 
                value 1 ; 
                description "master." ; 
            } 
            enum slave { 
                value 2 ; 
                description "slave." ; 
            } 
            enum DNI-PW { 
                value 3 ; 
                description "DNI PW." ; 
            } 
        } 
        default normal; 
    } 

    grouping qos-if-car { 
        description "qos parameter." ; 
        leaf direction { 
            description "qos for interface car" ; 
            type enumeration { 
                enum inbound{ 
                    value 0 ; 
                    description "inbound." ; 
                } 
                enum outbound { 
                    value 1 ; 
                    description "outbound." ; 
                } 
            } 
        }  

        leaf cir { 
            description "forward CIR. unit:Kbps" ; 
            type int32; 
        }   
        leaf pir { 
            description "forward PIR. unit:Kbps" ; 
            type int32; 
        }   
        leaf cbs { 
            description "forward CBS. unit:Kbps" ; 
            type int32; 
        }    
        leaf pbs { 
            description "forward PBS. unit:Kbps" ; 
            type int32; 
        }    
    } 

    grouping protect-policy { 

        leaf protect-type { 
            description "protection type" ; 
            type enumeration { 
                enum unprotected { 
                    value 0 ; 
                    description "unprotected." ; 
                } 
                enum protected { 
                    value 1 ; 
                    description "protection." ; 
                } 
            } 
            default unprotected ; 
        } 

        leaf revertive-type { 
            description "revertive mode" ; 
            type enumeration { 
                enum no-revertive { 
                    value 0 ; 
                    description "unprotected." ; 
                } 
                enum revertive { 
                    value 1 ; 
                    description "protection." ; 
                } 
            }  
        }                
        leaf wtr { 
            description "WTR.unit:s" ; 
            type uint32; 
            default 300; 
        }  
    } 
    grouping oam-policy { 
        leaf detect-type { 
            description "detect type" ; 
            type enumeration { 
                enum undetect { 
                    value 0 ; 
                    description "unprotected." ; 
                } 
                enum APS { 
                    value 1 ; 
                    description "protection." ; 
                } 
                enum BFD { 
                    value 2 ; 
                    description "unprotected." ; 
                }                
            }  
        }   
        container bfd-detect-para {                       
            leaf ingress-discriminator { 
                description "ingress-discriminator" ; 
                type int32;         
            }     
            leaf egress-discriminator { 
                description "egress-discriminator" ; 
                type int32;         
            }   
            leaf tx-interval { 
                description "tx-interval" ; 
                type int32;         
            }   
            leaf rx-interval { 
                description "rx-interval" ; 
                type int32;         
            }   
            leaf detect-interval { 
                description "detect-interval" ; 
                type int32;         
           }                               
        }  
    }     
    grouping ac { 
        leaf id{ 
            mandatory true; 
            description "ac id." ; 
            type string; 
        } 
        leaf name{ 
            config false; 
            description "ac name." ; 
            type string; 
        } 

        leaf ne-id { 
            mandatory true; 
            description "ne id." ; 
            type string ; 
        } 

        leaf ltp-id { 
            mandatory true; 
            description "ltp id." ; 
            type string ; 
        } 
       leaf admin-status { 
            type types:admin-status; 
       } 
       leaf operate-status { 
           type types:operate-status; 
        }         
        container l2-access { 
            description "link layer access information of ac." ; 
            uses l2-access; 
        }         

        leaf role { 
            description "role of snc lsp." ; 
            type enumeration { 
                enum master { 
                    value 0 ; 
                    description "master." ; 
                } 
                enum slave { 
                    value 1 ; 
                    description "slave." ; 
                } 
                enum hub { 
                    value 2 ; 
                    description "hub." ; 
                } 
                enum spoke { 
                    value 3 ; 
                    description "spoke." ; 
                } 
            } 
            default master; 
        } 
        container qos-policy {   
            container qos-if-cars {          
                list qos-if-car { 
                   key "direction"; 
                   uses qos-if-car; 
                } 
            } 
        } 
    } 
    grouping l3-ac { 
        uses ac; 
        container connection { 
            description "connection information of ac." ; 
            uses connection; 
        }         
    } 
    grouping l2-access { 
        leaf access-type{ 
            mandatory true;    
            type enumeration { 
                enum Port { 
                    value 0 ; 
                    description "master." ; 
                } 
                enum Dot1Q { 
                    value 1 ; 
                    description "Dot1Q." ; 
                }     
                enum QinQ { 
                    value 2 ; 
                    description "QinQ." ; 
                } 
            } 
        } 
        leaf dot1q-vlan-bitmap { 
            mandatory true;    
            description "Dot1Q Vlan Bitmap." ; 
            type string; 
        } 

        leaf qinq-svlan-bitmap { 
            mandatory true;    
            description "QinQ svlan Bitmap." ; 
            type string; 
        } 

        leaf qinq-cvlan-bitmap { 
            mandatory true;    
            description "QinQ cvlan Bitmap." ; 
            type string; 
        }                         
        leaf access-action { 
            mandatory true;    
            description "access type." ; 
            type enumeration { 
                enum Keep { 
                    value 0 ; 
                    description "keep." ; 
                } 
                enum Push { 
                    value 1 ; 
                    description "push." ; 
                }    
                enum Pop { 
                    value 2 ; 
                    description "pop." ; 
                } 
                enum Swap { 
                    value 3 ; 
                    description "swap." ; 
                }                 
            } 
        }             

        leaf action-vlan-id { 
            description "action vlan id." ; 
            type int32 { 
                range "1..4094"; 
            } 
        }     
    }     
    grouping connection { 
        leaf ip-address { 
            description "ip address of access circuit's 
            connectio." ; 
            type inet:ip-address ; 
        } 
        leaf mask-length { 
            description "mask length of ip address." ; 
            type int32 { 
                range "1..32"; 
            } 
        } 
        leaf protocols { 
            description "protocols between PE and CE." ; 
            type enumeration { 
                enum static { 
                    value 0 ; 
                    description "static." ; 
                } 
                enum ospf { 
                    value 1 ; 
                    description "ospf." ; 
                }    
                enum isis { 
                    value 2 ; 
                    description "bgp" ; 
                }                   
                enum bgp { 
                    value 3 ; 
                    description "bgp" ; 
                }              
            } 
        }             
        container static-routes {       

            list static-route { 
                key "ip-prefix mask-length"; 
                leaf ip-prefix { 
                    type inet:ipv4-address; 
                } 
                leaf mask-length { 
                    type uint32 { 
                         range "1..32"; 
                    } 
                } 
                leaf next-hop { 
                    type inet:ipv4-address ; 
                } 
                leaf preference { 
                    type uint32 { 
                        range "1..65535"; 
                    } 
                } 
            } 
        }         
    } 

    grouping pw{ 
        leaf id { 
            description "ID of pw." ; 
            type string ; 
        } 
        uses encaplate-type-grouping; 

        leaf ingress-ne-id { 
            description "ingress ne id." ; 
            type string ; 
        } 

        leaf egress-ne-id { 
            description "egress ne id." ; 
            type string ; 
        } 

        leaf ctrl-word-support { 
            description "ctrl word support. 0 : not support, 1 : 
            support" ; 
            type enumeration { 
                enum not-support { 
                    value 0 ; 
                    description "pw doesn't support control word" ; 
                } 
                enum support { 
                    value 1 ; 
                    description "pw supports control word" ; 
                } 
            } 
            default support; 
        } 

        leaf sn-support { 
            description "serial number support. 0 : not support, 
            1 : support" ; 
            type enumeration { 
                enum not-support { 
                    value 0 ; 
                    description "pw doesn't support control word" ; 
                } 
                enum support { 
                    value 1 ; 
                    description "pw supports control word" ; 
                } 
            } 
            default not-support; 
        } 

        leaf vccv-type { 
            description "vccv type" ; 
            type enumeration { 
                enum not-support { 
                    value 0 ; 
                    description "pw doesn't support vccv" ; 
                } 
                enum CWD { 
                    value 1 ; 
                    description "pw supports vccv" ; 
                } 
                enum Label-alert { 
                    value 2 ; 
                    description "pw supports vccv" ; 
                } 
                enum TTL { 
                    value 3 ; 
                    description "pw supports vccv" ; 
                } 
                enum CWD&Label-alert { 
                    value 4 ; 
                    description "pw supports vccv" ; 
                } 
                enum CWD&TTL { 
                    value 5 ; 
                    description "pw supports vccv" ; 
                } 
                enum Label-alert&TTL { 
                    value 6 ; 
                    description "pw supports vccv" ; 
                } 
                enum CWD&Label-alert&TTL { 
                    value 7 ; 
                    description "pw supports vccv" ; 
                } 
            } 
            default not-support; 
        } 

        leaf conn-ack-type { 
            description "Connectivity test type" ; 
            type enumeration { 
                enum not-support { 
                   value 0 ; 
                     description "pw doesn't support connection 
                     ack" ; 
                } 
                enum support { 
                    value 1 ; 
                    description "pw supports connection ack" ; 
                } 
            } 
            default not-support; 
        } 
        container tunnels { 
            list tunnel{ 
                key "tunnel-id"; 
                uses tunnel; 
            } 
        } 
    } 
    grouping tunnel { 
        leaf tunnel-id { 
            description "ID of tunnel." ; 
            type string ; 
        } 
        description "tunnel infomation" ; 
    } 
    grouping encaplate-type-grouping { 
        leaf encaplate-type { 
            description "encaplate type." ; 
            type enumeration { 
                enum NONE { 
                    value 0 ; 
                    description "none." ; 
                } 
                enum fr-dlci-martini { 
                    value 1 ; 
                    description "fr-dlci-martini." ; 
                } 
                enum atm-aal5-sdu { 
                    value 2 ; 
                    description "atm-aal5-sdu." ; 
                } 
                enum atm-transparent { 
                    value 3 ; 
                    description "atm-transparent." ; 
                } 
                enum ethernet-vlan { 
                    value 4 ; 
                    description "ethernet-vlan." ; 
                } 
                enum ethernet  { 
                    value 5 ; 
                    description "ethernet ." ; 
                } 
                enum  hdlc { 
                    value 6 ; 
                    description " hdlc." ; 
                } 
                enum ppp { 
                    value 7 ; 
                    description "ppp." ; 
                } 
                enum cep-mpls { 
                    value 8 ; 
                    description " cep-mpls." ; 
                } 
                enum atm-ntol { 
                    value 9 ; 
                    description "atm-ntol." ; 
                } 
                enum atm-nto1-vpc { 
                    value 10 ; 
                    description "atm-nto1-vpc." ; 
                } 
                enum ip-layer2 { 
                    value 11 ; 
                    description " ip-layer2." ; 
                } 
                enum atm-1to1-vcc { 
                    value 12 ; 
                    description "atm-1to1-vcc." ; 
                } 
                enum atm-1to1-vpc { 
                    value 13 ; 
                    description "atm-1to1-vpc." ; 
                } 
                enum atm-aal5-pdu { 
                    value 14 ; 
                    description "atm-aal5-pdu." ; 
                } 
                enum fr-port { 
                    value 15 ; 
                    description "fr-port." ; 
                } 
                enum cep-packet { 
                    value 16 ; 
                    description "cep-packet." ; 
                } 
                enum e1 { 
                    value 17 ; 
                    description "e1." ; 
                } 
                enum t1 { 
                    value 18 ; 
                    description "t1." ; 
                } 
                enum e3 { 
                    value 19 ; 
                    description "e3." ; 
                } 
                enum t3 { 
                    value 20 ; 
                    description " t3." ; 
                } 
                enum cesopsn-basic { 
                    value 21 ; 
                    description "cesopsn-basic." ; 
                } 
                enum tdmoip-aal1 { 
                    value 22 ; 
                    description "tdmoip-aal1." ; 
                } 
                enum cesopsn-tdm { 
                    value 23 ; 
                    description "cesopsn-tdm." ; 
                } 
                enum tdmoip-aal2 { 
                    value 24 ; 
                    description "tdmoip-aal2." ; 
                } 
                enum fr-dlci { 
                    value 25 ; 
                    description "fr-dlci." ; 
                } 
            } 
        } 
    } 

    grouping pw-trail{ 
        leaf id { 
            description "ID of pw-trail." ; 
            type string ; 
        } 

        leaf role { 
            description "role of pw-trail." ; 
            type pw-role; 
        } 
        container pw-lists { 
            list pw-list { 
                 key id; 
                 uses pw ; 
            } 
        } 
    } 
    grouping tunnel-service { 
        leaf signaling-type { 
            description "signaling type." ; 
            type enumeration { 
                enum RSVP-TE { 
                    value 0 ; 
                    description "RSVP-TE" ; 
                } 
                enum LDP { 
                    value 1 ; 
                    description "LDP" ; 
                } 
                enum GRE { 
                    value 2 ; 
                    description "GRE" ; 
                } 
                enum SR-BE { 
                    value 3 ; 
                    description "SR-BE" ; 
                } 
                enum SR-TE { 
                    value 4 ; 
                    description "SR-TE" ; 
                } 
            } 
            default RSVP-TE; 
        }  
        leaf tunnel-mode { 
            description "service to tunnel mode." ; 
            type enumeration { 
                enum Nto1 { 
                    value 0 ; 
                    description "multi service one tunnel" ; 
                } 
                enum 1to1 { 
                    value 1 ; 
                    description "oner service one tunnel" ; 
                } 
            } 
            default Nto1; 
        } 
        container protect-policy { 
            uses protect-policy; 
        } 
        container oam-policy {         
            uses oam-policy; 
        } 
        leaf latency { 
            description "tunnel latency requirement." ; 
            type int32; 
        } 
    } 
    grouping service-path {       

        leaf service-id { 
            description "l2vpn or l3vpn service id." ; 
            type string ; 
        } 
        leaf source-ne-id { 
            description "source ne id." ; 
            type string ; 
        } 
        leaf source-ac-id { 
            description "source ltp id." ; 
            type string ; 
        } 
        leaf destination-ne-id { 
            description "destination ne id." ; 
            type string ; 
        } 

        leaf destination-ac-id { 
            description "destination ltp id." ; 
            type string ; 
        }         
        container path-lists{  
            list path-list { 
                key "path-layer path-role";  
                leaf path-layer { 
                     description "path type. 0 : PW, 1 : BGP-LSP, 
                     2 : PW" ; 
                    type enumeration { 
                        enum PW { 
                            value 0 ; 
                            description "pw path." ; 
                        } 
                        enum BGP-LSP { 
                            value 1 ; 
                            description "BGP-LSP Path." ; 
                        } 
                        enum LSP { 
                            value 2 ; 
                            description "LSP Path." ; 
                        } 
                    } 
                } 
                leaf path-role { 
                     description "path role.. 0 : master, 1 : 
                     backup, 2 : Bypass." ; 
                    type enumeration { 
                        enum Primary { 
                            value 0 ; 
                            description "master path." ; 
                        } 
                        enum Backup { 
                            value 1 ; 
                            description "backup path." ; 
                        } 
                        enum Active { 
                            value 2 ; 
                            description "active path." ; 
                        } 
                    } 
                } 
                container paths { 
                    list path { 
                        key "ne-id"; 
                        leaf ne-id { 
                           type string; 
                        } 
                        leaf ingress-ltp-id { 
                           type string; 
                        } 
                        leaf backward-peer-id { 
                           type string; 
                        }  
                        leaf egress-ltp-id { 
                           type string; 
                        } 
                        leaf forward-peer-id { 
                           type string; 
                        } 
                    }  
                }  
            }    
        } 
    }  
}
