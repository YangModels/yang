module ietf-yang-instance-data-annotations {
   yang-version 1.1;
   namespace
     "urn:ietf:params:xml:ns:yang:ietf-yang-instance-data-annotations";
   prefix ida ;

   import ietf-yang-types { prefix "yang"; }
   import ietf-yang-metadata { prefix "md"; }

   organization  "IETF NETMOD Working Group";
   contact
   "WG Web:   <https://datatracker.ietf.org/wg/netmodf/>

    WG List:  <mailto:netmod@ietf.org>

    Author:  Balazs Lengyel
       <mailto:balazs.lengyel@ericsson.com>";

   description "The module defines annotations to allow defining
      metadata for YANG Instance Data files.";
   reference  "RFC 7950, RFC 7962";

   revision 2017-08-24 {
      description  "Initial revision.";
      reference "RFC XXXX: YANG Instance Data";
   }

   md:annotation instance-data-set {
       type yang:yang-identifier;
      description "Defines the name of a YANG instance data set.

         The annotation SHALL only be used on the top level
         <data> element in RFC XXXX defined YANG Instance Data files.
         Exactly one instance-data-set annotation SHALL be used per
         <data> element.";
    }

    md:annotation contact {
       type string;
      description "Contains the same information the ontact statement
         carries for a YANG module.

         The annotation SHALL only be used on the top level
         <data> element in RFC XXXX defined YANG Instance Data files.
         Zero or one contact annotation SHALL be used per
         <data> element.";
    }

    md:annotation organization {
       type string;
      description "Contains the same information the organization
         statement carries for a YANG module.

         The annotation SHALL only be used on the top level
         <data> element in RFC XXXX defined YANG instance data files.
         Zero or one organization annotation SHALL be used per
         <data> element.";
    }

    md:annotation revision {
       type string {
          pattern '\d{4}-\d{2}-\d{2}';
       }
      description "Specifies the data the instance-data-set was
         modified for this release.

         The annotation SHALL only be used on the top level
         <data> element in RFC XXXX defined YANG Instance Data files.
         One or more revision annotations SHALL be used per
         <data> element.
         A separate annotation SHOULD be added each time the
         instance-data-set is released.";
    }

    md:annotation description {
       type string;
      description "Defines the name of a YANG instance data set.

         The annotation SHALL be used on the top level <data> element
         in RFC XXXX defined YANG Instance Data files, and MAY be used
         on other data elements of an instance data file.
         Zero one description annotation SHALL be used per element, but
         exactly one description annotation SHALL be used on the top
         level <data> element.";
    }
}
