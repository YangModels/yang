module service-node {

  namespace "urn:cisco:params:xml:ns:yang:sfc-sn";

  prefix sfc-sn;

  import ietf-inet-types { prefix inet; }
  import ietf-yang-types { prefix yang; }
  import service-function {prefix sfc-sf; }

  organization "Cisco Systems, Inc.";
  contact "Reinaldo Penno <repenno@cisco.com>";

  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-05-08 {
    description
      "Initial revision.";
  }

  // Transport type definitions

  identity transport-type-identity {
    description
      "Base identity from which specific transport types are
      derived.";
  }

  identity vxlan-gpe {
    base "transport-type-identity";
    description "Programmable vxlan transport type";
  }

  typedef transport-type {
    type identityref {
      base "transport-type-identity";
    }
  }

  // Failmode type definitions

  identity failmode-type-identity {
    description
      "Base identity from which specific failmode
       types are derived. Fail mode specifies the behavior
       when the interface does not have connectivity to the
       service node.";
  }

  typedef failmode-type {
    type identityref {
      base "failmode-type-identity";
    }
  }

  identity close {
    base "failmode-type-identity";
    description "When service-node can not reach service function, packets will be dropped";
  }

  identity open {
    base "failmode-type-identity";
    description "When service-node can not reach service function, packets will be forwarded";
  }

  // Service Nodes

  // Service Node Type definitions

  identity service-node-type-identity {
    description
          "Base identity from which specific service function types are
          derived.";
  }

  identity egress {
    base "service-node-type-identity";
    description "Last node in the chain";
  }

  identity ingress {
    base "service-node-type-identity";
    description "First node in the chain";
  }

  identity middle {
    base "service-node-type-identity";
    description "Service nodes in the middle of the chain";
  }

  identity legacy {
    base "service-node-type-identity";
    description "Service Nodes that need a proxy function";
  }

  typedef service-node-type {
    type identityref {
      base "service-node-type-identity";
    }
  }

  typedef service-node-ref {
    type leafref {
      path "/sfc-sn:service-nodes/sfc-sn:service-node/sfc-sn:name";
    }
    description
      "This type is used by data models that need to reference
       configured service functions.";
  }

  container service-nodes {
    description
      "Physical or virtual element that hosts one or
      more service functions and has one or more network locators
      associated with it for reachability and service delivery.";
    list service-node {
      key "name";
      leaf name {
        type string;
        description
             "The name of the service node.";
        mandatory true;
      }
      leaf type {
        type service-node-type;
      }
      leaf transport {
        type transport-type;
      }
      leaf ip-host-address {
        type inet:ip-address;
      }
      leaf failmode {
        type failmode-type;
      }
      leaf-list service-function {
        type sfc-sf:service-function-ref;
        description
        "A list of service functions resident in this service node";
      }
    }
  }
}
