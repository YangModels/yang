module ietf-vn-rsc {
  yang-version 1.1;
  namespace "urn:ietf:params:xml:ns:yang:ietf-vn-rsc";
  prefix vnrsc;

  import ietf-inet-types {
    prefix inet;
  }
  import ietf-l3vpn-svc {
    prefix l3vpn-svc;
  }
  import ietf-interfaces{
    prefix if;
  }

  organization
    "IETF OPSAWG Working Group.";
  contact
    "WG List: foo@ietf.org
    Editor:  Qin Wu <mailto:bill.wu@huawei.com>
    Editor:  Zitao Wang <mailto:wangzitao@huawei.com>";

  description
    "The YANG module defines a generic service configuration
    model for Layer VN services common across all of the
    vendor implementations.";

revision 2018-02-03{
description
"Initial revision";
reference
"A YANG Data Model for VN Service Delivery.";
}
/* Features */

/* Typedefs */
typedef svc-id {
 type string;
 description
 "Type definition for servicer identifier";
}
 typedef address-family {
  type enumeration {
   enum ipv4 {
    description
     "IPv4 address family.";
   }
   enum ipv6 {
    description
     "IPv6 address family.";
   }
  }
  description
   "Defines a type for the address family.";
 }
 /*

/* Identities */
 identity vn-type {
  description
  "Base identity for VN type";
 }
 identity l2vpn {
  base vn-type;
  description
  "Identity for Layer 2 vpn";
 }
 identity l3vpn {
  base vn-type;
  description
  "Identity for Layer 3 vpn";
 }
 identity evpn {
  base l2vpn;
  description
  "Identity for evpn";
 }
 identity vpls {
  base l2vpn;
  description
  "Identity for vpls";
 }
 identity vpw {
  base l2vpn;
  description
  "Identity for vpw";
 }
 identity vpn-topology {
  description
   "Base identity for VPN topology.";
 }
 identity any-to-any {
  base vpn-topology;
  description
   "Identity for any-to-any VPN topology.";
 }
 identity hub-spoke {
  base vpn-topology;
  description

   "Identity for Hub-and-Spoke VPN topology.";
 }
 identity hub-spoke-disjoint {
  base vpn-topology;
  description
   "Identity for Hub-and-Spoke VPN topology
    where Hubs cannot communicate with each other.";
 }

 identity objective-function{
  description
  "Identity for objective function";
 }

 identity metric-type{
  description
  "Identity for metric type";
 }

 identity hop-type{
  description
  "Identity for hop-type";
 }
 identity loose{
  base hop-type;
  description
  "loose hop in an explicit path";
 }
 identity strict{
  base hop-type;
  description
  "strict hop in an explicit path";
 }
/* Grouping */
grouping vn-service-list {
 list vn-service {
  key "vn-id";
  leaf vn-id {
   type svc-id;
   description
   "VN id";
  }
  leaf customer-name {
   type string;
   description
   "Customer name";
  }
  leaf service-topology {
   type identityref {
    base vpn-topology;
   }
   default any-to-any;
   description
    "VPN service topology.";
  }
  container site-network-accesses{
   list site-network-access{
    key "site-network-access-id";
    leaf site-network-access-id{
     type svc-id;
     description
     "Site network access identifier";
    }
    description
    "List for site-network access";
   }
   description
   "Container for site network accesses";
  }

  description
  "List for vn service";
 }
 description
 "Grouping for vn service list";
}
grouping vn-services-grouping{
 container vn-services{
  uses vn-service-list;
  description
  "Container for virtual network service";
 }
 description
 "Grouping for vn services";
}

grouping interfaces-grouping{
 container interfaces{
  leaf interface{
   type if:interface-ref;
   description
   "Base interface";
  }
  leaf-list sub-interfaces{
   type if:interface-ref;
   description
   "Sub interfaces";
  }
  description
  "Container for interfaces";
 }
 description
 "Grouping for interfaces";
}

grouping cpe-device-list{
 list cpe-device{
  key "device-id";
  leaf device-id {
   type svc-id;
   description
   "Device identifier";
  }
  leaf address-family{
   type address-family;
   description
    "Address family used for management. If address-family
    is specified, the address may or may not be specified
   (by the customer).";
  }
  leaf address{
   type inet:ip-address;
   description
   "IP address";
  }
  uses interfaces-grouping;
  description
  "List for devices";
 }
 description
 "Grouping for cpe device list";

}
grouping cpe-devices-grouping{
 container cpe-devices{
  uses cpe-device-list;
  description
  "Container for cpe devices";
 }
 description
 "grouping for cpe-devices-grouping";
}

grouping bandwidth-grouping {
 leaf svc-input-bandwidth{
  type uint32;
  description
  "Service input bandwidth";
 }
 leaf svc-output-bandwidth{
  type uint32;
  description
  "Service output bandwidth";
 }
 description
 "Grouping for bandwidth";
}

grouping attachment-point-grouping{
 container attachment-point{
   leaf pe-device-id {
   type svc-id;
   description
   "PE Device identifier";
  }
  leaf address-family{
   type address-family;
   description
    "Address family used for management. If address-family
    is specified, the address may or may not be specified
   (by the customer).";
  }
  leaf address{
   type inet:ip-address;
   description
   "IP address";
  }
  uses interfaces-grouping;
  description
  "Container for attachment point";
 }
 description
 "Grouping for attachment points";
}

grouping vn-attachment-list{
 list vn-attachment{
  key "vn-id";
  leaf vn-id{
   type svc-id;
   description
   "Virtual network identifier";
  }
  leaf vn-type{
   type identityref{
    base vn-type;
   }
   description
   "VN type";
  }
  uses attachment-point-grouping;
  description
  "List for VN attachments";
 }
 description
 "Grouping for VN attachment list";
}

grouping vn-attachments-grouping{
 container vn-attachments{
  uses vn-attachment-list;
  description
  "Container for VN attachments";
 }
 description
 "Grouping for VN attachments";
}

grouping site-network-access-list{
 list site-network-access{
  key "site-network-access-id";
  leaf site-network-access-id{
   type leafref{
    path "/vn-svc/vn-services/vn-service"
 +"/site-network-accesses/site-network-access"
 +"/site-network-access-id";
   }
   description
   "Site network access identifier";
  }
  leaf device-id {
   type leafref{
    path "/vn-svc/sites/site/cpe-devices"
 +"/cpe-device/device-id";
   }
   description
   "Device id";
  }
  uses l3vpn-svc:access-diversity;
  container service {
   uses bandwidth-grouping;
   leaf svc-mtu {
    type uint16;
 description
 "Service-mtu";
   }
   uses l3vpn-svc:site-service-qos-profile;
   description
   "Container for service";
  }
  uses vn-attachments-grouping;
  description
  "List for site-network access";

 }
 description
 "Grouping for site-network access list";
}

grouping site-network-accesses-grouping{
 container site-network-accesses{
  uses site-network-access-list;
  description
  "Container for site network accesses";
 }
 description
 "Grouping for site network accesses";
}

grouping site-list-grouping{
 list site {
  key "site-id";
  leaf site-id {
   type svc-id;
   description
   "Site identifier";
  }
  uses cpe-devices-grouping;
  container service {
   uses l3vpn-svc:site-service-qos-profile;
   description
   "Site service";
  }
  uses site-network-accesses-grouping;
  description
  "List for sites";
 }
 description
 "Grouping for site list";
}

grouping sites-grouping {
 container sites{
  uses site-list-grouping;
  description
  "Container for sites";
 }
 description
 "Grouping for sites";
}

grouping src-grouping{
   container src{
    leaf src-address{
  type leafref {
   path "/vn-svc/sites/site/site-id";
  }
  description
  "Leaf list for source address";
 }
 leaf site-network-access-id{
  type leafref {
   path "/vn-svc/sites/site/site-network-accesses"+
   "/site-network-access/site-network-access-id";
  }
  description
  "Leaf list for site-network-access id";
 }
    description
 "Container for source id";
   }
 description
 "Grouping for source site";
}

grouping dst-grouping{
  container dst{
    leaf dst-address{
  type leafref {
   path "/vn-svc/sites/site/site-id";
  }
  description
  "Leaf list for source address";
 }
 leaf site-network-access-id{
  type leafref {
   path "/vn-svc/sites/site/site-network-accesses"+
   "/site-network-access/site-network-access-id";
  }
  description
  "Leaf list for site-network-access id";
 }
    description
 "Container for destination id";
   }
 description
 "Grouping for source site";
}

grouping objective-function-group{
 leaf objective-function {
  type identityref{
   base objective-function;
  }
  description
  "operational state of the objective function";
  }
  description
  "Grouping for objective functions";
}

grouping path-element-list{
 list path-element{
  key "path-element-id";
  leaf path-element-id{
   type leafref{
   path "/vn-svc/sites/site/site-network-accesses"+
   "/site-network-access/vn-attachments/vn-attachment"+
   "/attachment-point/pe-device-id";
   }
   description
   "Path element identifier";
  }
  leaf address{
   type leafref{
   path "/vn-svc/sites/site/site-network-accesses"+
   "/site-network-access/vn-attachments/vn-attachment"+
   "/attachment-point/address";
   }
   description
   "Path element address";
  }
  description
  "List for path elements";
 }
 description
 "Grouping for path elements";
}

grouping constraint-grouping{
 container constraint{
  config false;
  uses path-element-list;
  description
  "Container for constraint";
 }
 description
 "Grouping for constraint";
}

grouping metric-grouping{
 list metric {
  key metric-type;
  leaf metric-type {
   type identityref{
    base metric-type;
   }
   description
   "Metric type";
  }
  leaf metric-value {
   type uint32;
   description
   "Metric value";
  }
  description
  "List for metric";
 }
 description
 "Grouping for metric";
}

grouping path-list{
 list path-element{
  key "path-element-id";
  leaf path-element-id{
   type leafref{
   path "/vn-svc/sites/site/site-network-accesses"+
   "/site-network-access/vn-attachments/vn-attachment"+
   "/attachment-point/pe-device-id";
   }
   description
   "Path element identifier";
  }
  leaf index{
   type uint32;
   description
   "Index";
  }
  leaf address{
   type leafref{
   path "/vn-svc/sites/site/site-network-accesses"+
   "/site-network-access/vn-attachments/vn-attachment"+
   "/attachment-point/address";
   }
   description
   "Path element address";
  }
  leaf hop-type{
   type identityref {
    base hop-type;
   }
   description
   "Hop type";
  }
  description
  "List for path elements";
 }
 description
 "Grouping for path list";
}

grouping path-grouping{
 container path{
 uses path-list;
 description
 "Container for path";
 }
 description
 "Grouping for path";
}
grouping access-grouping{
 list source-access{
  key "access-id";
  leaf access-id {
    type leafref{
  path "/vn-svc/sites/site/site-network-accesses"
  +"/site-network-access/site-network-access-id";
 }
   description
   "Access id";
  }
  list destination-access{
  key "access-id";
  leaf access-id {
    type leafref{
  path "/vn-svc/sites/site/site-network-accesses"
  +"/site-network-access/site-network-access-id";
 }
   description
   "Access id";
  }
  description
  "List for destination access id";
 }
 description
 "List for source access id";
 }
 description
 "Grouping for access";
}
/* .....................................*/

container vn-svc{
 uses vn-services-grouping;
 uses sites-grouping;
 description
 "Container for vn service";
}

rpc vn-compute{
 description
 "RPC for VN compute";
 input {
  list vn-member-list {
   key "vn-member-id";
   leaf vn-member-id{
    type leafref{
  path "/vn-svc/vn-services/vn-service/vn-id";
 }
 description
 "VN member identifier";
   }
   uses src-grouping;
   uses dst-grouping;
   uses constraint-grouping;
   uses objective-function-group;
   uses metric-grouping;
   description
   "List for vn member";
  }

 }
 output{
  list vn-member-list {
   key "vn-member-id";
   leaf vn-member-id{
    type uint32;
 description
 "VN member identifier";
   }
   uses src-grouping;
   uses dst-grouping;
   uses metric-grouping;
   uses path-grouping;
   description
   "List for vn member";
  }
 }
}

rpc vn-stitch{
 description
 "RPC for VN compute";
 input {
  list vn-list {
   key "vn-id";
   leaf vn-id{
    type leafref{
  path "/vn-svc/vn-services/vn-service/vn-id";
 }
 description
 "VN identifier";
   }
   uses access-grouping;
   uses objective-function-group;
   uses metric-grouping;
   description
   "List for vn";
  }

 }
 output{
  list vn-access-list {
   key "index";
   leaf index{
    type uint32;
 description
 "Index for VN access";
   }
   leaf source-access {
    type leafref{
  path "/vn-svc/sites/site/site-network-accesses"
  +"/site-network-access/site-network-access-id";
 }
 description
 "Source Access ID";
   }
   leaf destination-access {
    type leafref{
  path "/vn-svc/sites/site/site-network-accesses"
  +"/site-network-access/site-network-access-id";
 }
 description
 "Destination Access ID";
   }
   list multi-domain-network-access-list {
    key "domain-id network-access-id";
    leaf domain-id {
    type string;
    description
    "Domain ID";
 }
 leaf network-access-id {
  type leafref{
  path "/vn-svc/sites/site/site-network-accesses"
  +"/site-network-access/site-network-access-id";
  }
   description
  "Network access ID";
 }
   description
   "List for multiple domain network access";
   }
   description
   "List for vn access";
  }
 }
}
}
