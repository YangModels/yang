module ietf-te-topology-packet-state {
  yang-version 1;
  namespace
    "urn:ietf:params:xml:ns:yang:ietf-te-topology-packet-state";

  prefix "tet-pkt-s";

  import ietf-te-topology-packet {
    prefix "tet-pkt";
  }

  import ietf-network-state {
    prefix "nd-s";
  }

  import ietf-network-topology-state {
    prefix "lnk-s";
  }

  import ietf-te-topology-state {
    prefix "tet-s";
  }

  import ietf-te-types {
    prefix "te-types";
  }

  organization
    "Traffic Engineering Architecture and Signaling (TEAS)
     Working Group";

  contact
    "WG Web:   <http://tools.ietf.org/wg/teas/>
     WG List:  <mailto:teas@ietf.org>

     WG Chair: Lou Berger
               <mailto:lberger@labn.net>
     WG Chair: Vishnu Pavan Beeram
               <mailto:vbeeram@juniper.net>

     Editors:  Xufeng Liu
               <mailto:Xufeng_Liu@jabil.com>

               Igor Bryskin
               <mailto:Igor.Bryskin@huawei.com>

               Vishnu Pavan Beeram
               <mailto:vbeeram@juniper.net>

               Tarek Saad
               <mailto:tsaad@cisco.com>

               Himanshu Shah
               <mailto:hshah@ciena.com>

               Oscar Gonzalez De Dios
               <mailto:oscar.gonzalezdedios@telefonica.com>";

  description "TE topology model";

  revision 2017-07-03 {
    description "Initial revision";
    reference "TBD";
  }

  /*
   * Augmentations
   */
  /* Augmentations to connectivity-matrix */
  augment "/nd-s:networks/nd-s:network/nd-s:node/tet-s:te/"
    + "tet-s:te-node-attributes/tet-s:connectivity-matrices" {
    description
      "Parameters for PSC TE topology.";
    uses te-types:performance-metric-container {
      if-feature tet-pkt:te-performance-metric;
    }
  }

  augment "/nd-s:networks/nd-s:network/nd-s:node/tet-s:te/"
        + "tet-s:te-node-attributes/tet-s:connectivity-matrices/"
        + "tet-s:connectivity-matrix" {
    description
      "Parameters for PSC TE topology.";
    uses te-types:performance-metric-container {
      if-feature tet-pkt:te-performance-metric;
    }
  }

  augment "/nd-s:networks/nd-s:network/nd-s:node/tet-s:te/"
        + "tet-s:information-source-entry/"
        + "tet-s:connectivity-matrices" {
    description
      "Parameters for PSC TE topology.";
    uses te-types:performance-metric-container {
      if-feature tet-pkt:te-performance-metric;
    }
  }

  augment "/nd-s:networks/nd-s:network/nd-s:node/tet-s:te/"
        + "tet-s:information-source-entry/"
        + "tet-s:connectivity-matrices/"
        + "tet-s:connectivity-matrix" {
    description
      "Parameters for PSC TE topology.";
    uses te-types:performance-metric-container {
      if-feature tet-pkt:te-performance-metric;
    }
  }

  /* Augmentations to tunnel-termination-point */
  augment "/nd-s:networks/nd-s:network/nd-s:node/tet-s:te/"
        + "tet-s:tunnel-termination-point/"
        + "tet-s:local-link-connectivities" {
    description
      "Parameters for PSC TE topology.";
    uses te-types:performance-metric-container {
      if-feature tet-pkt:te-performance-metric;
    }
  }

  augment "/nd-s:networks/nd-s:network/nd-s:node/tet-s:te/"
        + "tet-s:tunnel-termination-point/"
        + "tet-s:local-link-connectivities/"
        + "tet-s:local-link-connectivity" {
    description
      "Parameters for PSC TE topology.";
    uses te-types:performance-metric-container {
      if-feature tet-pkt:te-performance-metric;
    }
  }

  /* Augmentations to te-link-attributes */
  augment "/nd-s:networks/tet-s:te/tet-s:templates/"
        + "tet-s:link-template/tet-s:te-link-attributes" {
    when "tet-s:interface-switching-capability "
      + "[tet-s:switching-capability = 'switching-psc1']" {
      description "Valid only for PSC";
    }
    description
      "Parameters for PSC TE topology.";
    uses te-types:performance-metric-container {
      if-feature tet-pkt:te-performance-metric;
    }
  }

  augment "/nd-s:networks/nd-s:network/lnk-s:link/tet-s:te/"
        + "tet-s:te-link-attributes" {
    when "tet-s:interface-switching-capability "
      + "[tet-s:switching-capability = 'switching-psc1']" {
      description "Valid only for PSC";
    }
    description
      "Parameters for PSC TE topology.";
    uses te-types:performance-metric-container {
      if-feature tet-pkt:te-performance-metric;
    }
  }

  augment "/nd-s:networks/nd-s:network/lnk-s:link/tet-s:te/"
        + "tet-s:information-source-entry" {
    when "tet-s:interface-switching-capability "
      + "[tet-s:switching-capability = 'switching-psc1']" {
      description "Valid only for PSC";
    }
    description
      "Parameters for PSC TE topology.";
    uses te-types:performance-metric-container {
      if-feature tet-pkt:te-performance-metric;
    }
  }

  /* Augmentations to interface-switching-capability */
  augment "/nd-s:networks/tet-s:te/tet-s:templates/"
        + "tet-s:link-template/tet-s:te-link-attributes/"
        + "tet-s:interface-switching-capability" {
    when "tet-s:switching-capability = 'switching-psc1' " {
      description "Valid only for PSC";
    }
    description
      "Parameters for PSC TE topology.";
    uses tet-pkt:packet-switch-capable-container;
  }

  augment "/nd-s:networks/nd-s:network/lnk-s:link/tet-s:te/"
        + "tet-s:te-link-attributes/"
        + "tet-s:interface-switching-capability" {
    when "tet-s:switching-capability = 'switching-psc1' " {
      description "Valid only for PSC";
    }
    description
      "Parameters for PSC TE topology.";
    uses tet-pkt:packet-switch-capable-container;
  }

  augment "/nd-s:networks/nd-s:network/lnk-s:link/tet-s:te/"
        + "tet-s:information-source-entry/"
        + "tet-s:interface-switching-capability" {
    when "tet-s:switching-capability = 'switching-psc1' " {
      description "Valid only for PSC";
    }
    description
      "Parameters for PSC TE topology.";
    uses tet-pkt:packet-switch-capable-container;
  }
}
