module ietf-voucher-security-profile {
  yang-version 1.1;

  namespace
    "urn:ietf:params:xml:ns:yang:ietf-voucher-security-profile";
  prefix "security-profile";

  import ietf-restconf {
    prefix rc;
    description
      "This import statement is only present to access
       the yang-data extension defined in RFC 8040.";
    reference "RFC 8040: RESTCONF Protocol";
  }

  import ietf-voucher {
    prefix "iv";
  }

  organization
   "IETF ANIMA Working Group";

  contact
   "WG Web:   <http://tools.ietf.org/wg/anima/>
    WG List:  <mailto:anima@ietf.org>
    Author:   Srihari Raghavan
              <mailto:srihari@cisco.com>";

  description
  "This module extends the RFC8366 voucher format to provide
   a mechanism by which the authority can configure the security
   posture of the device.

   The key words 'MUST', 'MUST NOT', 'REQUIRED', 'SHALL',
   'SHALL NOT', 'SHOULD', 'SHOULD NOT', 'RECOMMENDED', 'MAY',
   and 'OPTIONAL' in the module text are to be interpreted as
   described in BCP 14 RFC 2119, and RFC8174.";

    revision "2024-05-26" {
      description
        "Updates to security profile aspects";
      reference
        "RFC XXXX: Voucher extensions for security profile";
    }

    revision "2023-11-27" {
      description
        "Updates to security profile aspects";
      reference
        "RFC XXXX: Voucher extensions for security profile";
    }

    revision "2023-05-30" {
      description
        "Initial version";
      reference
        "RFC XXXX: Voucher extensions for security profile";
    }

  feature security-profile-ietf
  {
    description
      "This feature indicates that the IETF version of the security profile
       feature is supported";
    reference "RFC XXXX: Voucher extensions for security profile";
  }

  feature security-profile-oem
  {
    description
      "This feature indicates that the oem version of the security profile
       feature is supported.  The OEM list is expected to be based on
       https://www.iana.org/assignments/enterprise-numbers/ (PENs).";
    reference "RFC XXXX: Voucher extensions for security profile";
  }

  rc:yang-data voucher-security-profile-artifact {
    // YANG data template for a voucher.
    uses voucher-security-profile-grouping;
  }

  typedef bitmask64 {
    type uint64;
      description
        "The bitmask64 type represents a non-negative integer
         that represents a bit mask type field with each bit
         set (or unset) representing a different intent along
         with a range of bits/values representing a group.  Using
         an appropriate mask, the individual bits can be set/reset.
         In addition, a range of bits can also be manipulated using
         an appropriate mask.

         The 'type bits' and 'position' yang based bit fields do
         not lend itself easily to range based comparisons and
         hence the need for a customized type definition.

         The bitmask64 type can be used for configuration
         schema nodes.  A default statement can be used in
         combination with the type bitmask64.";

       reference
        "RFC 2578: Structure of Management Information Version 2
                   (SMIv2)";
  }

  // Grouping for security parameters forming the security profile
  //
  // These are separated into two-groups: standardized and OEM.
  //
  // The security-parameters-standard are subject to standards definition
  // for inter-operability while the OEM range is expected to be
  // implementation dependent.
  //
  //
  // The specific bits are expected to be defined
  // following discussions with WG members and some examples
  // could be FIPS mode handling, SELinux handling,
  // Linux IMA handling etc., which could decide the
  // overall security posture of a device.";
  //
  //
  grouping security-parameters-group {
    leaf security-params-value {
      type bitmask64;
      description
        "Bit map for the different underlying security
         parameters. This is only valid if
         security-profile-enable-flag is true.

         Range: - 0x1, 0x2, 0x4..0x8000..0x10000..
        ";
    }

    leaf security-params-mask {
      type bitmask64;
      description
        "This represents the mask for the value above.
         If this mask is on for a bit, the corresponding
         value of the bit will be treated accordingly.  If
         the mask is off, the value of the bit could be
         treated as a don't care or default value";
    }
    description "The underlying security profile parameters.";
  }
