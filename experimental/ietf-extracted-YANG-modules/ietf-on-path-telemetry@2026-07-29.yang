module ietf-on-path-telemetry {
  yang-version 1.1;
  namespace "urn:ietf:params:xml:ns:yang:ietf-on-path-telemetry";
  prefix "on-path-telemetry";

     import ietf-access-control-list {
       prefix acl;
       reference
         "RFC 8519: YANG Data Model for Network Access Control
          Lists (ACLs)";
     }

     import ietf-interfaces {
       prefix if;
       reference
         "RFC 8343: A YANG Data Model for Interface Management";
     }

     import ietf-yang-types {
       prefix yang;
       reference
         "Section 3 of RFC 9911";
     }

     import ietf-lime-time-types {
       prefix lime;
       reference
         "RFC 8532: Generic YANG Data Model for the Management of
          Operations, Administration, and Maintenance (OAM) Protocols
          That Use Connectionless Communications";
     }

     import ietf-ioam {
       prefix ioam;
       reference
         "RFC 9617";
     }

     import ietf-altmark {
       prefix altmark;
       reference
         "draft-ietf-ippm-alt-mark-yang";
     }

  organization
    "IETF IPPM (IP Performance Metrics) Working Group";

  contact
    "WG Web: <https://datatracker.ietf.org/wg/ippm>
     WG List: <ippm@ietf.org>
     Author: giuseppe.fioccola@huawei.com
     Author: zhoutianran@huawei.com
     Author: zhuyq8@chinatelecom.cn
     Author: zhangwq@chinatelecom.cn
     Author: zhukeyi@huawei.com";

  description
    "This YANG module specifies a vendor-independent data
     model for On-Path Telemetry.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2026-07-29 {
    description "First revision.";
    reference "RFC XXXX: A YANG Data Model for On-path Telemetry";
  }

 /*
  * FEATURES
  */

  feature altmark {
    description
      "This feature indicates that the Alternate-Marking Method is
       supported.";
    reference
      "RFC 9341: Alternate-Marking Method;
       RFC 9342: Clustered Alternate-Marking Method
       RFC 9343: IPv6 Application of the Alternate-Marking Method
       RFC 9714: Application of the Alternate Marking Method to the
       MPLS Label Stack
       RFC 9947: Application of the Alternate Marking Method to the
       Segment Routing Header";
  }

  feature pathdelay {
    description
      "This feature indicates that the Path Delay is
       supported.";
    reference
      "RFC 9951: Export of Delay Performance Metrics in IPFIX";
  }

  feature ioam {
    description
      "This feature indicates that the IOAM Method is supported.";
    reference
      "RFC 9197: Data Fields for In-situ OAM";
  }

  feature incremental-trace {
    description
      "This feature indicates that the incremental tracing option is
       supported.";
    reference "RFC 9197: Data Fields for In-situ OAM";
  }

  feature preallocated-trace {
    description
      "This feature indicates that the preallocated tracing option is
       supported.";
    reference "RFC 9197: Data Fields for In-situ OAM";
  }

  feature direct-export {
    description
      "This feature indicates that the direct export option is
       supported.";
    reference "RFC 9326: In-situ OAM Direct Exporting";
  }

  feature proof-of-transit {
    description
      "This feature indicates that the proof of transit option is
       supported";
    reference "RFC 9197: Data Fields for In-situ OAM";
  }

  feature edge-to-edge {
    description
      "This feature indicates that the edge-to-edge option is
       supported.";
    reference "RFC 9197: Data Fields for In-situ OAM";
  }

 /*
  * IDENTITIES
  */

  identity filter {
    description
      "Base identity to represent a filter. A filter is used to
       specify the flow to which the On-Path Telemetry method is
       applied.";
  }

  identity acl-filter {
    base filter;
    description
      "Apply ACL rules to specify the flow.";
  }

  identity protocol {
    description
      "Base identity to represent the protocol. It's used to
       indicate the protocol for the application of the On-Path
       Telemetry method.";
  }

  identity ipv6 {
    base protocol;
    description
      "The On-Path Telemetry method is applied to IPv6 protocol.";
    reference
      "RFC 9343: IPv6 Application of the Alternate-Marking Method,
       RFC 9486: In-situ OAM IPv6 Options";
  }

  identity srh  {
    base protocol;
    description
      "The On-Path Telemetry method is applied to SRH.";
    reference
      "RFC 9947: Application of the Alternate Marking Method to the
       Segment Routing Header";
  }

  identity mpls  {
    base protocol;
    description
      "The On-Path Telemetry method is applied to MPLS.";
    reference
      "RFC 9714: Application of the Alternate Marking Method
       to the MPLS Label Stack";
  }

  identity nsh  {
    base protocol;
    description
      "The described IOAM data is embedded in NSH.";
    reference
      "RFC 9452: Network Service Header (NSH)
       Encapsulation for In-situ OAM (IOAM) Data";
   }

 /*
  * TYPE DEFINITIONS
  */

  typedef telemetry-filter-type {
    type identityref {
      base filter;
    }
    description
      "It specifies a known type of filter.";
  }

  typedef telemetry-protocol-type {
    type identityref {
      base protocol;
    }
    description
      "It specifies a known type of carrier protocol for the On-path
       Telemetry data.";
  }

  typedef flow-direction {
    type enumeration {
      enum "ingress" {
        value 1;
        description
          "Ingress of a flow.";
      }
      enum "transit" {
        value 2;
        description
          "Transit of a flow.";
      }
      enum "egress" {
        value 3;
        description
          "Egress of a flow.";
      }
    }
    description
      "Flow direction.";
  }

  typedef ioam-trace-data {
    type identityref {
      base ioam:trace-type;
    }
    description
      "It specifies the trace data.";
  }

  typedef ioam-pot-data {
    type identityref {
      base ioam:pot-type;
    }
    description
      "It specifies the pot data.";
  }

  typedef ioam-e2e-data {
    type identityref {
      base ioam:e2e-type;
    }
    description
      "It specifies the edge-to-edge data.";
  }

 /*
  * GROUP DEFINITIONS
  */

  grouping telemetry-filter {
    description
      "A grouping for On-path Telemetry filter definition";

    leaf filter-type {
      type telemetry-filter-type;
      description "filter type";
    }

    leaf ace-name {
      when "derived-from-or-self(../filter-type,
      'on-path-telemetry:acl-filter')";
      type leafref {
        path "/acl:acls/acl:acl/acl:aces/acl:ace/acl:name";
      }
      description
        "The Access Control Entry name is used to
         refer to an ACL specification.";
    }
  }

  grouping telemetry-dir-prot {
    description
      "A grouping for On-path Telemetry information.";

    leaf direction {
      type flow-direction;
      description
        "Specify the flow direction.";
    }

    leaf protocol-type {
      type telemetry-protocol-type;
      description
        "This item is used to indicate the carrier protocol where
         the On-path Telemetry is applied.";
    }
  }

  grouping altmark-telemetry {
    description
      "A grouping for On-path Telemetry profile.";

    leaf flow-mon-id {
      type altmark:flow-id;
      description
        "It specifies the 20-bit FlowMonID, as defined in RFC 9343
         and RFC 9714. Note that it corresponds to the
         altmarkFlowMonID parameter defined in
         draft-ietf-opsawg-ipfix-alt-mark.";
    }

    leaf measurement-period-number {
      type uint64;
      description
        "It specifies the On-path Telemetry period number.";
    }
  }

  grouping loss-counters {
    description
      "The set of counters for RFC 9341 and RFC 9342 loss
       calculation.";

    leaf loss-flag {
      type bits {
        bit l-flag {
          position 0;
          description
            "It indicates the loss-flag value";
        }
      }
      description
        "The loss-flag value is defined in RFC 9343 and RFC 9714.
         Note that it corresponds to the altmarkLossFlag parameter
         defined in draft-ietf-opsawg-ipfix-alt-mark.";
    }

    leaf in-traffic-pkts {
      type yang:counter64;
      description
        "Total inbound packets of the period according to RFC 9341
         and RFC 9342";
    }

    leaf out-traffic-pkts {
      type yang:counter64;
      description
        "Total outbound packets of the period according to RFC 9341
         and RFC 9342";
    }

    leaf in-traffic-bytes {
      type uint64;
      description
        "Total inbound bytes of the period according to RFC 9341
         and RFC 9342";
    }

    leaf out-traffic-bytes {
      type uint64;
      description
        "Total outbound bytes of the period according to RFC 9341
         and RFC 9342";
    }
  }

  grouping delay-timestamps {
    description
      "It indicates the set of timestamps for RFC 9341 and RFC 9342
       delay calculation.";

    leaf delay-flag {
      type bits {
        bit d-flag {
          position 0;
          description
            "It indicates the delay-flag value.";
        }
      }
      description
        "The delay-flag value is defined in RFC 9343 and RFC 9714.
         Note that it corresponds to the altmarkDelayFlag parameter
         defined in draft-ietf-opsawg-ipfix-alt-mark.";
    }

    container in-pkts-timestamps {
      description
        "The list of timestamps of the period according to RFC 9341
         and RFC 9342";

      leaf in-pkt-timestamp {
        type yang:date-and-time;
        description
          "To specify the timestamp of the delay packet for delay
           measurements";
      }

      leaf in-pkt-seq-num {
        type yang:counter32;
        description
          "To specify the sequence number of the delay packet for
           delay measurements";
      }
    }
    container out-pkts-timestamps {
      description
        "The list of timestamps of the period according to RFC 9341
         and RFC 9342";

      leaf out-pkt-timestamp {
        type yang:date-and-time;
        description
          "To specify the timestamp of the delay packet for delay
           measurements";
      }

      leaf out-pkt-seq-num {
        type yang:counter32;
        description
          "To specify the sequence number of the delay packet for
           delay measurements";
      }
    }
  }

  grouping path-delay-metrics {
    description
      "It indicates the path delay measurements.";

    leaf path-delay-mean {
      type uint32;
      description
        "mean path delay as per RFC 9951";
    }
    leaf path-delay-min {
      type uint32;
      description
        "min path delay as per RFC 9951";
    }

    leaf path-delay-max {
      type uint32;
      description
        "max path delay as per RFC 9951";
    }

    leaf path-delay-sum {
      type uint64;
      description
        "sum of the path delay as per RFC 9951";
    }
  }
  grouping ioam-incremental-tracing-data-list {
    description
      "A grouping for incremental tracing data.";

    leaf-list incremental-tracing {
      type ioam-trace-data;
      description
        "This object indicates the incremental tracing data.";
    }
  }

  grouping ioam-preallocated-tracing-data-list {
    description
      "A grouping for the list of pre-allocated tracing data.";

    leaf-list preallocated-tracing {
      type ioam-trace-data;
      description
        "This object indicates the preallocated tracing data.";
    }
  }

  grouping ioam-direct-export-tracing-data-list {
    description
      "A grouping for the list of direct export data.";

    leaf-list direct-export {
      type ioam-trace-data;
      description
        "This object indicates the direct export data.";
    }
  }

  grouping ioam-proof-of-transit-data-list {
    description
      "A grouping for the list of proof of transit data.";

    leaf-list proof-of-transit {
      type ioam-pot-data;
      description
        "This object indicates the proof of transit data.";
    }
  }

  grouping ioam-edge-to-edge-data-list {
    description
      "A grouping for the list of edge-to-edge data.";

    leaf-list edge-to-edge {
      type ioam-e2e-data;
      description
        "This object indicates the edge to edge data.";
    }
  }

 /*
  * DATA NODES
  */

  container on-path-telemetry-data {
    config false;
    description "On-path Telemetry top level container";

    container on-path-telemetry-info {
      config false;
      description
        "Describes information such as units or timestamp format
        that assists monitoring systems in the interpretation of the
        on-path-telemetry data.";

      leaf timestamp-type {
        type identityref {
          base lime:timestamp-type;
        }
        description
          "Type of timestamp, such as Truncated PTP or NTP.";
      }
    }

    list available-interface {
      key "if-name";
      description
        "It contains the list of the interfaces activated for
         Telemetry";
      leaf if-name {
        type if:interface-ref;
        description "This is a reference to the Interface name.";
      }

      container profiles {
        description
          "Contains On-path Telemetry profiles.";

        list altmark-profile {
          if-feature altmark;
          key "altmark-profile-name";
          description
            "It describes the list of the AltMark profiles configured
             on the node";
          leaf altmark-profile-name {
            type string{
              length "1..300";
            }
          description
            "Unique identifier for each AltMark profile.";
          }

          container filter {
            uses telemetry-filter;
            description
              "The filter which is used to indicate the flow where
               the On-path Telemetry is applied.";
          }

          uses telemetry-dir-prot;

          uses altmark-telemetry;

          container altmark-loss-measurement {
            description
              "It reports the loss measurement data.";

            uses loss-counters;
          }

          container altmark-delay-measurement {
            description
              "It reports the delay measurement data.";

            uses delay-timestamps;
          }

        }

        list path-delay-profile {
          if-feature pathdelay;
          key "path-delay-profile-name";
          description
            "It describes the list of the path delay profiles
             configured on the node";
          leaf path-delay-profile-name {
            type string {
              length "1..300";
            }
            description
              "Unique identifier for each path delay profile.";
          }

          container filter {
            uses telemetry-filter;
            description
              "The filter which is used to indicate the flow where
               the On-path Telemetry is applied.";
          }

          uses telemetry-dir-prot;

          uses path-delay-metrics;
        }

        list ioam-profile {
          if-feature ioam;
          key "ioam-profile-name";
          description
            "It describes the list of the IOAM profiles configured
             on the node";
          leaf ioam-profile-name {
            type string{
              length "1..300";
            }
          description
            "Unique identifier for each IOAM profile.";
          }

          container filter {
            uses telemetry-filter;
            description
              "The filter which is used to indicate the flow where
               the On-path Telemetry is applied.";
          }

          uses telemetry-dir-prot;

          container ioam-incremental-tracing {
            if-feature incremental-trace;
              presence "Enables incremental tracing option.";
            description
              "It reports the incremental tracing option data.";

            uses ioam-incremental-tracing-data-list;
          }

          container ioam-preallocated-tracing {
            if-feature preallocated-trace;
              presence "Enables preallocated tracing option.";
            description
              "It reports the preallocated tracing option data.";

            uses ioam-preallocated-tracing-data-list;
          }

          container ioam-direct-export {
            if-feature direct-export;
              presence "Enables direct-export option.";
            description
              "It reports the direct-export option data";

            uses ioam-direct-export-tracing-data-list;
          }

          container ioam-proof-of-transit {
            if-feature proof-of-transit;
              presence "Enables Proof of Transit option.";
            description
              "It reports the PoT option data.";

            uses ioam-proof-of-transit-data-list;
          }

          container ioam-edge-to-edge {
            if-feature edge-to-edge;
              presence "Enables edge-to-edge option.";
            description
              "It reports the edge-to-edge option data.";

            uses ioam-edge-to-edge-data-list;
          }
        }
      }
    }
  }
}
