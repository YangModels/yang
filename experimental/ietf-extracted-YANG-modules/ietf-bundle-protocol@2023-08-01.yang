module ietf-bundle-protocol {
  yang-version 1.1;
  namespace "urn:ietf:params:xml:ns:yang:ietf-bundle-protocol";
  prefix bundle;

  import ietf-bundle-protocol-types {
    prefix bundle-types;
  }

  organization
    "IETF DTN: Delay-Tolerant Networking Working Group";
  contact
    "WG Web:   <http://datatracker.ietf.org/wg/dtn>
     WG List:  <mailto:dtn@ietf.org>

     Author:   Marc Blanchet
               <mailto:marc.blanchet@viagenie.ca>
     Author:    Yingzhen Qu
               <mailto:yingzhen.ietf@gmail.com>";
  description
    "This module contains Bundle Protocol (RFC5050, RFC9171) types.

      The key words 'MUST', 'MUST NOT', 'REQUIRED', 'SHALL', 'SHALL
      NOT', 'SHOULD', 'SHOULD NOT', 'RECOMMENDED', 'NOT RECOMMENDED',
      'MAY', and 'OPTIONAL' in this document are to be interpreted as
      described in BCP 14 (RFC 2119) (RFC 8174) when, and only when,
      they appear in all capitals, as shown here.

      Copyright (c) 2023 IETF Trust and the persons identified as
      authors of the code.  All rights reserved.

      Redistribution and use in source and binary forms, with or
      without modification, is permitted pursuant to, and subject to
      the license terms contained in, the Revised BSD License set
      forth in Section 4.c of the IETF Trust's Legal Provisions
      Relating to IETF Documents
      (https://trustee.ietf.org/license-info).

      This version of this YANG module is part of RFC TBD; see
      the RFC itself for full legal notices.";

  revision 2023-08-01 {
    description
      "Initial revision. date TBD";
    reference
      "RFC 5050 Bundle Protocol Specification
       RFC 9171 Bundle Protocol Version 7
       IANA Bundle Protocol Registry,
       https://www.iana.org/assignments/bundle/bundle.xhtml";
  }

  container node {
    description
      "A bundle protocol node";
    leaf-list version {
      type bundle-types:bundle-protocol-version;
      description
        "The list of bundle protocol versions this node supports";
    }
    leaf endpoint_identifier {
      type bundle-types:bundle-endpoint-identifier;
      description
        "The endpoint identifier of this node";
    }
    leaf bundle-lifetime {
      type uint32;
      units "seconds";
      description
        "The default bundle lifetime";
    }
    leaf maximum-bundle-size {
      type uint32;
      units "octets";
      description
        "The maximum bundle size in bytes";
    }
    leaf send-status-reports {
      type boolean;
      default "false";
      description
        "Should the node send status reports";
    }
    leaf forwarding {
      type boolean;
      default "false";
      description
        "Controls forwarding of bundles received by,
         but not addressed to, this node.";
    }
    container neighbors {
      list neighbor {
        key "endpoint-identifier";
        description
          "A bundle protocol neighbor of this node. May not be active";
        leaf activate {
          type boolean;
          default "false";
          description
            "The configuration status of the neighbor";
        }
        leaf active {
          type boolean;
          config false;
          description
            "From the perspective of the node, this neighbor is live and active";
        }
        leaf endpoint-identifier {
          type bundle-types:bundle-endpoint-identifier;
          description
            "Endpoint identifier of the neighbor";
        }
        container convergence-layer-adapters {
          list convergence-layer-adapter {
            key "id";
            uses bundle-types:convergence-layer-adapter;
            description
              "A convergence layer adapter of this neighbor";
          }
          description
            "The convergence layer adapters of this neighbor";
        }
      }
      description
        "List of bundle protocol neighbors of this node";
    }
    /* TBD: from TVR work
      leaf-list forwarding-policies {
      }
     */
    leaf bundle-queue-size {
      type uint32;
      units "octets";
      description
        "The bundle queue size in bytes";
    }
    container convergence-layer-adapters {
      list convergence-layer-adapter {
        key "id";
        uses bundle-types:convergence-layer-adapter;
        description
          "A configured convergence layer adapter on the node";
      }
      description
        "The list of convergence layer adapters currently configured
         on the node";
    }
    container store {
      description
        "Storage for bundles that are waiting in storage because the
         destination is not reachable yet, as opposed to temporary
         bundles in memory about to be forwarded";
      leaf maximum-size {
        type uint32;
        description
          "maximum number of bytes of bundles storage";
      }
      leaf current-size {
        type uint32;
        config false;
        description
          "current size (in bytes) of used bundles storage";
      }
      leaf maximum-bundles {
        type uint32;
        description
          "maximum number of bundles in storage";
      }
      leaf bundles-number {
        type uint32;
        config false;
        description
          "current number of bundles in storage";
      }
      list bundles {
        key "id";
        uses bundle-types:bundle;
        description
          "Stored bundles awaiting forwarding";
      }
    }
  }
}
