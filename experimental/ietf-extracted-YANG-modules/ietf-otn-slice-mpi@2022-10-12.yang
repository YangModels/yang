module ietf-otn-slice-mpi {
  yang-version 1.1;
  namespace "urn:ietf:params:xml:ns:yang:ietf-otn-slice-mpi";
  prefix "otns-mpi";

  import ietf-network {
    prefix "nw";
    reference
      "RFC 8345: A YANG Data Model for Network Topologies";
  }

  import ietf-network-topology {
    prefix "nt";
    reference
      "RFC 8345: A YANG Data Model for Network Topologies";
  }

  import ietf-te-topology {
    prefix "tet";
    reference
      "RFC8795: YANG Data Model for Traffic Engineering
      (TE) Topologies";
  }

  import ietf-otn-topology {
    prefix "otnt";
    reference
      "I-D.ietf-ccamp-otn-topo-yang: A YANG Data Model
       for Optical Transport Network Topology";
  }

  import ietf-layer1-types {
    prefix "l1-types";
    reference
      "I-D.ietf-ccamp-layer1-types: A YANG Data Model
       for Layer 1 Types";
  }

  organization
    "IETF CCAMP Working Group";
  contact
    "WG Web: <http://tools.ietf.org/wg/ccamp/>
     WG List: <mailto:ccamp@ietf.org>

     Editor: Haomian Zheng
             <mailto:zhenghaomian@huawei.com>

     Editor: Italo Busi
             <mailto:italo.busi@huawei.com>

     Editor: Aihua Guo
             <mailto:aihuaguo.ietf@gmail.com>

     Editor: Sergio Belotti
             <mailto:sergio.belotti@nokia.com>";

  description
    "This module defines a YANG data model for network slice
     realization in Optical Transport Networks (OTN).

     The model fully conforms to the Network Management Datastore
     Architecture (NMDA).

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see the
     RFC itself for full legal notices.";

  revision "2022-10-12" {
    description
      "Latest revision of MPI YANG model for OTN slicing.";
    reference
      "draft-ietf-ccamp-yang-otn-slicing-03: Framework and Data
       Model for OTN Network Slicing";
  }

  /*
   * Groupings
   */

  grouping otn-link-slice-profile {
    description
      "Profile of an OTN link slice.";
    choice otn-slice-granularity {
      default "link";
      description
        "Link slice granularity.";
      case link {
        leaf slice-id {
          type uint32;
           description
             "Slice identifier";
        }
      }
      case link-resource {
        list slices {
          key slice-id;
          description
            "List of slices.";
          leaf slice-id {
            type uint32;
            description
              "Slice identifier";
          }
          choice technology {
            description
              "Data plane technology types.";
            case otn {
              choice slice-bandwidth {
                description
                  "Bandwidth specification for OTN slices.";
                case containers {
                  uses l1-types:otn-link-bandwidth;
                }
                case time-slots {
                  leaf otn-ts-num {
                    type uint32;
                    description
                      "Number of OTN tributary slots allocated
                       for the slice.";
                  }
                }
              }
            }
          }
          leaf sliced-link-ref {
            type leafref {
              path "../../../../../nt:link/nt:link-id";
            }
            config false;
            description
              "Relative reference to virtual links generated from
               this TE link.";
          }
        }
      }
    }
  }

  /*
   * Augments
   */
  augment "/nw:networks/nw:network/nt:link/tet:te/"
        + "tet:te-link-attributes" {
    when "../../../nw:network-types/tet:te-topology/"
       + "otnt:otn-topology" {
      description
        "Augmentation parameters apply only for networks with
         OTN topology type.";
    }
    description
      "Augment OTN TE link attributes with slicing profile.";
    uses otn-link-slice-profile;
  }
}
