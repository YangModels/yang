module ietf-traffic-policy {
  yang-version 1.1;
  namespace "urn:ietf:params:xml:ns:yang:ietf-traffic-policy";
  prefix policy;

  import ietf-interfaces {
    prefix if;
  }
  import iana-qos-types {
    prefix qos-types;
    reference
      "RFC XXXX: YANG Data Models for Quality of Service (QoS).";
  }

  organization
    "IETF Routing Area Working Group";

  contact
    "WG Web:   <https://datatracker.ietf.org/wg/rtgwg/>
     WG List:  <mailto:rtgwg@ietf.org>

     Editor:   Aseem Choudhary
               <mailto:achoudhary@aviatrix.com>
     Editor:   Mahesh Jethanandani
               <mailto:mjethanandani@gmail.com>";

  description
    "This module contains a collection of YANG definitions for
     configuring qos specification implementations.

     Copyright (c) 2021 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision 2022-10-24 {
    description
      "Initial version";
    reference
      "RFC XXXX: YANG Models for Quality of Service (QoS).";
  }

  grouping filters {
    description
      "Filters types in a Classifier entry";
    leaf type {
      type identityref {
        base qos-types:filter-type;
      }
      description
        "This leaf defines type of the filter";
    }
    leaf logical-not {
      type boolean;
      description
        "This is logical-not operator for filter values and/or value
         ranges. When true, it indicates filter looks for absence
         of values and/or value ranges defined by the filter.";
    }
  }
  grouping generic-classifier-attr {
    description
      "
       Classifier generic attributes like name,
       description, operation type
      ";
    leaf name {
      type string;
      description
        "classifier entry name";
    }
    leaf description {
      type string;
      description
        "classifier entry description statement";
    }
    leaf filter-operation {
      type qos-types:match-operation-type;
      description
        "Filters are applicable as match-any or match-all filters";
    }
  }
  grouping inline-attr {
    description
      "attributes of inline classifier in a policy";
    leaf filter-operation {
      type qos-types:match-operation-type;
      description
        "Filters are applicable as match-any or match-all filters";
    }
    list filter{
      key "type logical-not";
      uses filters;
      description
        "Filters configured inline in a policy";
    }
  }

  grouping classifier-action-entry {
    description
      "List of Configuration of classifier & associated actions";
    list action {
      key "type";
      ordered-by user;
      description
        "Configuration of classifier & associated actions";
      leaf type {
        type identityref {
          base qos-types:action-type;
        }
        description
          "This defines action type ";
      }
      choice action-params {
        description
          "Choice of action types";
      }
    }
  }
  container classifiers {
    description
      "list of classifier entry";
    list classifier{
      key "name";
      description
        "each classifier entry contains a list of filters";
      uses generic-classifier-attr;
      list filter {
        key "type logical-not";
        uses filters;
        description
          "Filter entry configuration";
      }
    }
  }
  container policies{
    description
      "list of policy templates";
    list policy{
      key "name type";
      description
        "policy template";

      leaf name {
        type string;
        description
          "policy name";
      }

      leaf type {
        type identityref {
          base qos-types:policy-type;
        }
        description
          "policy type";
      }
      leaf description {
        type string;
        description
          "policy description";
      }

      list classifier{
        key "name";
        ordered-by user;
        description
          "Classifier entry configuration in a policy";
        leaf name {
          type string;
          description
            "classifier entry name";
        }
        container inline {
          presence "This container is present for when the device
                    is configured for inline classification";
          uses inline-attr;
          description
            "Container for when an inline classification
             is desired.";
        }
        uses classifier-action-entry;
      }
    }
  }
  augment "/if:interfaces/if:interface" {
    description
      "Augments Diffserv Target Entry to Interface module";
    list qos-target-policy {
      key "direction type";
      description
        "policy target for inbound or outbound direction";
      leaf direction {
        type identityref {
          base qos-types:direction;
        }
        description
          "Direction of the traffic flow either inbound or outbound";
      }
      leaf type {
        type identityref {
          base qos-types:policy-type;
        }
        description
          "Policy entry type";
      }
      leaf name {
        type string;
        mandatory true;
        description
          "Policy name";
      }
    }
  }
}
