module ietf-supa-ddc {
  namespace "urn:ietf:params:xml:ns:yang:ietf-supa-ddc";
  // replace with IANA namespace when assigned
  prefix ddc;

  // import ietf-supa-vpn,ietf-supa-abstacted-l3vpn,
  // ietf-supa-l2vpn

  organization "IETF";
  contact
     "Editor: Ying Cheng
      chengying10@chinaunicom.cn

      Maxim Klyus
      klyus@NetCracker.com
     ";

  description
     "This YANG module defines a component that describing
      the ddc service model for creating and optimizing
      tenant's DC (data center) services that are deployed
      in multiple data centers.

      Terms and Acronyms
        DDC: Distributed Data Center
        L2VPN: Layer 2 Virtual Private Network
        L3VPN: Layer 3 Virtual Private Network
      ";
  revision 2014-12-25 {
     description
        "Initial revision.";
     reference "RFC4364, RFC7277";
  }

  container ddc-services {
    description
      "To create service for tenant's network that are deployed
      in multiple data centers. The following data are needed:
      name of data centers that the tenant's service are
      deployed in, connected method between data centers for
      the tenant (e.g. L2VPN, l3VPN, Native IP, etc.), name
      of tenant, ID of networks that belong to the tenant";

    list ddc-service {
      key "name";
      description
        "Overall ddc operational data, including the names of
        data center,the connection method between data centers,
        name of service, etc.";

      leaf name {
        type string;
        description
          "Indicates the name of the service";
      }

      leaf tenant-name {
        type string;
        description
          "Indicates the name of the tenant for whom
      the ddc service is being created.";
      }

      leaf-list dc-name {
        type string;
        description
          "List of the names of data center on which
          tenant's service is deployed in.";
      }

      leaf-list interface-name {
        type string;
        description
          "Indicates a set of access interface
          names of the network device that the
          data centers (deployment of tenant's
          service)are connected to.";
      }

      leaf connection-type {
        type enumeration {
          enum L2VPN {
            value 0;
            description "L2VPN";
          }
        enum L3VPN {
            value 1;
            description "L3VPN";
          }
          enum native-ipv4 {
            value 2;
            description "native IPv4";
          }
          enum native-ipv6 {
            value 3;
            description "native IPv6";
          }
        }
        description
          "Indicates the connection  type between the
          Data centers on which tenant service is being
          deployed . The connection type may be VPN
          (L2VPN or L3VPN) or Native IP (IPv4 or IPv6)";
      }

      leaf connection-name {
    type leafref { path "/l2vpn:l2vpn-instance/
      instance-name"; }
        mandatory true;
        description
          "Indicates the name of the connection e.g.,VPN
          instance";
      }

      leaf bandwidth {
        type uint32;
        description
          "Indicates the bandwidth of the network connection
          instance that is created for tenant.";
      }

      leaf latency {
        type uint32;
        description
          "Indicates the latency of the network connection
          instance that is created for tenant.";
      }
    }
  }
