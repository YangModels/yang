module ietf-microwave-radio-link { 

 namespace "urn:ietf:params:xml:ns:yang:ietf-microwave-radio-link"; 

  prefix mrl; 

  import ietf-yang-types { 

    prefix yang; 

  } 

  import ietf-interfaces { 

    prefix if; 

  } 

  import iana-if-type { 

    prefix ianaift; 

  } 

  organization 

    "IETF CCAMP Working Group"; 

  contact 

    "jonas.ahlberg@ericsson.com 

    amy.yemin@huawei.com 

    Xi.Li@neclab.eu 

    cjbc@it.uc3m.es 

    "; 

  description 

   "This is a module for the entities in a generic microwave 
   system."; 

  revision 2016-10-29 { 

    description 

      "Draft revision."; 

    reference ""; 
  }

    /* 

     * Features 

     */ 

    feature xpic { 

     description 

       "Indicates that the device supports XPIC."; 

    } 

    feature mimo { 

     description 

       "Indicates that the device supports MIMO."; 
    } 

    /* 

    * Interface identities 

    */ 

    identity radio-link-terminal { 

     base ianaift:iana-interface-type; 

     description 

       "Interface identity for a radio link terminal."; 

    } 

    identity carrier-termination { 

     base ianaift:iana-interface-type; 

     description 

       "Interface identity for a carrier termination."; 

    } 

    /* 

     * Coding and modulation identities 

     */ 

      identity coding-modulation { 

        description 

          "The coding and modulation schemes."; 

      } 

    /* 

    * Typedefs 

    */ 

    typedef power { 

     type decimal64 { 

       fraction-digits 1; 

    } 

     description 

       "Type used for power values, selected and measured."; 

    } 

    /* 

    * Radio Link Terminal (RLT) - Configuration data nodes 

    * to be filled 

    */ 

    /* 

    * Carrier Termination (CT) - Configuration data nodes 

    */ 

    augment "/if:interfaces/if:interface" { 

    when "if:type = 'mrl:carrier-termination'"; 

    description 

    "Addition of data nodes for carrier termination to the 

    standard Interface data model, for interfaces of the type 

    'carrier-termination'."; 

    leaf carrier-id { 

     type string; 

       default "A"; 

     description 

       "ID of the carrier. (e.g. A, B, C or D) 

       Used in multi carrier configuration, such as XPIC & MIMO  

       configurations to check that the carrier termination is  

       connected to the correct far-end carrier termination. 

       Should be the same carrier ID on both sides of the hop. 

       Defaulted when single carrier configuration."; 

    } 

    leaf tx-enabled { 

     type boolean; 
     description 

       "The adminstrative status of the transmitter. 

       True (enable) or False(disable) or the transmitter. 

       Only applicable when the interface is enabled 

       (interface:enabled = true) otherwise it's always 

       disabled."; 

    } 

    leaf tx-frequency { 

     type uint32; 

     units "kHz"; 

     default "0"; 

     description 

       "Selected transmitter frequency."; 

    } 

    leaf rx-frequency { 

     type uint32; 

     units "kHz"; 

     default "0"; 

     description 

       "Selected receiver frequency. 

       Only writeable when duplex-config=disabled and 

       duplex-type=variable."; 

    } 

    leaf duplex-distance { 

     type uint32; 

     units "kHz"; 

     default "0"; 

     description 

       "Distance between Tx & Rx frequencies. 

       Only writeable when duplex-config=true and 

       duplex-type=variable."; 

    } 

    leaf duplex-config { 

     type boolean; 

     default "false"; 

     description 

       "Enable (true) or disable (false) configuration of 

       rx-Frequency using a defined duplex distance."; 

    } 

    leaf polarization { 

     type enumeration { 

       enum "horizontal" { 

         description "Horizontal polarization."; 

       } 

       enum "vertical" { 

         description "Vertical polarization."; 

       } 

       enum "not-specified" { 

         description "Polarization not specified."; 

       } 

     } 

     default "not-specified"; 

     description 

       "Polarization - A textual description for info only."; 

     } 

     leaf power-mode { 

      type enumeration { 

        enum rtpc { 

          description "Remote Transmit Power Control (RTPC)."; 

        } 

        enum atpc { 

          description "Automatic Transmit Power Control (ATPC)."; 

        } 

      } 

      description 

        "A choice of Remote Transmit Power Control (RTPC) 

        or Automatic Transmit Power Control (ATPC)."; 

      } 

     leaf selected-output-power { 

      when "../power-mode = 'rtpc'"; 

      type power; 

      units "dBm"; 

      description 

        "Selected output power in RTPC mode."; 

     } 

     leaf coding-modulation-mode { 

      type enumeration { 

        enum fixed { 

          description "Fixed coding/modulation."; 

        } 

        enum adaptive { 

          description "Adaptive coding/modulation."; 

        } 

      } 

      description 

        "A selection of fixed or 

        adaptive coding/modulation mode."; 

     } 

     leaf selected-cm { 

      when "../coding-modulation-mode = 'fixed'"; 

      type identityref { 

        base coding-modulation; 

      } 

      description 

        "Selected fixed coding/modulation."; 

     } 

     leaf selected-min-acm { 

      when "../coding-modulation-mode = 'adaptive'"; 

      type identityref { 

        base coding-modulation; 

      } 

      description 

        "Selected minimum coding/modulation. 

        Adaptive coding/modulation shall not go 

        below this value."; 

     } 

     leaf selected-max-acm { 

      when "../coding-modulation-mode = 'adaptive'"; 

      type identityref { 

        base coding-modulation; 

      } 

      description 

        "Selected maximum coding/modulation. 

        Adaptive coding/modulation shall not go 

        above this value."; 

     } 

     leaf if-loop { 

      type boolean; 

      default "false"; 

      description 

     "Enable (true) or disable (false) the intermediate  

     frequency (IF) loop, which loops the signal back to the  

     client side(not the radio side)."; 

     } 

     /* 

     * Radio Link Termination - state data nodes 
     * to be filled 

     */ 

     /* 

     * Carrier Termination - state data nodes 
     * to be filled 

     */ 

     /* 

     * Radio Link Protection - Configuration data nodes 
     * to be filled 

     */ 

     /* 

     * Radio Link Protection - state data nodes 
     * to be filled 

     */ 

     /* 

     * XPIC - Configuration data nodes 
     * to be filled

     */ 

     /* 

     * MIMO - Configuration data nodes 
     * to be filled

     */ 

 } 

}
