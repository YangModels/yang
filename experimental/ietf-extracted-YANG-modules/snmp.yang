module snmp {
  namespace "http://yang-central.org/ns/snmp";
  prefix "snmp";

  include snmp-common {
    revision-date 2010-10-17;
  }
  include snmp-agent {
    revision-date 2010-10-17;
  }
  include snmp-community {
    revision-date 2010-10-17;
  }
  include snmp-notification {
    revision-date 2010-10-17;
  }
  include snmp-target {
    revision-date 2010-10-17;
  }
  include snmp-target-params {
    revision-date 2010-10-17;
  }
  include snmp-vacm {
    revision-date 2010-10-17;
  }
  include snmp-usm {
    revision-date 2010-10-17;
  }

  description
    "This module contains a collection of YANG definitions for
     configuring SNMP engines.";

  revision 2010-10-17 {
    description
      "Initial revision.";
  }

}
