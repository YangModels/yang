module ietf-sr-service-programming {
  yang-version 1.1;

  namespace "urn:ietf:params:xml:ns:yang:ietf-sr-service-programming";
  prefix "sr-svc-pgm";

  import ietf-yang-types {
    prefix "yang";
  }

  import ietf-srv6-base {
    prefix "srv6";
  }

  import ietf-routing {
    prefix rt;
    reference "RFC 8349: A YANG Data Model for Routing
               Management (NMDA Version)";
  }

  import ietf-service-function-types {
    prefix "service-types";
  }

  import ietf-segment-routing {
    prefix sr;
  }

  import ietf-segment-routing-mpls {
    prefix srmpls;
  }

  import ietf-sr-service-programming-types {
    prefix "sr-svc-pgm-types";
  }

  import ietf-routing-types {
    prefix "rt-types";
  }
  import ietf-srv6-types {
    prefix "srv6-types";
  }

  organization "IETF SPRING Working Group";

  contact
      "WG Web:   <http://tools.ietf.org/wg/spring/>
       WG List:  <mailto:spring@ietf.org>

       Editor:   Jaganbabu Rajamanickam
                 <mailto:jrajaman@cisco.com>

       Editor:   Kamran Raza
                 <mailto:skraza@cisco.com>

       Editor:   Daniel Bernier
                 <mailto:daniel.bernier@bell.ca>

       Editor:   Gaurav Dawra
                 <mailto:gdawra.ietf@gmail.com>

       Editor:   Cheng Li
                 <mailto:c.l@huawei.com>";

  grouping service-statistics {

    container statistics {

      config false;
      description "Service statistics";

      leaf in-packet-count {
        type yang:counter64;
        description
          "Total number of packets processed by this service";
      }

      leaf in-bytes-count {
        type yang:counter64;
        description
          "Total number of bytes processed by this service";
      }

      leaf out-packet-count {
        type yang:counter64;
        description
          "Total number of packets end out after processing by this service";
      }

      leaf out-bytes-count {
        type yang:counter64;
        description
          "Total number of bytes end out after processing by this service";
      }

      leaf in-drop-packet-count {
        type yang:counter64;
        description
          "Total number of packets dropped while processing by this service";
      }

      leaf out-drop-packet-count {
        type yang:counter64;
        description
          "Total number of packets dropped while this service try to
           forward to its destination";
      }
    }
  }

  grouping service-mpls-sid-binding {
    container mpls {
      description
        "MPLS Service SID binding Container";

      when "../../service-programming-info/dataplane = 'mpls'";

      leaf sid {
        config false;
        type rt-types:mpls-label;
        description
          "MPLS SID value.";
      }
    }
  }

  grouping service-srv6-sid-binding {
    container srv6 {
      description
        "SRv6 Service SID binding Container";

      when "../../service-programming-info/dataplane = 'srv6'";

      leaf sid {
        config false;
        type srv6-types:srv6-sid;
        description
          "SRv6 SID value.";
      }

      leaf locator {
        type leafref {
          path "/rt:routing/sr:segment-routing"
              + "/srv6:srv6/srv6:locators/srv6:locator/srv6:name";
        }
        description
          "Reference to a SRv6 locator. This is valid only when
           the SID allocation mode is dynamic";
      }
    }
  }

  grouping service-sid-binding {
    container sid-binding {
      description
        "Service SID binding Container";

      leaf alloc-mode {
        config false;
        default dynamic;
        type sr-svc-pgm-types:sid-alloc-mode-type;
        description
          "Service SID allocation mode";
      }

      uses service-mpls-sid-binding;
      uses service-srv6-sid-binding;
    }
  }

  grouping service-programming-infos {
    container service-programming-info {

        leaf behaviour {
          mandatory true;
          type identityref {
            base sr-svc-pgm-types:service-program-behaviour-type;
          }
          description
            "SR program behaviour";
        }

        leaf dataplane {
          mandatory true;
          type sr-svc-pgm-types:dataplane-type;
          description
            "Service SID dataplane.";
        }

        leaf service-name {
          mandatory true;
          type string;
          description
            "Service program name to identify a specific program.";
        }

        leaf service-type {
          mandatory true;
          type identityref {
            base service-types:service-function-type;
          }
          description
            "Service-Type defined by IANA Service Type Table (STT). Like
             Firewall, DPI etc...";
        }

        leaf service-variant {
          mandatory true;
          type string;
          description
            "This identifies the variant of the service. This value should
             be unique in the given network. Example Format:
             <vendor>-<vendor-sub-variant>-<product-version>.";
        }

        leaf service-instance {
          mandatory true;
          type uint32;
          description
            "Service instance which differentiates the same service -- e.g.
             same vendors Firewall service could have several instances
             available. This could be used to differentiate the VPN
             customers or for load sharing purposes.";
        }

        leaf admin-status {
          type sr-svc-pgm-types:admin-status-type;
          default down;
          description
            "Admin Status";
        }
        leaf oper-status {
          config false;
          type identityref {
            base sr-svc-pgm-types:service-program-oper-status-type;
          }
          description
            "Service SID operational mode.";
        }

        uses service-statistics;

        container sr-services {

          description
              "Any SR-aware or AR-unaware services could augment this container";
          reference "Segment Routing Service Programming Architecture.";
        }
    }
  }

  grouping service-programmings {
    container service-programming {
      description
        "service programming container.
         Any new services programming added could augment
         this container to support that specific services.
         Currently in this model, only service proxy
         is defined. (i.e) For example if
         a Firewall services needs to be added then
         they could augment this container and
         extend this model";

      list service-program {
        key "name";
        description
          "Service program is keyed by the service program name";

        leaf name {
          mandatory true;
          type leafref {
            path "/rt:routing/sr:segment-routing/"
                + "sr-svc-pgm:service-programming/"
                + "sr-svc-pgm:service-program/"
                + "sr-svc-pgm:service-programming-info/"
                + "sr-svc-pgm:service-name";
          }
        }
        uses service-sid-binding;
        uses service-programming-infos;
      }
    }
  }

  /*
   * MPLS/SRv6 SR service programming using dynamic SID allocation
   */
  augment "/rt:routing/sr:segment-routing" {
    description
      "Augmenting the segment-routing to add SR service programming";

    uses service-programmings;
  }

  /*
   * MPLS SR service programming using static MPLS binding SID
   */
  augment "/rt:routing/sr:segment-routing/srmpls:sr-mpls/srmpls:bindings" {
    description
      "Augmenting the segment-routing MPLS static binding to add static
       MPLS SR service programming";

    container mpls-static-service-programming {
      description
        "Augmenting the MPLS segment-routing bindings with the SR service
         programming";
      list service-program {
        key "name";
        description
          "Service program is keyed by the service program name";

        leaf name {
          mandatory true;
          type leafref {
            path "/rt:routing/sr:segment-routing/"
                + "sr-svc-pgm:service-programming/"
                + "sr-svc-pgm:service-program/"
                + "sr-svc-pgm:service-programming-info/"
                + "sr-svc-pgm:service-name";
          }
        }

        leaf sid {
          mandatory true;
          type rt-types:mpls-label;
          description
            "MPLS SID value.";
        }

        uses service-programming-infos {
          /*
           * In the case of MPLs static binding configuration
           * the dataplane is set to mpls and not allowed to
           * configure
           */
          refine service-programming-info/dataplane {
            mandatory false;
            default mpls;
            config false;
          }
        }
      }
    }

  }

  /*
   * SRv6 SR service programming using static SRv6 binding SID
   */
  augment "/rt:routing/sr:segment-routing/srv6:srv6/srv6:locators/srv6:locator" {
    description
      "Augmenting the segment-routing SRv6 static to add static binding to
       SRv6 SR service programming";

    container end-AS {
      description
        "End.AS - Static Proxy SID behaviour";
      list service-program {
        key "name";
        description
          "Service program is keyed by the service program name";

        leaf name {
          mandatory true;
          type leafref {
            path "/rt:routing/sr:segment-routing/"
                + "sr-svc-pgm:service-programming/"
                + "sr-svc-pgm:service-program/"
                + "sr-svc-pgm:service-programming-info/"
                + "sr-svc-pgm:service-name";
          }
        }

        uses service-programming-infos {
          /*
           * In the case of SRv6 static binding configuration
           * the dataplane is set to mpls and not allowed to
           * configure
           */
          refine service-programming-info/dataplane {
            config false;
            mandatory false;
            default srv6;
          }
          refine service-programming-info/behaviour {
            config false;
            //when "service-programming-info/dataplane = 'srv6'";
            mandatory false;
            default sr-svc-pgm-types:static-proxy;
          }

        }
      }
    }

    container end-AD {
      description
        "End.AD - Dynamic Proxy SID behaviour";
      list service-program {
        key "name";
        description
          "Service program is keyed by the service program name";

        leaf name {
          mandatory true;
          type leafref {
            path "/rt:routing/sr:segment-routing/"
                + "sr-svc-pgm:service-programming/"
                + "sr-svc-pgm:service-program/"
                + "sr-svc-pgm:service-programming-info/"
                + "sr-svc-pgm:service-name";
          }
        }

        uses service-programming-infos {

          refine service-programming-info/dataplane {
            config false;
            mandatory false;
            default srv6;
          }
          refine service-programming-info/behaviour {
            //when "service-programming-info/dataplane = 'srv6'";
            config false;
            mandatory false;
            default sr-svc-pgm-types:dynamic-proxy;
          }

        }
      }
    }

    container end-AM {
      description
        "End.AD - Masquerading Proxy SID behaviour";
      list service-program {
        key "name";
        description
          "Service program is keyed by the service program name";

        leaf name {
          mandatory true;
          type leafref {
            path "/rt:routing/sr:segment-routing/"
                + "sr-svc-pgm:service-programming/"
                + "sr-svc-pgm:service-program/"
                + "sr-svc-pgm:service-programming-info/"
                + "sr-svc-pgm:service-name";
          }
        }

        uses service-programming-infos {

          refine service-programming-info/dataplane {
            config false;
            mandatory false;
            default srv6;
          }
          refine service-programming-info/behaviour {
            //when "service-programming-info/dataplane = 'srv6'";
            mandatory false;
            default sr-svc-pgm-types:Masquerading-proxy;
          }

        }
      }
    }

  }

  notification service-program-oper-status {
    description
      "This notification is sent when there is a change in the service
       program oper status.";
    leaf name {
      mandatory true;
      type leafref {
        path "/rt:routing/sr:segment-routing/"
            + "sr-svc-pgm:service-programming/"
            + "sr-svc-pgm:service-program/"
            + "sr-svc-pgm:name";
      }
      description
        "Service program name to identify a specific programming.";
    }

    leaf oper-status {
      mandatory true;
      type leafref {
        path "/rt:routing/sr:segment-routing/"
            + "sr-svc-pgm:service-programming/"
            + "sr-svc-pgm:service-program/"
            + "sr-svc-pgm:service-programming-info/"
            + "sr-svc-pgm:oper-status";
      }
      description
        "Service program operational status.";
    }

  }
}
