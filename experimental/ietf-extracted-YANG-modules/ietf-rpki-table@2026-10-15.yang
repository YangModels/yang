module ietf-rpki-table {
  yang-version 1.1;
  namespace "urn:ietf:params:xml:ns:yang:ietf-rpki-table";
  prefix rpki-table;

  import ietf-yang-types {
    prefix yang;
    reference
      "RFC 9911: Common YANG Data Types";
  }
  import ietf-inet-types {
    prefix inet;
    reference
      "RFC 9911: Common YANG Data Types";
  }
  import ietf-routing {
    prefix rt;
    reference
      "RFC 8349: A YANG Data Model for Routing Management
                 (NMDA Version)";
  }

  organization
    "IETF Secure Inter-Domain Routing Operations (SIDROPS)
     Working Group";
  contact
    "WG Web:   <https://datatracker.ietf.org/wg/sidrops/>
     WG List:  SIDROPS <mailto:sidrops@ietf.org>

     Editor:   Yisong Liu
               <mailto:liuyisong@chinamobile.com>
     Editor:   Changwang Lin
               <mailto:linchangwang.04414@h3c.com>
     Editor:   Haibo Wang
               <mailto:rainsword.wang@huawei.com>
     Editor:   Jishnu Roy
               <mailto:jishnu.roy@hpe.com>
     Editor:   Jeffrey Haas
               <mailto:jeffrey.haas@hpe.com>
     Editor:   Hongwei Liu
               <mailto:liu.hongwei3@zte.com.cn>
     Editor:   Di Ma
               <mailto:madi@zdns.cn>";
  description
    "This module describes a YANG model for the Resource Public
     Key Infrastructure (RPKI) to Router (RTR) protocol data
     management.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see the
     RFC itself for full legal notices.";

  revision 2026-10-15 {
    description
      "Initial Version";
    reference
      "RFC XXXX: YANG Data Model for RPKI to Router Protocol";
  }

  typedef ipv4-prefix-length {
    type uint8 {
      range "0 .. 32";
    }
    description
      "IPv4 Prefix Length.";
  }

  typedef ipv6-prefix-length {
    type uint8 {
      range "0 .. 128";
    }
    description
      "IPv6 Prefix Length.";
  }

  typedef subject-key-id {
    type binary {
      length "20";
    }
    description
      "Subject Key Identifier.";
  }

  typedef ccr-hash {
    type binary {
      length "32";
    }
    description
      "Canonical Cache Representation (CCR) state hash.

       This represents a 256-bit SHA-256 hash of the canonical
       representation of RPKI data as defined in RFC YYYY.

       The hash provides a compact, verifiable representation
       of the complete state of RPKI validation data, enabling
       efficient synchronization and consistency verification
       between caches.";
    reference
      "RFC YYYY: A Profile for Resource Public Key Infrastructure
                 (RPKI) Canonical Cache Representation (CCR)";
  }

  grouping aspa-overall-records {
    description
      "Autonomous System Provider Authorization (ASPA) records
       received from all RPKI cache servers.";
    reference
      "RFC ZZZZ: The Resource Public Key Infrastructure (RPKI) to
                 Router Protocol, Version 2";
    list aspas {
      key "customer-asn";
      description
        "An entry for ASPA.";
      leaf customer-asn {
        type inet:as-number;
        description
          "The AS number of a customer.";
      }
      leaf server-address {
        type inet:ip-address;
        description
          "IP address of the RPKI cache server.";
      }
      list provider-asns {
        key "provider-asn";
        description
          "Providers of the customer.";
        leaf provider-asn {
          type inet:as-number;
          description
            "The AS number of a provider.";
        }
      }
    }
  }

  augment "/rt:routing" {
    description
      "RPKI tables augmentation of ietf-routing module.";
    container vrp-tables {
      config false;
      description
        "List of tables containing Validated ROA Payloads
         received from all RPKI cache servers.";
      list vrp-table {
        key "name";
        description
          "Table of Validated ROA Payloads received from
           a RPKI cache server.";
        leaf name {
          type string;
          description
            "Name of the Validated ROA Payload table.";
        }
        leaf ccr-roapayloadstate-hash {
          type ccr-hash;
          description
            "CCR state hash for the ROA payload.

             This hash represents the canonical state of this
             specific ROA entry as defined in the CCR specification.
             It is optional and can be used to verify the integrity
             and consistency of ROA data originating from the RPKI
             cache.";
          reference
            "RFC YYYY: A Profile for Resource Public Key
                       Infrastructure (RPKI) Canonical Cache
                       Representation (CCR)";
        }
        container ipv4 {
          config false;
          description
            "Container for IPv4 Validated ROA Payloads table.";
          container vrps {
            config false;
            description
              "IPv4 Validated ROA Payloads received from the RPKI
               cache server.";
            list vrp {
              key "prefix max-len asn source";
              description
                "An entry of IPv4 Validated ROA Payload.";
              leaf prefix {
                type inet:ipv4-prefix;
                description
                  "The IPv4 prefix of the IPv4 Validated ROA
                   Payload.";
              }
              leaf max-len {
                type ipv4-prefix-length;
                description
                  "Denotes the longest IPv4 prefix allowed. This
                   MUST NOT be less than the IPv4 prefix length.";
              }
              leaf asn {
                type inet:as-number;
                description
                  "The origin AS number of the IPv4 Validated ROA
                   Payload.";
              }
              leaf source {
                type union {
                  type inet:ip-address;
                  type string;
                }
                description
                  "String representing the source of the record
                   in this record-set.";
              }
            }
          }
          leaf total-records {
            type yang:gauge32;
            description
              "Total number of IPv4 Validated ROA Payload records.";
          }
          leaf records-added {
            type yang:counter64;
            description
              "Number of IPv4 Validated ROA Payload records
               cumulatively added.";
          }
          leaf records-deleted {
            type yang:counter64;
            description
              "Number of IPv4 Validated ROA Payload records
               cumulatively deleted.";
          }
        }
        container ipv6 {
          config false;
          description
            "Container for IPv6 Validated ROA Payloads table.";
          container vrps {
            config false;
            description
              "IPv6 Validated ROA Payloads received from the RPKI
               cache server.";
            list vrp {
              key "prefix max-len asn source";
              description
                "An entry for IPv6 Validated ROA Payload.";
              leaf prefix {
                type inet:ipv6-prefix;
                description
                  "The IPv6 prefix of the IPv6 Validated ROA
                   Payload.";
              }
              leaf max-len {
                type ipv6-prefix-length;
                description
                  "Denotes the longest IPv6 prefix allowed. This
                   MUST NOT be less than the prefix length.";
              }
              leaf asn {
                type inet:as-number;
                description
                  "The origin AS number of the IPv6 Validated ROA
                   Payload.";
              }
              leaf source {
                type union {
                  type inet:ip-address;
                  type string;
                }
                description
                  "Representing the source of the record in this
                   record-set. Either a server IP or a source file
                   of static records.";
              }
            }
          }
          leaf total-records {
            type yang:gauge32;
            description
              "Total number of IPv6 Validated ROA Payload records.";
          }
          leaf records-added {
            type yang:counter64;
            description
              "Number of IPv6 Validated ROA Payload records
               cumulatively added.";
          }
          leaf records-deleted {
            type yang:counter64;
            description
              "Number of IPv6 Validated ROA Payload records
               cumulatively deleted.";
          }
        }
      }
    }
    container router-key-tables {
      config false;
      description
        "List of Router Key table received from all RPKI cache
         servers.";
      list router-key-table {
        key "name";
        description
          "Table of Router Keys received from a RPKI cache
           server.";
        leaf name {
          type string;
          description
            "Name of the Router Key table.";
        }
        leaf ccr-routerkeystate-hash {
          type ccr-hash;
          description
            "CCR state hash for the Router Key payload.

             This hash represents the canonical state of this
             specific Router Key entry as defined in the CCR
             specification. It is optional and can effectively
             verify the consistency of BGPsec Router Key data
             derived from the RPKI cache.";
          reference
            "RFC YYYY: A Profile for Resource Public Key
                       Infrastructure (RPKI) Canonical Cache
                       Representation (CCR)";
        }
        container router-keys {
          config false;
          description
            "Router Keys received from the RPKI cache server.";
          list router-key {
            key "ski asn key server-address";
            description
              "An entry for Router Key.";
            leaf ski {
              type subject-key-id;
              description
                "A Router Key's Subject Key Identifier (SKI).";
              reference
                "RFC 6487: A Profile for X.509 PKIX Resource
                           Certificates";
            }
            leaf asn {
              type inet:as-number;
              description
                "The AS number of the router which the key
                 belongs to.";
            }
            leaf key {
              type binary;
              description
                "A Router Key's subjectPublicKeyInfo value, as
                 described in Section 3.1.1 of RFC 8608, encoded
                 using ASN.1 Distinguished Encoding Rules (DER).";
              reference
                "RFC 8608: BGPsec Algorithms, Key Formats, and
                           Signature Formats";
            }
            leaf server-address {
              type inet:ip-address;
              description
                "IP address of the RPKI cache server.";
            }
          }
        }
      }
    }
    container aspa-tables {
      config false;
      description
        "List of tables of ASPAs received from all RPKI cache
         servers.";
      list aspa-table {
        key "name";
        description
          "Table of ASPAs received from a RPKI cache server.";
        leaf name {
          type string;
          description
            "Name of the ASPA table.";
        }
        leaf ccr-aspapayloadstate-hash {
          type ccr-hash;
          description
            "CCR state hash for the ASPA payload.

             This hash represents the canonical state of this
             specific ASPA entry as defined in the CCR
             specification. It is optional and facilitates
             consistency checking for AS path validation data
             originating from the RPKI cache.";
          reference
            "RFC YYYY: A Profile for Resource Public Key
                       Infrastructure (RPKI) Canonical Cache
                       Representation (CCR)";
        }
        uses aspa-overall-records;
      }
    }
  }
}
