module ietf-qos-classifier {
  yang-version 1.1;
  namespace "urn:ietf:params:xml:ns:yang:ietf-qos-classifier";
  prefix classifier;
  organization "IETF RTG (Routing Area) Working Group";
  contact
    "WG Web:   <http://tools.ietf.org/wg/rtgwg/>
     WG List:  <mailto:rtgwg@ietf.org>
     WG Chair: Chris Bowers
               <mailto:cbowers@juniper.net>
     WG Chair: Jeff Tantsura
               <mailto:jefftant.ietf@gmail.com>
     Editor:   Aseem Choudhary
               <mailto:asechoud@cisco.com>
     Editor:   Mahesh Jethanandani
               <mailto:mjethanandani@gmail.com>";
  description
    "This module contains a collection of YANG definitions for
     configuring qos specification implementations.
     Copyright (c) 2021 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";
  revision 2021-07-12 {
    description
      "Initial revision of qos base classifier module";
    reference "RFC XXXX";
  }
  feature policy-inline-classifier{
    description
      " This feature allows classifier configuration
        directly under policy.";
  }
  feature classifier-template-feature {
    description
      " This feature allows classifier as template configuration
        in a policy.";
  }
  feature match-any-filter-type-support {
    description
      " This feature allows classifier configuration
        directly under policy.";
  }

  identity filter-type {
    description
      "This is identity of base filter-type";
  }
  identity match-filter-operation {
    description
      "filter match logical operation type";
  }
  identity match-all-filter {
    base match-filter-operation;
    description
      "Classifier entry filter logical AND operation";
  }
  identity match-any-filter {
    if-feature "match-any-filter-type-support";
    base match-filter-operation;
    description
      "Classifier entry filter logical OR operation";
  }
  grouping filters {
    description
      "Filters types in a Classifier entry";
    leaf type {
      type identityref {
        base filter-type;
      }
      description
        "This leaf defines type of the filter";
    }
    leaf logical-not {
      type boolean;
      description
        "
         This is logical-not operator for a filter. When true, it
         indicates filter looks for absence of a pattern defined
         by the filter
        ";
    }
  }
  grouping generic-attr {
    description
      "
       Classifier generic attributes like name,
       description, operation type
      ";
    leaf name {
      type string;
      description
        "classifier entry name";
    }
    leaf description {
      type string;
      description
        "classifier entry description statement";
    }
    leaf filter-operation {
      type identityref {
        base match-filter-operation;
      }
      default "match-all-filter";
      description
        "Filters are applicable as match-any or match-all filters";
    }
  }
  grouping inline-attr {
    description
      "attributes of inline classifier in a policy";
    leaf inline {
      type boolean;
      default "false";
      description
        "Indication of inline classifier entry";
    }
    leaf filter-operation {
      type identityref {
        base match-filter-operation;
      }
      default "match-all-filter";
      description
        "Filters are applicable as match-any or match-all filters";
    }
    list filter{
      if-feature policy-inline-classifier;
      must " ../inline = 'true' " {
        description
          "For inline filter configuration, inline attribute" +
          "must be true";
      }
      key "type logical-not";
      uses filters;
      description
        "Filters configured inline in a policy";
    }
  }
  container classifiers {
    if-feature classifier-template-feature;
    description
      "list of classifier entry";
    list classifier{
      key "name";
      description
        "each classifier entry contains a list of filters";
      uses generic-attr;
      list filter {
        key "type logical-not";
        uses filters;
        description
          "Filter entry configuration";
      }
    }
  }
}
