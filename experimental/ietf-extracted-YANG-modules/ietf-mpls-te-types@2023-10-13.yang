module ietf-mpls-te-types {
  yang-version 1.1;
  namespace "urn:ietf:params:xml:ns:yang:ietf-mpls-te-types";
  prefix mpls-te-types;

  import ietf-routing-types {
    prefix rt-types;
    reference
      "RFC 8294: Common YANG Data Types for the Routing Area";
  }

  organization
    "Internet Engineering Task Force (IETF) TEAS WG";
  contact
    "WG Web:   <https://datatracker.ietf.org/wg/teas/>
     WG List:  <mailto:teas@ietf.org>

     Editor:   Italo Busi
               <mailto:italo.busi@huawei.com>

     Editor:   Aihua Guo
               <mailto:aihuaguo.ietf@gmail.com>

     Editor:   Xufeng Liu
               <mailto:xufeng.liu.ietf@gmail.com>

     Editor:   Tarek Saad
               <mailto:tsaad.net@gmail.com>

     Editor:   Rakesh Gandhi
               <mailto:rgandhi@cisco.com>";

  description
    "This module defines a collection of common YANG data type 
    and grouping definitions specific to MPLS-TE.

    Copyright (c) 2023 IETF Trust and the persons
    identified as authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

     This version of this YANG module is part of RFC XXXX; see
     the RFC itself for full legal notices.";

  revision 2023-10-13 {
    description
      "Initial Version";
    reference
      "RFC XXXX: A YANG Data Model for MPLS-TE Topology";
  }
  // RFC Editor: replace XXXX with the actual RFC number assigned 
  // to the RFC once this draft 
  // becomes an RFC, update date information and remove this note.

  /*
  * Typedefs
  */

  typedef load-balancing-type {
    type enumeration {
      enum per-flow {
        description
          "The load-balancing algorithm ensures that packets
           characterized as the same flow (e.g. based on IP 5-tuple)
           that egress on a LAG or a bundled TE link are forwarded
           on the same component link.

           Packets for different flows within the same LSP can be
           forwarded on different component links.";
      }
      enum per-top-label {
        description
          "The load-balancing algorithm ensures incoming MPLS
           packets with the same top MPLS label and that egress on
           on a LAG or bundled TE link are forwarded on the same
           component link.

           Packets for different flows within the same LSP are
           forwarded on the same component link.";
      }
    }
    description
      "The type of load balancing used on bundled links.";
  }  // typedef load-balancing-type

  /*
  * Groupings
  */

  grouping te-mpls-label-hop {
    description
      "MPLS-TE Label Hop.";

    leaf mpls-label {
      type rt-types:mpls-label;
      description
        "MPLS Label.";
    }
  }  // grouping te-mpls-label-hop
}
