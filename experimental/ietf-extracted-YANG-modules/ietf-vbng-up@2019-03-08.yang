module ietf-vbng-up{
namespace "urn:ietf:params:xml:ns:yang:ietf-vbng-up";
prefix "vbng-up";

import ietf-inet-types {
   prefix "inet";
 }

import ietf-logical-network-element {
  prefix lne;
}

organization
  "IETF NETCONF Working Group";

  contact
   "
     WG List:  <mailto:netconf@ietf.org>

     Editor:   Guangping Huang
               <mailto:huang.Guangping@zte.com.cn>
    ";

description
   "The YANG module defines a generic configuration
     model for vbng";

revision 2019-03-08{
  description "Initial a new vbng control and user plane separation
  yang data model, it includes ietf-vbng, ietf-vbng-cp,and ietf-vbng-up, this
  is ietf-vbng-up";
  reference
     "draft-cuspdt-rtgwg-cu-separation-yang-model-02";
}

/* Typedefs  */

  typedef address-family-type {
    type enumeration {
      enum ipv4 {
        description
          "IPv4";
      }
      enum ipv6 {
        description
          "IPv6";
      }
    }
    description
      "Typedef for address family type.";
  }

 /* Configuration Data */

 augment /lne:logical-network-elements/lne:logical-network-element {
 container ietf-vbng-up{
   list vbng-up {
     key shelf-no ;
     leaf shelf-no {
       type uint8 {
         range 1..127 ;
       }
       description 'Configure shelf-no of forwarder,1-127.';
     }

     leaf vbng-up-name {
       type string {
         length 1..31 ;
       }
       description 'Configure bng up name.' ;
     }
     container netconf-client {
       presence netconf-client ;
       list address-family {
        key "af";
        leaf af {
           type address-family-type;
           description
             "Address family type value.";
        }
        leaf ip {
         type inet:ip-address;
         mandatory true ;
         description 'Configure ip address of netconf server.';
        }
        description "address family list";
       }
       leaf user-name {
         type string {
           length 1..65 ;
         }
         description 'configure user name, default: "who".';
       }

       leaf password {
         type string {
           length 3..32 ;
         }
         description 'configure password, default: "who".';
       }

       leaf port {
         type uint32;
         description 'Configure port.';
       }
      description 'Configure netconf server.';
     }

     leaf keepalive-sink {
       type enumeration {
         enum enable {
           value 1 ;
           description 'enable the keepalive-sink function';
         }
         enum disable {
           value 0 ;
           description 'disable keepalive-sink function';
         }
       }
       description "configure keepalive-sink";
      }
      description "configure vbng-up list";
     }
   description "vbng-up configuration!";
 }
 description "augment lne model";
}
}
