module ietf-sr-policy-group {
  yang-version "1.1";
  namespace "urn:ietf:params:xml:ns:yang:ietf-sr-policy-group";
  prefix "sr-policy-group";

  import ietf-routing {
    prefix rt;
    reference
      "RFC 8349, A YANG Data Model for Routing Management
       (NMDA Version).";
  }
  organization
    "IETF SPRING Working Group";

  contact
    "TBD";

  description
    "This module describes a YANG model for configuring and managing
     SR Policy Groups.

     This YANG model conforms to the Network Management
     Datastore Architecture (NMDA) as described in RFC 8342.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2024-05-22 {
    description
      "Initial Version";
    reference
      "draft-ietf-spring-sr-policy-yang-02, YANG Data Model for
       Segment Routing Policy";
  }

  typedef dataplane-type {
    description "Dataplane type of segment routing";
    type enumeration {
      enum mpls {
        value 1;
          description "Segment-routing MPLS";
      }
      enum srv6 {
        value 2;
          description "Segment-routing v6";
      }
    }
  }

  augment "/rt:routing" {
    description
      "SR Policy Group augmentation to the segment routing traffic
       engineering model.";
    container sr-policy-groups {
      description
        "Configuration parameters of SR Policy Group.";
      list sr-policy-group {
        key "group-color";
        description
          "Each entry contains parameters for SR Policy Group
           identifiedby the 'color' key.";
        leaf group-color {
          type uint32 {
            range "1..4294967295";
          }
          mandatory true;
          description "Color associated with the policy group";
        }
        leaf name {
          type string {
            length "1..59";
          }
          description "SR Policy group name";
        }
        leaf description {
          type string;
          description "Description of the policy group";
        }
        leaf service-distinguish-method {
          type enumeration {
            enum DSCP-based {
              value 1;
              description "Distinguish service type based on DSCP
                in the message";
            }
            enum dot1q-based {
              value 2;
              description "Distinguish service type based on dot1q";
            }
            enum ServiceClass-based {
              value 3;
              description "Distinguish service type based on service
                class";
            }
            enum None {
              value 4;
              description "Not configure service type recognition
                method";
            }
          }
          description "Service traffic steering methods within SR
            policy group";
        }
        container forward-based-dscp {
          description "parameters of DSCP based steering traffic
            for SR policy group";
          leaf best-effort-dscp-list-v4 {
            type string;
            description "DSCP values for IPv4 packets matching
              best-effort. It is a comma-separated list of DSCP
              values. Each item can be an individual DSCP value
              or a DSCP value range. Use a tilde (~) to separate
              the start and end DSCP values of a range.
              Example: 1,2,3,5~8.";
          }
          leaf best-effort-dscp-list-v6 {
            type string;
            description "DSCP values for IPv6 packets matching
              best-effort. It is a comma-separated list of DSCP
              values. Each item can be an individual DSCP value
              or a DSCP value range. Use a tilde (~) to separate
              the start and end DSCP values of a range.
              Example: 1,2,3,5~8.";
          }
          leaf dscp-mismatch-drop {
            type boolean;
            default "false";
            description "When all DSCP values configured for
              best effort forwarding and SR policy forwarding do
              not match, and no default forwarding path is
              specified, discard traffic.";
          }
          container dscp-color-mapping-entries {
            description "DSCP-color mapping table";
            list mapping-entry {
              key "policy-color dataplane";
              description "This table contains color-DSCP mappings
                for an SRv6 policy group.";
              leaf policy-color {
                type uint32 {
                  range "1..4294967295";
                }
                mandatory true;
                description "Color associated with the policy
                  group";
              }
              leaf dataplane {
                type dataplane-type;
                mandatory true;
                description "The data plane type of the mapping
                  relationship between DSCP and color";
              }
              leaf dscp-list {
                type string;
                description "DSCP values for packets matching.
                  It is a comma-separated list of DSCP values.
                  Each item can be an individual DSCP value or
                  a DSCP value range. Use a tilde (~) to separate
                  the start and end DSCP values of a range.
                 Example: 1,2,3,5~8.";
              }
              leaf is-as-default {
                type boolean;
                default false;
                description "Whether to use the SRv6 policy
                  with this color as the default policy for
                  packets";
              }
            }
          }
        }
        container forward-based-dot1q {
          description "parameters of dot1q based steering
            traffic for SR policy group";
          leaf best-effort-dot1q-list {
            type string;
            description "Dot1q values for packets matching
              best-effort. It is a comma-separated list of
              dot1q values. Each item can be an individual
              dot1q value or a dot1q value range. Use a
              tilde (~) to separate the start and end dot1q
              values of a range. Example: 1,2,3,5~8.";
          }
          leaf dot1q-mismatch-drop {
            type boolean;
            default "false";
            description "When all dot1q values configured
              for best effort forwarding and SR policy
              forwarding do not match, and no default
              forwarding path is specified, discard traffic.";
          }
          container dot1q-color-mapping-entries {
            description "Dot1q-color mapping table";
            list mapping-entry {
              key "policy-color";
              description "This table contains color-dot1q
                mappings for an SRv6 policy group.";
              leaf policy-color {
                type uint32 {
                  range "1..4294967295";
                }
                mandatory true;
                description "Color associated with the policy
                  group";
              }
              leaf dot1q-list {
                type string;
                description "Dot1q values for packets
                  matching. It is a comma-separated list of
                  dot1q values. Each item can be an individual
                  dot1q value or a dot1q value range. Use a tilde
                  (~) to separate the start and end dot1q values
                  of a range. Example: 1,2,3,5~8.";
              }
              leaf is-as-default {
                type boolean;
                default false;
                description "Whether to use the SRv6 policy
                  with this color as the default policy for
                  packets";
              }
            }
          }
          container class-color-mapping-entries {
            description "Serviceclass-color mapping table";
            list mapping-entry {
              key "policy-color";
              description "This table contains color-serviceclass
                mappings for an SRv6 policy group.";
              leaf policy-color {
                type uint32 {
                  range "1..4294967295";
                }
                mandatory true;
                description "Color associated with the policy
                  group";
              }
              leaf class-list {
                type string;
                description "Service class values for packets
                  matching. It is a comma-separated list of
                  service class values. Each item can be an
                  individual service class value or a service
                  class value range. Use a tilde (~) to separate
                  the start and end service class values of
                  a range. Example: 1,2,3,5~8.";
              }
              leaf is-as-default {
                type boolean;
                default false;
                description "Whether to use the SRv6 policy
                  with this color as the default policy for
                  packets";
              }
            }
          }
        }
      }
    } // sr-policy-group
  } // augment
}
