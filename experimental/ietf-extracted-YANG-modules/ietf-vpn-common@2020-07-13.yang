module ietf-vpn-common {
  yang-version 1.1;
  namespace "urn:ietf:params:xml:ns:yang:ietf-vpn-common";
  prefix vpn-common;

  import ietf-netconf-acm {
    prefix nacm;
    reference
      "RFC 8341: Network Configuration Access Control Model";
  }
  import ietf-routing-types {
    prefix rt-types;
    reference
      "RFC 8294: Common YANG Data Types for the Routing Area";
  }
  import ietf-yang-types {
    prefix yang;
    reference
      "Section 3 of RFC 6991";
  }

  organization
    "IETF OPSA (Operations and Management Area) Working Group";
  contact
    "WG Web:   <https://datatracker.ietf.org/wg/opsawg/>
     WG List:  <mailto:opsawg@ietf.org>

     Editor:  Samier Barguil
              <mailto:samier.barguilgiraldo.ext@telefonica.com>

     Editor:  Oscar Gonzalez de Dios
              <mailto:oscar.gonzalezdedios@telefonica.com>

     Editor:  Mohamed Boucadair
              <mailto:mohamed.boucadair@orange.com>

     Author:  Qin Wu
              <mailto:bill.wu@huawei.com>";
  description
    "This YANG module defines a common module that is meant
     to be reused by various VPN-related modules (e.g.,
     Layer 3 VPN Service Model (L3SM), Layer 2 VPN Service
     Model (L2SM), Layer 3 VPN Network Model (L3NM), Layer 2
     VPN Network Model (L2NM)).

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-07-13 {
    description
      "Initial revision.";
    reference
      "RFC XXXX: A Layer 2/3 VPN Common YANG Model";
  }

  /* Features */

  feature cloud-access {
    description
      "Indicates support of the VPN to connect to a Cloud
       Service Provider (CSP).";
  }

  feature lag-interface {
    description
      "Indicates the support of Link aggregation between
       Site Network Accesses. ";
  }

  feature site-diversity {
    description
      "Indicates the site diversity in the customer premises.";
  }

  feature dot1q {
    description
      "This feature indicates the support of
       the 'dot1q' encapsulation.";
  }

  feature qinq {
    description
      "This feature indicates the support of
       the 'qinq' encapsulation.";
  }

  feature vxlan {
    description
      "This feature indicates the support of
       the 'vxlan' encapsulation.";
  }

  feature qinany {
    description
      "This feature indicates the support of
       the 'qinany' encapsulation.";
  }

  feature multicast {
    description
      "Indicates multicast capabilities support in a VPN.";
  }

  feature ipv4 {
    description
      "Indicates IPv4 support in a VPN.";
  }

  feature ipv6 {
    description
      "Indicates IPv6 support in a VPN.";
  }

  feature carrierscarrier {
    description
      "Indicates support of Carrier-of-Carrier VPNs.";
  }

  feature extranet-vpn {
    description
      "Indicates support of extranet VPNs.";
  }

  feature fast-reroute {
    description
      "Indicates support of Fast Reroute (FRR).";
  }

  feature qos {
    description
      "Indicates support of classes of services (CoSes).";
  }

  feature encryption {
    description
      "Indicates support of encryption.";
  }

  feature bfd {
    description
      "Indicates support of BFD.";
  }

  feature bearer-reference {
    description
      "Indicates support of the 'bearer-reference' access
       constraint.";
  }

  feature input-bw {
    description
      "This feature indicates the support of
       the 'input-bw' limit.";
  }

  /* Typedef */

  typedef vpn-id {
    type string;
    description
      "Defines an identifier that is used as
       a service identifier, for example.";
  }
  typedef address-family {
    type enumeration {
      enum ipv4 {
        description
          "IPv4 address family.";
      }
      enum ipv6 {
        description
          "IPv6 address family.";
      }
    }
    description
      "Defines a type for the address family.";
  }

  /* Identities */

  identity bw-direction {
    description
      "Identity for the bandwidth direction.";
  }

  identity input-bw {
    base bw-direction;
    description
      "Identity for the input bandwidth.";
  }

  identity output-bw {
    base bw-direction;
    description
      "Identity for the output bandwidth.";
  }

  identity qos-profile-direction {
    description
      "Base identity for QoS profile direction.";
  }

  identity site-to-wan {
    base qos-profile-direction;
    description
      "Identity for Site-to-WAN direction.";
  }

  identity wan-to-site {
    base qos-profile-direction;
    description
      "Identity for WAN-to-Site direction.";
  }

  identity both {
    base qos-profile-direction;
    description
      "Identity for both WAN-to-Site direction
       and Site-to-WAN direction.";
  }

  identity customer-application {
    description
      "Base identity for customer application.";
  }

  identity web {
    base customer-application;
    description
      "Identity for Web application (e.g., HTTP, HTTPS).";
  }

  identity mail {
    base customer-application;
    description
      "Identity for mail application.";
  }

  identity file-transfer {
    base customer-application;
    description
      "Identity for file transfer application (e.g., FTP, SFTP).";
  }

  identity database {
    base customer-application;
    description
      "Identity for database application.";
  }

  identity social {
    base customer-application;
    description
      "Identity for social-network application.";
  }

  identity games {
    base customer-application;
    description
      "Identity for gaming application.";
  }

  identity p2p {
    base customer-application;
    description
      "Identity for peer-to-peer application.";
  }

  identity network-management {
    base customer-application;
    description
      "Identity for management application
       (e.g., Telnet, syslog, SNMP).";
  }

  identity voice {
    base customer-application;
    description
      "Identity for voice application.";
  }

  identity video {
    base customer-application;
    description
      "Identity for video conference application.";
  }

  identity embb {
    base customer-application;
    description
      "Identity for an enhanced Mobile Broadband (eMBB)
       application.  Note that an eMBB application demands
       network performance with a wide variety of
       characteristics, such as data rate, latency,
       loss rate, reliability, and many other parameters.";
  }

  identity urllc {
    base customer-application;
    description
      "Identity for an Ultra-Reliable and Low Latency
       Communications (URLLC) application.  Note that a
       URLLC application demands network performance
       with a wide variety of characteristics, such as latency,
       reliability, and many other parameters.";
  }

  identity mmtc {
    base customer-application;
    description
      "Identity for a massive Machine Type
       Communications (mMTC) application.  Note that an
       mMTC application demands network performance
       with a wide variety of characteristics, such as data
       rate, latency, loss rate, reliability, and many
       other parameters.";
  }

  identity ie-type {
    description
      "Defines Import-Export routing profiles.
       Those profiles can be reused between VPN nodes.";
  }

  identity import {
    base ie-type;
    description
      "Import a routing profile.";
  }

  identity export {
    base ie-type;
    description
      "Export a routing profile.";
  }

  identity import-export {
    base ie-type;
    description
      "Import/Export a routing profile.";
  }

  identity site-network-access-type {
    description
      "Base identity for site-network-access type.";
  }

  identity point-to-point {
    base site-network-access-type;
    description
      "Identity for point-to-point connection.";
  }

  identity multipoint {
    base site-network-access-type;
    description
      "Identity for multipoint connection.
       Example: Ethernet broadcast segment.";
  }

  identity pseudowire {
    base site-network-access-type;
    description
      "Identity for pseudowire connections.";
  }

  identity loopback {
    base site-network-access-type;
    description
      "Identity for loopback connections.";
  }

  identity operational-status {
    description
      "Base identity for the operational status.";
  }

  identity operational-state-up {
    base operational-status;
    description
      "Operational status is UP/Enabled.";
  }

  identity operational-state-down {
    base operational-status;
    description
      "Operational status is DOWN/Disabled.";
  }

  identity operational-state-unknown {
    base operational-status;
    description
      "Operational status is UNKNOWN.";
  }

  identity administrative-status {
    description
      "Base identity for administrative status.";
  }

  identity administrative-state-up {
    base administrative-status;
    description
      "Administrative status is UP/Enabled.";
  }

  identity administrative-state-down {
    base administrative-status;
    description
      "Administrative status is DOWN/Disabled.";
  }

  identity administrative-state-testing {
    base administrative-status;
    description
      "Administrative status is up for testing purposes.";
  }

  identity administrative-state-pre-deployment {
    base administrative-status;
    description
      "Administrative status is pre-deployment phase.";
  }

  identity encapsulation-type {
    description
      "Base identity for encapsulation type.";
  }

  identity priority-tagged {
    base encapsulation-type;
    description
      "Identity for the priority-tagged interface.";
  }

  identity dot1q {
    base encapsulation-type;
    description
      "This identity indicates the support of
       the 'dot1q' encapsulation.";
  }

  identity qinq {
    base encapsulation-type;
    description
      "This identity indicates the support of
       the 'qinq' encapsulation.";
  }

  identity qinany {
    base encapsulation-type;
    description
      "This identity indicates the support of
       the 'qinany' encapsulation.";
  }

  identity vxlan {
    base encapsulation-type;
    description
      "This identity indicates the support of
       the 'vxlan' encapsulation.";
  }

  identity ethernet-type {
    base encapsulation-type;
    description
      "Identity for encapsulation type.";
  }

  identity vlan-type {
    base encapsulation-type;
    description
      "Identity for VLAN encapsulation.";
  }

  identity untagged-int {
    base encapsulation-type;
    description
      "Identity for Ethernet type.";
  }

  identity tagged-int {
    base encapsulation-type;
    description
      "Identity for the VLAN type.";
  }

  identity lag-int {
    base encapsulation-type;
    description
      "Identity for the VLAN type.";
  }

  identity tag-type {
    description
      "Base identity from which all tag types are derived.";
  }

  identity c-vlan {
    base tag-type;
    description
      "A CVLAN tag, normally using the 0x8100 Ethertype.";
  }

  identity s-vlan {
    base tag-type;
    description
      "An SVLAN tag.";
  }

  identity c-s-vlan {
    base tag-type;
    description
      "Using both a CVLAN tag and an SVLAN tag.";
  }

  identity protocol-type {
    description
      "Base identity for Protocol Type.";
  }

  identity gre {
    base protocol-type;
    description
      "GRE encapsulation.";
    reference
      "RFC 1701: Generic Routing Encapsulation (GRE)
       RFC 1702: Generic Routing Encapsulation over IPv4 networks
       RFC 7676: IPv6 Support for Generic Routing Encapsulation
                 (GRE)";
  }

  identity ldp {
    base protocol-type;
    description
      "Transport based on LDP.";
    reference
      "RFC 3086: LDP Specification";
  }

  identity sr {
    base protocol-type;
    description
      "Transport based on SR.";
    reference
      "RFC 8660: Segment Routing with the MPLS Data Plane
       RFC 8663: MPLS Segment Routing over IP
       RFC 8754: IPv6 Segment Routing Header (SRH)";
  }

  identity sr-te {
    base protocol-type;
    description
      "Transport based on SR-TE.";
    reference
      "RFC 8426: Recommendations for RSVP-TE and Segment Routing (SR)
       Label Switched Path (LSP) Coexistence";
  }

  identity rsvp-te {
    base protocol-type;
    description
      "Transport based on RSVP-TE.";
    reference
      "RFC 2205: Resource ReSerVation Protocol (RSVP) --
       Version 1 Functional Specification";
  }

  identity bgp-lu {
    base protocol-type;
    description
      "Transport based on BGP-LU.";
  }

  identity unknown {
    base protocol-type;
    description
      "Not known at this stage.";
  }

  identity vpn-topology {
    description
      "Base identity for VPN topology.";
  }

  identity any-to-any {
    base vpn-topology;
    description
      "Identity for any-to-any VPN topology.";
  }

  identity hub-spoke {
    base vpn-topology;
    description
      "Identity for Hub-and-Spoke VPN topology.";
  }

  identity hub-spoke-disjoint {
    base vpn-topology;
    description
      "Identity for Hub-and-Spoke VPN topology
       where Hubs cannot communicate with each other.";
  }

  identity custom {
    base vpn-topology;
    description
      "Identity for CUSTOM VPN topology
       where Hubs can act as Spoke for certain part of
       the network or Spokes as Hubs.";
  }

  identity role {
    description
      "Base identity for site or node type.";
  }

  identity any-to-any-role {
    base role;
    description
      "VPN-Node in an any-to-any IP VPN.";
  }

  identity spoke-role {
    base role;
    description
      "VPN-Node acting as a Spoke IP VPN.";
  }

  identity hub-role {
    base role;
    description
      "VPN-Node acting as a Hub IP VPN.";
  }

  identity custom-role {
    base role;
    description
      "VPN-Node with custom or complex role in the VPN.";
  }

  identity vpn-signaling-type {
    description
      "Identity of VPN signaling types";
  }

  identity l2vpn-bgp {
    base vpn-signaling-type;
    description
      "Identity of l2vpn-bgp";
  }

  identity evpn-bgp {
    base vpn-signaling-type;
    description
      "Identity of evpn-bgp";
  }

  identity t-ldp {
    base vpn-signaling-type;
    description
      "Identity of t-ldp.";
  }

  identity h-vpls {
    base vpn-signaling-type;
    description
      "Identity for h-vpls";
  }

  identity l2tp {
    base vpn-signaling-type;
    description
      "Identity of l2tp.";
  }

  identity service-type {
    description
      "Identity of service type.";
  }

  identity l3vpn {
    base service-type;
    description
      "Identity of L3VPN service.";
  }

  identity vpws {
    base service-type;
    description
      "Point-to-point Virtual Private Wire Service (VPWS)
       service type.";
  }

  identity pwe3 {
    base service-type;
    description
      "Pseudowire Emulation Edge to Edge (PWE3) service type.";
  }

  identity ldp-l2tp-vpls {
    base service-type;
    description
      "LDP-based or L2TP-based multipoint Virtual Private LAN
       Service (VPLS) service type.  This VPLS uses LDP-signaled
       Pseudowires or L2TP-signaled Pseudowires.";
  }

  identity bgp-vpls {
    base service-type;
    description
      "BGP-based multipoint VPLS service type.  This VPLS uses a
       BGP control plane.";
    reference
      "RFC4761:  Virtual Private LAN Service (VPLS) Using
                 BGP for Auto-Discovery and Signaling
       RFC 6624: Layer 2 Virtual Private Networks Using BGP for
                 Auto-Discovery and Signaling";
  }

  identity vpws-evpn {
    base service-type;
    description
      "VPWS service type using Ethernet VPNs (EVPNs).";
    reference
      "RFC 7432: BGP MPLS-Based Ethernet VPN";
  }

  identity pbb-evpn {
    base service-type;
    description
      "PBB EVPN.";
  }

  identity vxlan-peer-mode {
    description
      "Base identity for the VXLAN peer mode.";
  }

  identity static-mode {
    base vxlan-peer-mode;
    description
      "Identity for VXLAN access in the static mode.";
  }

  identity bgp-mode {
    base vxlan-peer-mode;
    description
      "Identity for VXLAN access by BGP EVPN learning.";
  }

  identity multicast-gp-address-mapping {
    description
      "Identity for multicast group mapping type.";
  }

  identity static-mapping {
    base multicast-gp-address-mapping;
    description
      "Identity for static mapping, i.e., attach the interface
       to the multicast group as a static member.";
  }

  identity dynamic-mapping {
    base multicast-gp-address-mapping;
    description
      "Identity for dynamic mapping, i.e., an interface was added
       to the multicast group as a result of snooping.";
  }

  identity multicast-tree-type {
    description
      "Base identity for multicast tree type.";
  }

  identity ssm-tree-type {
    base multicast-tree-type;
    description
      "Identity for SSM tree type.";
  }

  identity asm-tree-type {
    base multicast-tree-type;
    description
      "Identity for ASM tree type.";
  }

  identity bidir-tree-type {
    base multicast-tree-type;
    description
      "Identity for bidirectional tree type.";
  }

  identity multicast-rp-discovery-type {
    description
      "Base identity for RP discovery type.";
  }

  identity auto-rp {
    base multicast-rp-discovery-type;
    description
      "Base identity for Auto-RP discovery type.";
  }

  identity static-rp {
    base multicast-rp-discovery-type;
    description
      "Base identity for static type.";
  }

  identity bsr-rp {
    base multicast-rp-discovery-type;
    description
      "Base identity for BSR discovery type.";
  }

  /* Grouping */

  grouping vpn-description {
    leaf vpn-id {
      type vpn-common:vpn-id;
      description
        "VPN identifier.
         This identifier has a local meaning.";
    }
    leaf vpn-name {
      type string;
      description
        "A name used to refer to the VPN.";
    }
    leaf vpn-description {
      type string;
      description
        "Textual description of a VPN service.";
    }
    leaf customer-name {
      type string;
      description
        "Name of the customer that actually uses the VPN service.";
    }
    description
      "Provides common VPN information.";
  }

  grouping vpn-profile-cfg {
    container valid-provider-identifiers {
      list cloud-identifier {
        if-feature "cloud-access";
        key "id";
        leaf id {
          type string;
          description
            "Identification of cloud service.
             Local administration meaning.";
        }
        description
          "List for Cloud Identifiers.";
      }
      list encryption-profile-identifier {
        key "id";
        leaf id {
          type string;
          description
            "Identification of the SP encryption profile
             to be used.  Local administration meaning.";
        }
        description
          "List for encryption profile identifiers.";
      }
      list qos-profile-identifier {
        key "id";
        leaf id {
          type string;
          description
            "Identification of the QoS Profile to be used.
             Local administration meaning.";
        }
        description
          "List for QoS Profile Identifiers.";
      }
      list bfd-profile-identifier {
        key "id";
        leaf id {
          type string;
          description
            "Identification of the SP BFD Profile to be used.
             Local administration meaning.";
        }
        description
          "List for BFD Profile identifiers.";
      }
      list forwarding-profile-identifier {
        key "id";
        leaf id {
          type string;
          description
            "Identification of the Forwrding Profile Filter to be used.
             Local administration meaning.";
        }
        description
          "List for Forwrding Profile identifiers.";
      }
      list routing-profile-identifier {
        key "id";
        leaf id {
          type string;
          description
            "Identification of the routing Profile to be used
             by the routing-protocols within sites, vpn-
             network-accesses or vpn-nodes for refering
             vrf-import/export policies.
             This identifier has a local meaning.";
        }
        description
          "List for Routing Profile Identifiers.";
      }
      nacm:default-deny-write;
      description
        "Container for Valid Provider Identifies.";
    }
    description
      "Grouping for VPN Profile configuration.";
  }

  grouping status-timestamp {
    leaf status {
      type identityref {
        base operational-status;
      }
      description
        "Operations status";
    }
    leaf last-updated {
      type yang:date-and-time;
      description
        "Indicates the actual date and time of the service
         status change.";
    }
    description
      "This grouping defines some operational
       parameters for the service.";
  }

  grouping service-status {
    container status {
      container admin-status {
        leaf status {
          type identityref {
            base administrative-status;
          }
          description
            "Administrative service status.";
        }
        leaf last-updated {
          type yang:date-and-time;
          description
            "Indicates the actual date and time of the service
             status change.";
        }
        description
          "Administrative service status.";
      }
      container oper-status {
        config false;
        uses status-timestamp;
        description
          "Operational service status.";
      }
      description
        "Service status.";
    }
    description
      "Service status grouping.";
  }

  grouping svc-transport-encapsulation {
    container underlay-transport {
      leaf-list type {
        type identityref {
          base protocol-type;
        }
        ordered-by user;
        description
          "Protocols used to deliver a VPN service.";
      }
      description
        "Container for the Transport underlay.";
    }
    description
      "This grouping defines the type of underlay transport
       for VPN service.";
  }

  grouping rt-rd {
    leaf rd {
      type union {
        type rt-types:route-distinguisher;
        type empty;
      }
      description
        "Route distinguisher value. If this leaf has not been
         configured, the server will auto-assign a route
         distinguisher value and use that value operationally.
         This calculated value is available in the operational
         state.

         Use the empty type to indicate RD has no value and
         is not to be aouto-assigned.";
    }
    container vpn-targets {
      description
        "Set of route-targets to match for import and export routes
         to/from VRF";
      uses vpn-route-targets;
    }
    description
      "Grouping for RT and RD.";
  }

  grouping vpn-route-targets {
    description
      "A grouping that specifies Route Target import-export rules
       used in a BGP-enabled VPN.";
    list vpn-target {
      key "id";
      leaf id {
        type int8;
        description
          "Identifies each VPN Target";
      }
      list route-targets {
        key "route-target";
        leaf route-target {
          type rt-types:route-target;
          description
            "Route Target value";
        }
        description
          "List of Route Targets.";
      }
      leaf route-target-type {
        type rt-types:route-target-type;
        mandatory true;
        description
          "Import/export type of the Route Target.";
      }
      description
        "L3VPN route targets. AND/OR Operations are available
         based on the RTs assigment.";
    }
    reference
      "RFC4364: BGP/MPLS IP Virtual Private Networks (VPNs)
       RFC4664: Framework for Layer 2 Virtual Private Networks
       (L2VPNs)";
    container vpn-policies {
      description
        "VPN policies";
      leaf import-policy {
        type string;
        description
          "Defines the import policy.";
      }
      leaf export-policy {
        type string;
        description
          "Defines the export policy.";
      }
    }
  }

  grouping vpn-node-group {
    container groups {
      list group {
        key "group-id";
        leaf group-id {
          type string;
          description
            "Group-id the vpn-node belongs to.";
        }
        description
          "List of group-ids.";
      }
      description
        "Groups the vpn node and network access belongs to.";
    }
    description
      "Grouping definition to assign
       group-ids to group or network access.";
  }
}
