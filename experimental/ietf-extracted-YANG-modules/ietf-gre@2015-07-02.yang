module ietf-gre {
  namespace "urn:ietf:params:xml:ns:yang:ietf-gre";
  //namespace to be assigned by IANA
  prefix "gre";
  import ietf-inet-types {
    prefix "inet";
  }
  organization "IETF INTAREA Working Group";
  contact "draft-zheng-intarea-gre-yang";
  description "This module contains the YANG definition for GRE
               parameters as per RFC2784, RFC2890,
               draft-ietf-intarea-gre-ipv6 and
               draft-ietf-intarea-gre-mtu";
  revision "2015-07-02" {
   description "Initial revision.";
   reference "draft-zheng-intarea-gre-yang";
  }

  container gre-tunnel {
    description "Top level container";
    list gre-tunnel {
      key "tunnel-name";
      description "GRE tunnel";
      leaf tunnel-name {
        type string {
          length "1..63";
        }
        description "GRE tunnel name";
      }
      choice delivery-protocol {
        case ipv4 {
          leaf source-ipv4-address {
            type inet:ipv4-address;
            description "Source IP address";
          }
          leaf dest-ipv4-address {
            type inet:ipv4-address;
            description "Destination IP address";
          }
        }
        case ipv6 {
          leaf source-ipv6-address {
            type inet:ipv6-address;
            description "Source IP address";
          }
          leaf dest-ipv6-address {
            type inet:ipv6-address;
            description "Destination IP address";
          }
        }
        description "Delivery protocol";
      }
      leaf pmtud-enable {
        type boolean;
        description "Enable tunnel PMTU discovery";
      }
      leaf fragmentation-enable {
        type boolean;
        description "Enable delivery packets fragmentation";
      }
      leaf checksum-enable {
        type boolean;
        description "Enable GRE tunnel checksum verification";
      }
      leaf key-enable {
        type boolean;
        description "Enable optional GRE tunnel Key";
      }
      leaf key {
        when "/gre-tunnel/gre-tunnel/key-enable == 'true'" {
          description "When key-enable is true";
        }
        type uint32;
        description "GRE tunnel key value";
      }
      leaf sequence-number-enable {
        type boolean;
        description "Enable optional GRE tunnel Sequence Number";
      }
    }
  }
}
