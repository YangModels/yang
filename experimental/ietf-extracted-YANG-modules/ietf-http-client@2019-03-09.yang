module ietf-http-client {
  yang-version 1.1;
  namespace "urn:ietf:params:xml:ns:yang:ietf-http-client";
  prefix httpc;

  organization
    "IETF NETCONF (Network Configuration) Working Group";
  contact
    "WG Web:   <http://datatracker.ietf.org/wg/netconf/>
     WG List:  <mailto:netconf@ietf.org>
     Author:   Kent Watsen <mailto:kent+ietf@watsen.net>";
  description
    "This module defines reusable groupings for HTTP clients that
     can be used as a basis for specific HTTP client instances.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 [RFC2119]
     [RFC8174] when, and only when, they appear in all
     capitals, as shown here.

     Copyright (c) 2019 IETF Trust and the persons identified as
     authors of the code. All rights reserved.

     Redistribution and use in source and binary forms, with or
     without modification, is permitted pursuant to, and subject
     to the license terms contained in, the Simplified BSD
     License set forth in Section 4.c of the IETF Trust's
     Legal Provisions Relating to IETF Documents
     (http://trustee.ietf.org/license-info).

     This version of this YANG module is part of RFC XXXX; see
     the RFC itself for full legal notices.";

  revision 2019-03-09 {
    description
      "Initial version";
    reference
      "RFC XXXX: YANG Groupings for HTTP Clients and HTTP Servers";
  }

  // Features

  feature http-client-keepalives {
    description
      "Per socket HTTP keepalive parameters are configurable for
       HTTP clients on the server implementing this feature.";
  }

  // Groupings

  grouping http-client-grouping {
    description
      "A reusable grouping for configuring a HTTP client,
       including the IP address and port number it initiates
       a connections to.";
    uses http-client-identity-grouping;
    uses http-keepalives-grouping;
    // uses http-proxy-grouping;
  }

  grouping http-client-identity-grouping {
    description
      "A reusable grouping for configuring a HTTP client identity.";
    container http-client-identity {
      description
        "The credentials used by the client to authenticate to
         the HTTP server.";
      choice auth-type {
        description
          "The authentication type.";
        container basic {
          leaf user-id {
            type string;
            description
              "The user-id for the authenticating client.";
          }
          leaf password {
            type string;
            description
              "The password for the authenticating client.";
          }
          description
            "The 'basic' HTTP scheme credentials.";
          reference
            "RFC 7617: The 'Basic' HTTP Authentication Scheme";
        }
        container bearer {
          leaf token {
            type string;
            description
              "The bearer token for the authenticating client,
               encoded in base64, as described in RFC 6750,
               Section 2.1.";
          }
          description
            "The 'bearer' HTTP scheme credentials.";
          reference
            "RFC 6750: The OAuth 2.0 Authorization Framework:
                       Bearer Token Usage";
        }
        container digest {
          leaf username {
            type string;
            description
              "The username for the authenticating client.";
          }
          leaf password {
            type string;
            description
              "The password for the authenticating client.";
          }
          description
            "The 'digest' HTTP scheme credentials.";
          reference
            "RFC 7616: HTTP Digest Access Authentication";
        }
        container hoba {
          // FIXME
          description
            "The 'hoba' HTTP scheme credentials.";
          reference
            "RFC 7486: HTTP Origin-Bound Authentication (HOBA)";
        }
        container mutual {
          // FIXME
          description
            "The 'mutual' HTTP scheme credentials.";
          reference
            "RFC 8120: Mutual Authentication Protocol for HTTP";
        }
        container negotiate {
          // FIXME
          description
            "The 'negotiate' HTTP scheme credentials.";
          reference
            "RFC 4559: SPNEGO-based Kerberos and NTLM HTTP
                       Authentication in Microsoft Windows";
        }
        container oauth {
          // FIXME
          description
            "The 'oauth' HTTP scheme credentials.";
          reference
            "RFC 6749: The OAuth 2.0 Authorization Framework";
        }
        container scram-sha-1 {
          // FIXME
          description
            "The 'scram-sha-1' HTTP scheme credentials.";
          reference
            "RFC 7804: Salted Challenge Response HTTP
                       Authentication Mechanism";
        }
        container scram-sha-256 {
          // FIXME
          description
            "The 'scram-sha-256' HTTP scheme credentials.";
          reference
            "RFC 7804: Salted Challenge Response HTTP
                       Authentication Mechanism";
        }
        container vapid {
          // FIXME
          description
            "The 'vapid' HTTP scheme credentials.";
          reference
            "RFC 8292: Voluntary Application Server
                       Identification (VAPID) for Web Push";
        }
      }
    }
  }
  grouping http-keepalives-grouping {
    description
      "A reusable grouping for configuring HTTP client keepalive
       parameters.";
    container http-keepalives {
      if-feature "http-client-keepalives";
      description
        "Configures the keep-alive policy, to proactively test
         the aliveness of the HTTP server.  An unresponsive
         HTTP server is dropped after approximately max-wait
         * max-attempts seconds.";
      leaf max-wait {
        type uint16 {
          range "1..max";
        }
        units "seconds";
        default "30";
        description
          "Sets the amount of time in seconds after which if no
           data has been received from the HTTP server, a HTTP
           level message will be sent to test the aliveness of
           the HTTP server.";
      }
      leaf max-attempts {
        type uint8;
        default "3";
        description
          "Sets the maximum number of sequential keep-alive messages
           that can fail to obtain a response from the HTTP server
           before assuming the HTTP server is no longer alive.";
      }
    }
  }
}
