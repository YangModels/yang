module ietf-transport-network-slice {
  yang-version 1.1;
  namespace
    "urn:ietf:params:xml:ns:yang:ietf-transport-network-slice";
  prefix "tns";

  import ietf-network {
    prefix "nw";
    reference "RFC 8345: A YANG Data Model for Network Topologies";
  }
  import ietf-network-topology {
    prefix "nt";
    reference "RFC 8345: A YANG Data Model for Network Topologies";
  }

  import ietf-network-slice-service {
    prefix "ietf-nss";
    reference
      "draft-ietf-teas-ietf-network-slice-nbi-yang-01:
       IETF Network Slice Service YANG Model";
  }

  import ietf-ns-topo {
    prefix "ns-topo";
    reference
      "draft-liu-teas-transport-network-slice-yang-06:
       IETF Network Slice YANG Model";
  }

  organization
    "IETF CCAMP Working Group";
  contact
    "WG Web: <http://tools.ietf.org/wg/ccamp/>
     WG List: <mailto:ccamp@ietf.org>

     Editor: Haomian Zheng
             <mailto:zhenghaomian@huawei.com>

     Editor: Italo Busi
             <mailto:italo.busi@huawei.com>

     Editor: Aihua Guo
             <mailto:aihuaguo.ietf@gmail.com>

     Editor: Sergio Belotti
             <mailto:sergio.belotti@nokia.com>";

  description
    "This module defines a base YANG data model for configuring
     generic network slices in optical transport networks, e.g.,
     Optical Transport Network (OTN).

     The model fully conforms to the Network Management Datastore
     Architecture (NMDA).

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see the
     RFC itself for full legal notices.";

  revision "2023-02-08" {
    description
      "Latest revision of NBI YANG model for OTN slicing.";
    reference
      "draft-ietf-ccamp-yang-otn-slicing-03: Framework and Data
       Model for OTN Network Slicing";
  }

  /*
   * Groupings
   */
  grouping topology-ref {
    description
      "Grouping for network topology reference.";
    leaf topology-id {
      type leafref {
        path "/nw:networks/nw:network/nw:network-id";
      }
      description
        "Relative reference to network slice topology id.";
    }
    uses explicit-path;
  }

  grouping explicit-path {
    description
      "Explicit path for a connectivity matrix entry";

    list explicit-path {
      key "tp-id";
      description
        "List of TPs within a network topology that form a
         path.";
      leaf tp-id {
        type leafref {
          path "/nw:networks/nw:network/nw:node"+
               "/nt:termination-point/nt:tp-id";
        }
        description
          "Relative reference to TP id.";
      }
    }
  }

  /*
   * Augmented data nodes
   */
  augment "/ietf-nss:network-slice-services" +
          "/ietf-nss:slo-sle-templates" +
          "/ietf-nss:slo-sle-template" +
          "/ietf-nss:service-slo-sle-policy" {
    description
       "Augment IETF network slice service templates with
                technology-specific SLO/SLE policy attributes.";

    uses ns-topo:ns-topo-slo-sle-policy;
  }

  augment "/ietf-nss:network-slice-services" +
          "/ietf-nss:slo-sle-templates" +
          "/ietf-nss:slo-sle-template" +
          "/ietf-nss:service-slo-sle-policy" +
          "/ietf-nss:steering-constraints" {
    description
       "Augment IETF network slice service templates with
                technology-specific steering constraints.";

    uses ns-topo:ns-topo-steering-constraints;
  }

  augment "/ietf-nss:network-slice-services" +
          "/ietf-nss:slice-service" +
          "/ietf-nss:slo-sle-policy" +
          "/ietf-nss:custom" +
          "/ietf-nss:service-slo-sle-policy" {
    description
       "Augment IETF network slice services to include technology-
        specific SLO/SLE policy for connectivity-based transport
       network slices.";

    uses ns-topo:ns-topo-slo-sle-policy;
  }

  augment "/ietf-nss:network-slice-services" +
          "/ietf-nss:slice-service" +
          "/ietf-nss:slo-sle-policy" +
          "/ietf-nss:custom" +
          "/ietf-nss:service-slo-sle-policy" +
          "/ietf-nss:steering-constraints" {
    description
      "Augment IETF network slice services to include steering
      constraints for connectivity-based transport network
      slices.";

    uses ns-topo:ns-topo-steering-constraints;
  }

  /* connectivity construct augments */
  augment "/ietf-nss:network-slice-services" +
          "/ietf-nss:slice-service" +
          "/ietf-nss:connection-groups" +
          "/ietf-nss:connection-group" +
          "/ietf-nss:slo-sle-policy" +
          "/ietf-nss:custom" +
          "/ietf-nss:service-slo-sle-policy" {
    description
      "Augment IETF network slice services to include technology-
       specific SLO/SLE policy for connectivity-constructs within
       a connectivity-based transport network slice.";
    uses ns-topo:ns-topo-slo-sle-policy;
  }

  augment "/ietf-nss:network-slice-services" +
          "/ietf-nss:slice-service" +
          "/ietf-nss:connection-groups" +
          "/ietf-nss:connection-group" +
          "/ietf-nss:slo-sle-policy" +
          "/ietf-nss:custom" +
          "/ietf-nss:service-slo-sle-policy" +
          "/ietf-nss:steering-constraints" {
    description
      "Augment IETF network slice services to include steering
      constraints for connectivity-constructs within a
      connectivity-based transport network slice.";
    uses ns-topo:ns-topo-steering-constraints;
  }

  augment "/ietf-nss:network-slice-services" +
          "/ietf-nss:slice-service" +
          "/ietf-nss:connection-groups" +
          "/ietf-nss:connection-group" +
          "/ietf-nss:slo-sle-policy" +
          "/ietf-nss:custom" +
          "/ietf-nss:service-slo-sle-policy" +
          "/ietf-nss:steering-constraints" +
          "/ietf-nss:path-constraints" {
    description
      "Add toplogy id and explicit path to the connection group";

    uses topology-ref;
  }

  augment "/ietf-nss:network-slice-services" +
          "/ietf-nss:slice-service" +
          "/ietf-nss:connection-groups" +
          "/ietf-nss:connection-group" +
          "/ietf-nss:connectivity-construct" +
          "/ietf-nss:slo-sle-policy" +
          "/ietf-nss:custom" +
          "/ietf-nss:service-slo-sle-policy" {
    description
      "Augment IETF network slice services to include technology-
       specific SLO/SLE policy for connectivity-constructs within
       a connectivity-based transport network slice.";
    uses ns-topo:ns-topo-slo-sle-policy;
  }

  augment "/ietf-nss:network-slice-services" +
          "/ietf-nss:slice-service" +
          "/ietf-nss:connection-groups" +
          "/ietf-nss:connection-group" +
          "/ietf-nss:connectivity-construct" +
          "/ietf-nss:slo-sle-policy" +
          "/ietf-nss:custom" +
          "/ietf-nss:service-slo-sle-policy" +
          "/ietf-nss:steering-constraints" {
    description
      "Augment IETF network slice services to include steering
      constraints for connectivity-constructs within a
      connectivity-based transport network slice.";
    uses ns-topo:ns-topo-steering-constraints;
  }

  augment "/ietf-nss:network-slice-services" +
          "/ietf-nss:slice-service" +
          "/ietf-nss:connection-groups" +
          "/ietf-nss:connection-group" +
          "/ietf-nss:connectivity-construct" +
          "/ietf-nss:slo-sle-policy" +
          "/ietf-nss:custom" +
          "/ietf-nss:service-slo-sle-policy" +
          "/ietf-nss:steering-constraints" +
          "/ietf-nss:path-constraints" {
    description
      "Add toplogy id and explicit path to the connectivity
               construct";

    uses topology-ref;
  }

  augment "/ietf-nss:network-slice-services" +
          "/ietf-nss:slice-service" +
          "/ietf-nss:connection-groups" +
          "/ietf-nss:connection-group" +
          "/ietf-nss:connectivity-construct" +
          "/ietf-nss:type" +
          "/ietf-nss:a2a" +
          "/ietf-nss:a2a-sdp" +
          "/ietf-nss:slo-sle-policy" +
          "/ietf-nss:custom" +
          "/ietf-nss:service-slo-sle-policy" {
    description
      "Augment IETF network slice services to include technology-
       specific SLO/SLE policy for a2a connectivity-constructs
       within a connectivity-based transport network slice.";
    uses ns-topo:ns-topo-slo-sle-policy;
  }

  augment "/ietf-nss:network-slice-services" +
          "/ietf-nss:slice-service" +
          "/ietf-nss:connection-groups" +
          "/ietf-nss:connection-group" +
          "/ietf-nss:connectivity-construct" +
          "/ietf-nss:type" +
          "/ietf-nss:a2a" +
          "/ietf-nss:a2a-sdp" +
          "/ietf-nss:slo-sle-policy" +
          "/ietf-nss:custom" +
          "/ietf-nss:service-slo-sle-policy" +
          "/ietf-nss:steering-constraints" {
    description
      "Augment IETF network slice services to include steering
      constraints for a2a connectivity-constructs within a
      connectivity-based transport network slice.";
    uses ns-topo:ns-topo-steering-constraints;
  }

  augment "/ietf-nss:network-slice-services" +
          "/ietf-nss:slice-service" +
          "/ietf-nss:connection-groups" +
          "/ietf-nss:connection-group" +
          "/ietf-nss:connectivity-construct" +
          "/ietf-nss:type" +
          "/ietf-nss:a2a" +
          "/ietf-nss:a2a-sdp" +
          "/ietf-nss:slo-sle-policy" +
          "/ietf-nss:custom" +
          "/ietf-nss:service-slo-sle-policy" +
          "/ietf-nss:steering-constraints" +
          "/ietf-nss:path-constraints" {
    description
      "Add toplogy id and explicit path to a2a connectivity
               construct";

    uses topology-ref;
  }
}
