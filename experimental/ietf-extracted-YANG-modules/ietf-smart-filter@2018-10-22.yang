module ietf-smart-filter {
  yang-version "1.1";
  namespace "urn:ietf:params:xml:ns:yang:ietf-smart-filter";
  prefix "sf";

  import ietf-yang-types {
    prefix yang;
        reference
          "RFC 6991: Common YANG Data Types";
  }

  import ietf-subscribed-notifications {

    prefix sn;
    reference
      "draft-ietf-netconf-subscribed-notifications:
       Customized Subscriptions to a Publisher's Event Streams

       NOTE TO RFC Editor: Please replace above reference to
       draft-ietf-netconf-subscribed-notifications with RFC number
       when published (i.e. RFC xxxx).";
  }

  organization "IETF";
  contact
    "WG Web:   <http://tools.ietf.org/wg/netconf/>
     WG List:  <mailto:netconf@ietf.org>

     Editor:   Alexander Clemm
               <mailto:ludwig@clemm.org>

     Editor:   Eric Voit
               <mailto:evoit@cisco.com>

     Editor:   Xufeng Liu
               <mailto:xufeng.liu.ietf@gmail.com>

     Editor:   Igor Bryskin
               <mailto:igor.bryskin@huawei.com>

     Editor:   Tianran Zhou
               <mailto:zhoutianran@huawei.com>

     Editor:   Guangying Zheng
               <mailto:zhengguangying@huawei.com>

     Editor:   Henk Birkholz
               <mailto:henk.birkholz@sit.fraunhofer.de>";

  description
    "This module contains YANG specifications for smart filter.

    Copyright (c) 2018 IETF Trust and the persons identified as authors
    of the code.  All rights reserved.

    Redistribution and use in source and binary forms, with or without
    modification, is permitted pursuant to, and subject to the license
    terms contained in, the Simplified BSD License set forth in Section
    4.c of the IETF Trust's Legal Provisions Relating to IETF Documents
    (https://trustee.ietf.org/license-info).

        This version of this YANG module is part of
        draft-clemm-netmod-push-smart-filters-01; see the RFC itself
                for full legal notices.

        NOTE TO RFC EDITOR: Please replace above reference to
        with RFC number when
        published (i.e. RFC xxxx).";

  revision 2018-10-22 {
    description
      "Initial revision.
      NOTE TO RFC EDITOR:
      (1)Please replace the above revision date to
      the date of RFC publication when published.
      (2) Please replace the date in the file name
      (ietf-smart-filter@2018-10-22.yang) to the date of RFC
      publication.
      (3) Please replace the following reference to
      draft-clemm-netmod-push-smart-filters-01 with RFC number when
      published (i.e. RFC xxxx).";
    reference
      "draft-clemm-netmod-push-smart-filters-01";
  }

 /*
  * IDENTITIES
  */

  /* Smart-filter type identities  */

  identity smart-filter {
     description
      "A base identity that represents the smart filter types. ";
  }

  identity smart-filter-threshold {
     base smart-filter;
     description
      "An identity instance based on smart-filter, which support
       filter the push data by fix threshold value.";
  }

 /*
  * TYPE DEFINITIONS
  */
  typedef sf-op-type {
    type enumeration {
      enum eq {
        description "equal to";
      }
      enum gt {
        description "greater than";
      }
      enum ge {
        description "greater than or equal to";
      }
      enum lt {
        description "less than";
      }
      enum le {
        description "less than or equal to";
      }
    }
    description "A boolean comparator for an object and a data value.
            Include: eq, gt, ge, lt, le.";
  }

 /*
  * GROUP DEFINITIONS
  */
  grouping sf-threshold{
    description
      "the group for threshold filter";
    leaf filter-node {
      if-feature "sn:xpath";
      type yang:xpath1.0;
      description
        "This parameter contains an XPath expression identifying
         the node of the target filter.";
      }

    leaf threshold-value {
      type string;
      description "threshold value";
    }

    leaf op-type {
      type sf-op-type;
      description "comparison operator";
    }
  }

  //augment statements
  augment "/sn:subscriptions/sn:subscription" {
    description "add the smart filter container";
    container smart-filter {
      description "It concludes filter configurations";

      choice filter-type {
        description
          "Select different smart filter";
        case threshold-filter {
          description
            "threshold-filter";
          uses sf-threshold;
        }
      }
    }
  }
}
