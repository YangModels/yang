module ietf-flexe-yang {
  yang-version 1.1;
  namespace "urn:ietf:params:xml:ns:yang:ietf-flexe-yang";
  prefix "flexe";
  import ietf-routing-types {
    prefix rt-types;
    description "Import ietf-routing-types module.";
    reference "RFC8294";
  }
  import ietf-interfaces {
    prefix if;
    description "Import ietf-interfaces module.";
    reference "RFC7223";
  }
  import ietf-flexe-types {
    prefix flexe-tp;
    description "Import ietf-flexe-types module.";
  }
  organization
    "Internet Engineering Task Force (IETF) CCAMP WG";
  contact
    "WG List: <mailto:ccamp@ietf.org>
     Editor:  Xiaobing Niu (niu.xiaobing@zte.com.cn);
     Editor:  Qilei Wang (wang.qilei@zte.com.cn);
     Editor:  Sivakumar Munagapati (smunagap@cisco.com)";
  description
    "This module defines a YANG data model for FlexE.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents(http://trustee.ietf.org/license-info).

     This version of this YANG module is part of RFC TBD; see the RFC
     itself for full legal notices.";
  revision 2019-11-04 {
    description
      "Version 03.";
    reference
      "draft-xiaobn-ccamp-flexe-yang-mod-03.txt";
  }
  revision 2019-06-06 {
    description
      "Version 02.";
    reference
      "draft-xiaobn-ccamp-flexe-yang-mod-02.txt";
  }
  revision 2019-05-17 {
    description
      "Version 01.";
    reference
      "draft-xiaobn-ccamp-flexe-yang-mod-01.txt";
  }
  revision 2019-03-11 {
    description
      "Initial version.";
    reference
      "draft-xiaobn-ccamp-flexe-yang-mod-00.txt";
  }

  grouping slot-list
  {
    description
      "Calendar slots in FlexE instances.";
    list instance-slots{
      key "flexe-inst-num slot-id";
      description
        "List of slots for the FlexE client.";
      leaf flexe-inst-num{
        type uint8 ;
        description
          "It refers to the FlexE instance of a calendar slot.
           Clause 6.1 FlexE Group in FlexE IA 2.1";
      }
      leaf slot-id {
        type uint8;
        description
          "Id number of a sub-calendar slot in a FlexE instance.
           In a 100G FlexE instance,
           for 5G granularity, the range of slot-id is [0,19];
           for 25G granularity, the range of slot-id is [0,3];
           In a 50G FlexE instance,
           for 5G granularity, the range of slot-id is [0,9];
           for 25G granularity, the range of slot-id is [0,1];
           Refer to clause 6.8 in FlexE IA 2.1. ";
      }
    }
  }

  /* Configuration of FlexE */
  container flexe-configuration{
    description
      "FlexE configuration, including configurations of FlexE groups
       and FlexE clients.";
    container flexe-groups {
      description
        "Container for the FlexE Group";
      list flexe-group {
        key group-number;
        description
          "List of FlexE Group";
        leaf group-number {
          type uint32 {
            range 1..1048574 ;
          }
        description
          "The FlexE Group number is selected from the range 1~0xFFFFE.
           The value of 0x00000 and 0xFFFFF may not be used to
           designate a FlexE Group.";
        }
        container group-attributes {
          description
            "The attributes of a FlexE Group";
          leaf flexe-gp-avb-bw{
            type rt-types:bandwidth-ieee-float32;
            description
              "Availbale bandwidth allocated in the FlexE Group.
              Considering the FlexE Client MAC rates supported by FlexE
              Groups are 10, 40, m*25 Gbps, or a subset of these rates,
              it's recommended to confine the bandwidth allocated for a
              FlexE group into a integer compound from litmited types
              of MAC rateds.";
          }
          leaf cal-slot-gran{
            type flexe-tp:cal-slot-gran;
              description
                "The granularity of calendar slot is 5G or 25G";
              reference
                "OIF FlexE IA 2.1";
          }
          leaf flexe-phy-type{
            type flexe-tp:flexe-phy-type;
            description
              "Types of PHYs, such as 50/100/200/400GBASE-R";
            reference
              "OIF FlexE IA 2.1";
          }
          container bonded-phys {
            description
              "PHYs bonded to form a FlexE Group";
            list flexe-phys {
              key phy-number-in-group;
              description
                "One of bonded PHYs in a FlexE Group";
              leaf phy-number-in-group{
                type uint8{
                  range "1 .. 254";
                }
                description
                  "Refer to the clause 6.1 in FlexE IA 2.0.
                   For 100GBASE-R, the FlxeE PHY num and the 100G
                   FlexE instance num are the same and in the range
                   [1-254]; For 200GBASE-R, each PHY num is in the
                   range [1-126]. For 400GBASE-R, each PHY num is
                   in the range [1-62]. For 50GBASE-R, each PHY num is
                   in the range [1-126].";
              }
              leaf local-phy-interface{
                type if:interface-ref;
                description
                  "Local PHY interface related to the current PHY in a
                   FlexE group.";
              }
              leaf remote-phy-interface{
                type if:interface-ref;
                description
                  "Remote PHY interface related to the current PHY in
                   a FlexE group.";
              }
            }
          }

        container flexe-instances {
          description
            "FlexE instances in a FlexE Group";
          list flexe-instance {
            key flexe-inst-num;
            description
              "List of a FlexE instance in a FlexE Group. Not including
               those unequipped instances in the bonded PHYs.";
            leaf flexe-inst-num{
              type uint8 ;
              description
                "Logical FlexE instance number";
              reference
                "Clause 6.1 FlexE Group in FlexE IA 2.1.
                 For 50G and 100G, instance num=PHY num;
                 For 200G, 8-bit instance num consists of the PHY num
                 in the upper seven bits, and 0 or 1 in the lower order
                 bit.
                 For 400G, 8-bit instance num consists of the PHY num
                 in the upper six bits, and 0,1,2, or 3 in the two
                 lower order bits.  ";
            }
            list unavb-sub-cal-slot-list {
              key sub-cal-slot-id;
              description
                "List of sub-calendar slots unavailable in a FlexE
                 Instance.";
              leaf sub-cal-slot-id {
                type uint8;
                description
                 "Id number of a sub-calendar slot in a FlexE instance.
                  In a 100G FlexE instance,
                  for 5G granularity, the range of slot-id is [0,19];
                  for 25G granularity, the range of slot-id is [0,3];
                  In a 50G FlexE instance,
                  for 5G granularity, the range of slot-id is [0,9];
                  for 25G granularity, the range of slot-id is [0,1];
                  Refer to clause 6.8 in FlexE IA 2.1. ";
              }
            }
          }
          list uneq-flexe-instance {
            key flexe-inst-num;
            description
              "Unequipped FlexE instances in the bonded PHYs.
               Strictly speaking, a unequipped instance does not belong
               to any FlexE Group, because in the overhead frame, the
               FlexE Group number is set to 0x00000.
               Refer to Clause 6.6 Unequipped 100G FlexE Instances in
               FlexE IA 2.1.";
            leaf flexe-inst-num{
              type uint8 ;
              description
                "Clause 6.1 FlexE Group in FlexE IA 2.1";
            }
          }
        }
        leaf expected-group-number {
          type uint32 {
            range 1..1048574 ;
          }
        description
          "The expected FlexE group number is configured at the FlexE
           demux. Its vaule is in the range 1~0xFFFFE.
           Refer to ExGID in G.8023.";
        }
        leaf expected-phy-map {
          type string {
            length "256";
            pattern "[0-1]*";
         }
        description
          "The expected FlexE PHY MAP is configured at the FlexE
           demux. The length of PHY MAP is 8*32=256. If a FlexE PHY
           ( for FlexE IA V1.1) or FlexE instance( for FlexE IA V2.0)
           is configured in the FlexE Group, the corresponding bit is
           set to 1.
           Refer to ExPHYMAP in G.8023.";
        }
        leaf expected-cal-cfg {
          type flexe-tp:calendar-AorB;
          description
            "The expected calendar configuration( ExCC in ITU-T G.8023)
             is configured on FlexE demux.
             Refer to ExCC in G.8023.";
        }
        leaf tx-calendar {
          type flexe-tp:calendar-AorB;
          description
            "Calendar configuration in the transmit direction.
             Refer to TxCC in G.8023. ";
        }
        leaf rx-calendar {
          type flexe-tp:calendar-AorB;
          description
            "Calendar configuration in the receive direction";
        }
        leaf tx-calendar-neg {
          type enumeration {
            enum STATIC-MODE {
              value 1 ;
              description
                "STATIC mode. In this mode, calendar slots on mux and
                 demux need to be configured";
            }
            enum MASTER-SLAVE {
              value 2 ;
              description
                "MASTER-SLAVE mode. In this mode, calendar slots only
                 need to be configured on mux";
            }
          }
          description
            "TX calendar negotiation methods";
        }
        leaf reply-ca-mode {
          type enumeration {
            enum never {
              value 1 ;
              description
                "never reply CA (Configuration Ack)";
            }
            enum immediately {
              value 2 ;
              description
                "immediately reply CA (Configuration Ack)";
            }
            enum ask-controller {
              value 3 ;
              description
                "Ask controller for more control";
            }
          }
          description
            "Reply CA mode";
          }
        }
      }
    }
    container flexe-clients {
      description
        "FlexE clients information";
      list flexe-client {
        key client-number ;
        description
          "Attributes of FlexE client" ;
        leaf client-number {
          type uint16 {
            range 1..65534 ;
          }
          description
            "Client number in the range of 1~0xFFFE.
             The value 0x0000 indicates a calendar slot which is unused
             (but available).
             The value 0xFFFF (all ones) indicates a calendar slot that
             is unavailable.
             Refer to Clause 7.3.4 in FlexE IA 2.1.";
          reference
            "FlexE IA 2.1.";
        }
        container bandwidth {
          description "Client bandwidth";
          uses flexe-tp:flexe-client-bandwidth;
        }
        leaf flexe-group-number {
          type uint32 {
            range 1..1048574 ;
          }
          description
            "The FlexE Group is used to transport the FlexE client.";
        }
        container alloc-slots{
          description
            "Slots are allocated on the mux(Transmit-direction).";
          container tx-alloc-A-slots{
            uses slot-list;
             description
               "Slots in A calendar are allocated on the mux.
                Refer to TxCCA in G.8023.";
          }
          container tx-alloc-B-slots{
            uses slot-list;
             description
               "Slots in B calendar are allocated on the mux.
                Refer to TxCCB in G.8023.";
          }
          choice tx-calendar-neg{
            description
              "According to the mode, to determine what should be
               configured.";
            case STATIC-MODE{
              container rx-alloc-slots{
                uses slot-list;
                description
                  "Slots for a specific FlexE client allocated on the
                   demux(Receive-direction).";
              }
              container rx-expected-A-slots{
                uses slot-list;
                description
                  "The expected received slots for a specific FlexE
                   client in A calendar are configured on the demux.
                   Refer to ExCCA in G.8023.";
                reference
                  "ITU-T G.8023";
              }
             container rx-expected-B-slots{
                uses slot-list;
                description
                  "The expected received slots for a specific FlexE
                   client in B calendar are configured on the demux.
                   Refer to ExCCB in G.8023.";
                reference
                  "ITU-T G.8023";
              }
            }
            case MASTER-SLAVE{

            }
          }
        }

        leaf client-interface {
          type if:interface-ref;
          description
            "A FlexE Client is used as an interface.
             The attributes of the interface can be configured.";
        }
      }
    }
  }
}
