module ietf-rdnm-tunnel {
  yang-version 1.1;
  namespace "urn:ietf:params:xml:ns:yang:ietf-rdnm-tunnel";
  prefix rdnm-tnl;

  import ietf-te {
    prefix "te";
  }

  import ietf-yang-types {
    prefix "yang";
  }

  import ietf-rdnm-types {
    prefix "rdnm-types";
  }  

  import ietf-network {
    prefix "nw";
  }  

  import ietf-network-topology {
    prefix "nt";
  }

  import ietf-te-topology {
    prefix "tet";
  }  

  organization
    "IETF CCAMP Working Group";
  contact
    "WG Web: <http://tools.ietf.org/wg/ccamp/>
     WG List: <mailto:ccamp@ietf.org>

     Editor: Chaode Yu
             <mailto:yuchaode@huawei.com>
             Xing Zhao 
             <mailto:zhaoxing@caict.ac.cn>
             Yanxia Tan
             <mailto:tanyx11@chinaunicom.cn>
             Nigel Davis
             <mailto:ndavis@ciena.com>
             Daniel King
             <mailto:daniel@olddog.co.uk>";

  description
    "This module provide some extensions to TE topology model, based
    on transport Rich-Detail Network Management requirement";

  revision 2025-02-22 {
    description
      "Revision 1.0";
    reference
      "draft-yu-ccamp-rdnm-yang-00";
  }

  augment "/te:te/te:tunnels/te:tunnel" {
    description
      "Extensions for TE tunnel structure, includes alias, time 
      management and another option of specifying source and 
      destination.";

    leaf alias {
      type string;
      description 
        "alias of TE tunnel";
    }

    uses time-state-grouping;

    container source-endpoints {
      description
        "Source endpoints.";
      list source-endpoint {
        uses endpoint-grouping;
        description
          "List of source endpoints.";
      }
    }

    container destination-endpoints {
      description
        "Destination endpoints.";
      list destination-endpoint {
        uses endpoint-grouping;
        description
          "List of destination endpoints.";
      }
    }
  }

  augment  "/te:te/te:tunnels/te:tunnel/te:restoration" {
    description
      "Extensions of TE tunnel restoration.";

    leaf restoration-lock {
      type boolean;

      description
        "a lock to control whether the restoration can take effect or
        not, it is useful in the maintenance scenrios, such as in
        cutover";
    }

    leaf restoration-reversion-lock {
      type boolean;
      description
        "a lock to control whether the reversion of restoration can
        take effect or not.";
    }

    leaf scheduled-reversion-time {
      type yang:date-and-time;

      description
        "a time when the reversion of restoration can take effect.";
    }

    leaf restoration-priority {
      type enumeration {
        enum high;
        enum medium;
        enum low;
      }

      description
        "when there are multiple services need to be restored, the 
        higher estoration priority services can occupied the idle 
        resource in priority, it is used to control the restoration 
        sequence.";
    }

    leaf restoration-layer {
      type enumeration {
        enum odu;
        enum wdm;
      }

      description
        "the layer of topolgy prefered to be operated when restoration
        is needed.";
    }
  }

  augment  "/te:te/te:tunnels/te:tunnel/te:primary-paths"
           + "/te:primary-path/te:explicit-route-objects"
           + "/te:route-object-include-exclude/te:type"    {
    description 
      "a TTP hop";
    case ttp-hop {
      uses rdnm-types:explicit-ttp-hop;
    }
  }

  augment  "/te:te/te:tunnels/te:tunnel/te:secondary-paths"
           + "/te:secondary-path/te:explicit-route-objects"
           + "/te:route-object-include-exclude/te:type"    {
    description 
      "a TTP hop";
    case ttp-hop {
      uses rdnm-types:explicit-ttp-hop;
    }
  }  

  augment  "/te:te/te:tunnels/te:tunnel/te:primary-paths"
           + "/te:primary-path/te:primary-reverse-path"
           + "/te:explicit-route-objects"
           + "/te:route-object-include-exclude/te:type"    {
    description 
      "a TTP hop";
    case ttp-hop {
      uses rdnm-types:explicit-ttp-hop;
    }
  }

  augment  "/te:te/te:tunnels/te:tunnel/te:secondary-reverse-paths"
           + "/te:secondary-reverse-path"
           + "/te:explicit-route-objects"
           + "/te:route-object-include-exclude/te:type"    {
    description 
      "a TTP hop";
    case ttp-hop {
      uses rdnm-types:explicit-ttp-hop;
    }
  }    

  grouping time-state-grouping {
    description
      "time management of TE tunnel.";

    leaf create-time {
      type yang:date-and-time;
      config false;
      description
        "the time when the tunnel was created";

    }

    leaf active-time {
      type yang:date-and-time;
      config false;
      description
        "the lastest time when the tunnel was activated";
    }    
  }

  grouping endpoint-grouping {
    description
      "Source/destination endpoint information of TE tunnel.";

    leaf node-id {
      type leafref {
        path "/nw:networks/nw:network/nw:node/nw:node-id";
      }
      description
        "Identifier of node for this endpoint.";
    }

    choice endpoint-tp {
      description
        "The client can choose to specify LTP or TTP to create TE 
        tunnel.";

      case ltp {
        leaf tp-id {
          type leafref {
            path "/nw:networks/nw:network/nw:node/nt:termination-point"
            + "/nt:tp-id";
          }
          description
            "identifier of LTP for this endpoint.";
        }
      }

      case ttp {
        choice id-or-name {
          description
            "The client can choose to specify the identifier or the 
            name of TTP to create TE tunnel.";

          case id {
            leaf ttp-id {
              type leafref {
                path "/nw:networks/nw:network/nw:node/tet:te"
                + "/tet:tunnel-termination-point/tet:tunnel-tp-id";
              }
              description
                "the identifier of TTP for this endpoint.";
            }
          }

          case name {
            leaf ttp-name {
              type leafref {
                path "/nw:networks/nw:network/nw:node/tet:te"
                + "/tet:tunnel-termination-point/tet:name";
              }
              description
                "the name of TTP for this endpoint.";
            }
          }
        }
      }
    }

    leaf protection-role {
      type enumeration {
        enum work;
        enum protect;
      }
      description
        "role of this endpoint in multipoints scenario";
    }
  }

}
