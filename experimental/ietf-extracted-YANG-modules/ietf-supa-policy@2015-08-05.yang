module ietf-supa-policy { 
  namespace "urn:ietf:params:xml:ns:yang:ietf-supa-policy"; 
  // replace with IANA namespace when assigned 
  prefix policy; 

  import ietf-yang-types { 
    prefix yang; 
  } 
  organization "IETF"; 
  contact 
    "Editor: Maoke Chen"; 
  description 
  "This YANG module defines a component that describing 
  the generic ECA policy data model refining from SGPIM and EPRIM. 
  Terms and Acronyms 
  ";    
  revision 2015-08-05 ; 

  container supa-policy{ 
    description 
    "This defines a Generic ECA policy data model "; 
    leaf supa-policy-name { 
      description  
      "The name of the policy";                                         
      type string; 
      } 
      leaf supa-policy-priority { 
      description 
      "The priority of the defined policy"; 
      type uint8; 
    } 
    container supa-policy-validity-period { 
      description 
      "The valid time of the policy. E.g., the policy will be valid 9am-
       9am daily"; 
      leaf start { 
        type yang:date-and-time; 
         }  
      leaf end { 
        type yang:date-and-time; 
      } 
      leaf duration { 
        type uint32; 
      } 
      leaf periodicity { 
        type enumeration { 
          enum daily {   
          } 
          enum monthly {    
          } 
        } 
      } 
    } 
    container supa-policy-target { 
      description  
      "SUPAPolicyTarget is an abstract class that defines a set of 
      managed objects that may be affected by the actions of a 
      SUPAPolicyStatement."; 
      leaf profileType { 
        description 
        "Which profile the policy will be worked on"; 
        type string; 
      } 
      leaf asDomainName { 
        description 
        "Which domain the policy will be worked on"; 
        type string; 
      } 
      leaf adminSubnetwork { 
        description 
        "Which subnet the policy will be worked on"; 
        type string; 
      } 
      leaf businessTypeName { 
        description 
        "Which business the policy will be worked on"; 
        type string; 
      }   
      choice instanceName  { 
        description 
        "Which instance the policy will be worked on? E.g., a VPN, a flow 
        or a link"; 
        case instanceType { 
          leaf instanceElement{ 
            type empty; 
          } 
        } 
      }   
    } 
    container supa-policy-atomic { 
      description 
      "Define a atomic ECA policy rule"; 
      container supa-ECA-policy-rule { 
        description  
        "A supa-policy-atomic class represents a SUPA ECA Policy Rule 
        that can operate as a single, stand-alone, manageable object. Put 
        another way, a supa-policy-atomic object can NOT be modeled as a 
        set of hierarchical supa-policy-rule objects; if this is required, 
        then a supa-policy-composite object should be used instead.'';   
        leaf policy-rule-deploy-status { 
          type enumeration { 
            enum 0{ 
              description "undefined";        
            } 
            enum 1{ 
              description "deployed and enabled";        
            } 
            enum 2{ 
              description "deployed and in test";        
            } 
            enum 3{ 
              description "deployed but not enabled";        
            } 
            enum 4{ 
              description "ready to be deployed";        
            } 
            enum 5{ 
              description "not deployed";        
            } 
          } 
        } 
        leaf policy-rule-exec-status { 
          type enumeration { 
            enum 0{ 
              description "undefined";        
            } 
            enum 1{ 
              description "executed and SUCEEDED (operational mode)";        
            } 
            enum 2{ 
              description "executed and FAILED (operational mode)";        
            } 
            enum 3{ 
              description "currently executing (operational mode)";        
            } 
            enum 4{ 
              description "executed and SUCEEDED (test mode)";        
            } 
            enum 5{ 
              description "executed and FAILED (test mode)";        
            } 
            enum 6{ 
              description "currently executing (test mode)";        
            } 
          } 
        } 
        container supa-ECA-component{ 
          description 
          "The component defines how the event, condition and action 
          clauses are constructed into policy"; 
          container supa-policy-events { 
            description 
            "An event or a set of events that trigger the evaluation 
            of policy: This is the trigger for the service management 
            application to evaluate if a policy needs to be applied. 
            For example a user action to provision a new VPN service 
            can be an event."; 
            leaf has-policy-events { 
              description 
              "Whether the policy has an event?"; 
              type boolean; 
            } 
          } 
          container supa-policy-conditions { 
            description 
            "A set of conditions that need to be satisfied for the 
            policy to be applicable: This enables service management 
            to select the right policy by validating the conditions 
            against the current network state."; 
            leaf has-policy-conditions { 
              description 
              "Whether the policy has an condition?"; 
              type boolean;  
            } 
            leaf conjunctive-type { 
              description  
              "Define how the condition clauses will be conjuncted, 
              AND or OR"; 
              type enumeration { 
                enum 0 { 
                          description "AND: all the conditions must be 
                          matched"; 
                } 
                enum 1 { 
                          description "OR: one or more of the conditions 
                          are matched"; 
                } 
              } 
            }   
          } 
          container supa-policy-actions { 
            description 
            "A set of actions that should be triggered as part of the 
            policy execution: This enables the service management to 
            provision the service.";  
            leaf action-execution { 
              description 
              "How the actions will be executed";  
              type enumeration{ 
                enum 0 { 
                  description "Single: execute one action"; 
                } 
                enum 1 { 
                          description "Sequenced: execute actions one by 
                          one in sequence"; 
                } 
              } 
            } 
          } 
        } 
      }
