module gen-oam {
  namespace "urn:cisco:params:xml:ns:yang:gen-oam";
  prefix goam;

  import ietf-interfaces {
    prefix if;
  }
  import ietf-yang-types {
    prefix yang;
  }
  import ietf-inet-types {
    prefix inet;
  }

  organization "IETF NETMOD (NETCONF Data Modeling ) Working Group";
  contact
    "Tissa Senevirathne tsenevir@cisco.com";
  description
    "This YANG module defines the generic configuration,
     statistics and rpc for OAM to be used within IETF in
     a protocol indpendent manner. Functional level
     abstraction is indendent with YANG modeling. It is
     assumed that each protocol maps corresponding
     abstracts to its native format.
     Each protocoal may extend the YANG model defined
     here to include protocol specific extensions";

  revision 2014-04-17 {
    description
      "Initial revision. - 02 version";
    reference "draft-tissa-netmod-oam";
  }

  identity technology-types {
    description
      "this is the base identity of technology types which are
       vpls, nvo3, TRILL, ipv4, ipv6, mpls";
  }

  identity ipv4 {
    base technology-types;
    description
      "technology of ipv4";
  }

  identity ipv6 {
    base technology-types;
    description
      "technology of ipv6";
  }

  identity command-sub-type {
    description
      "defines different rpc command subtypes, e.g rfc792 ping
       vs udp ping, this is optional for most cases";
  }

  identity icmp-rfc792 {
    base command-sub-type;
    description
      "Defines the command subtypes for ICMP ping";
    reference "RFC 792";
  }

  typedef MEP-direction {
    type enumeration {
      enum "Up" {
        value 0;
      }
      enum "Down" {
        value 1;
      }
    }
  }

  typedef MEP-id {
    type uint32 {
      range "1..8191";
    }
    description
      "Defines type for MEPIDm range is 1..8191";
  }

  typedef CCM-Interval {
    default "interval-1min";
    type enumeration {
      enum "interval-invalid" {
        value 0;
      }
      enum "interval-300hz" {
        value 1;
      }
      enum "interval-10ms" {
        value 2;
      }
      enum "interval-100ms" {
        value 3;
      }
      enum "interval-1s" {
        value 4;
      }
      enum "interval-10s" {
        value 5;
      }
      enum "interval-1min" {
        value 6;
      }
      enum "interval-10min" {
        value 7;
      }
    }
    reference
      "802.2Q Rev5 or 802.ag, all of the above
       are standard enumeration from the 802.1Q";
    description
      "IntervalInvalid - value 0
       Interval300Hz - Value 1
       Intervale10ms - value 2
       Interval100ms - value3
       Interval1s    - value 4
       Interval10s  - value 5
       Interval1min - value 6
       Interval10min - value 7";
  }

  typedef ecmp-choices {
    type enumeration {
      enum "ecmp-use-platform-hash" {
        value 0;
      }
      enum "ecmp-use-round-robin" {
        value 1;
      }
    }
  }
  typedef MD-name-format {
    type enumeration {
      enum "ieee-reserved" {
        value 0;
      }
      enum "none" {
        value 1;
      }
      enum "dns-like-name" {
        value 2;
      }
      enum "mac-address-and-uint" {
        value 3;
        reference "802.1Q Rev5";
        description
          "Domain name 3 specifies domain name is mac-address + 2
octets.";
      }
    }
    reference "802.1Q";
    description
      "defines the domain name format";
  }

  typedef MA-name-format {
    type enumeration {
      enum "ieee-reserved" {
        value 0;
      }
      enum "primary-vid" {
        value 1;
      }
      enum "char-string" {
        value 2;
      }
      enum "unsigned-int16" {
        value 3;
      }
      enum "rfc2865-vpnid" {
        value 4;
      }
    }
    reference "802.1Q";
    description
      "Defines Format of MA-names";
  }
  typedef oam-counter32 {
    type yang:zero-based-counter32;
    description
      "defines 32 bit counter for OAM";
  }

  grouping mep-address {
    choice mep-address {
      case mac-address {
        leaf mac-address {
          type yang:mac-address;
        }
      }
      case ipv4-address {
        leaf ipv4-address {
          type inet:ipv4-address;
        }
      }
      case ipv6-address {
        leaf ipv6-address {
          type inet:ipv6-address;
        }
      }
    }
  }

  grouping maintenance-domain {
    status current;
    description
      "Defines the MA-domain group";
    reference "802.1Q Rev5";
    leaf technology {
      mandatory true;
      status current;
      type identityref {
        base technology-types;
      }
      description
        "Defines the technology";
    }
    leaf md-name-format {
      mandatory true;
      status current;
      description
        "Defines the maintenance domain name";
      type MD-name-format;
      reference "802.1Q Rev5";
    }
    leaf md-name {
      status current;
      description
        "Defines the MA-Domain name. This is a binary (octet) string
         of 43 bytes";
      type binary {
        length "1..43";
      }
      reference "802.1Q Rev5";
    }
    leaf md-level {
      mandatory true;
      status current;
      description
        "Defines the MD-Level";
      type int32 {
        range "0..7";
      }
      reference "802.1Q Rev5 or 802.1ag";
    }
  }

  grouping ma-identifier {
    description
      "ma-identifier defines MAID parameters as defined in 8021Q";
    reference "IEEE 802.1Q Rev5";
    leaf ma-name-format {
      mandatory true;
      status current;
      description
        "This defines the MA name format 1 is no format,
         2 - dnslikename, 3- macaddress 4-CharString";
      type MA-name-format;
      reference "IEEE 802.1Q Rev 5";
    }
    leaf ma-name {
      mandatory true;
      description
        "Define the MA-Name according to the specified format.
         This is 43 byte string.";
      type binary {
        length "1..45";
      }
      reference "802.1Q Rve 5 or 8021ag Clause 21.6.5";
    }
  }

  grouping MEP {
    status current;
    description
      "Defines elements withing the MEP";
    reference "802.1Q Rev5";
    leaf mep-id {
      mandatory true;
      status current;
      description
        "Assigm MEPID in the range of 1..8191";
      type MEP-id {
        range "1..8191";
      }
      reference "802.1Q Rev5";
    }
    leaf mep-name {
      type string;
      description
        "Defines textual name for MEP. This is not specified in IEEE
but
         defined in IETF OAM for ease of use";
    }
    leaf mep-direction {
      type MEP-direction;
      mandatory true;
    }
    leaf ccm-Tx-enable {
      type boolean;
      default "false";
    }
    uses mep-address;
    uses context-id;
    leaf Interface {
      type if:interface-ref;
      description
        "Interface name as defined by ietf-interfaces";
    }
  }

  grouping CCM-defect-stats {
    description
      "Contains all of  the CCM related defect stats";
    leaf ccm-rdi-indicator {
      config false;
      type boolean;
      description
        "True indicate one or more of the MEP have seen RDI
         flag set from remote MEP";
    }
    leaf ccm-xcon-count {
      config false;
      type oam-counter32;
      description
        "Number of times cross connect errors are seen";
    }
    leaf ccm-xcon-Indicator {
      config false;
      type boolean;
      description
        "There is currently cross connect error seen since last
         clearing of the variable";
    }
  }

  grouping monitor-stats {
    leaf tx-packt-count {
      type oam-counter32;
      description
        "Transmitted Packet count";
    }
    leaf rx-packet-count {
      type oam-counter32;
      description
        "Received packet count";
    }
    leaf min-delay {
      units "milliseconds";
      type oam-counter32;
      description
        "Delay is specified in milliseconds";
    }
    leaf average-delay {
      units "milliseconds";
      type oam-counter32;
      description
        "average delay in milliseconds";
    }
    leaf max-delay {
      type oam-counter32;
      units "millisecond";
    }
  }
  grouping MIP {
    description
      "defines MIP";
    leaf interface {
      type if:interface-ref;
    }
    leaf direction {
      type MEP-direction;
    }
  }

  grouping nested-oam-layer {
    leaf offset {
      type int8 {
        range "1..7";
      }
      description
        "defines nested OAM layer offset
         +1 is the layer immediatly above
         -1 is the layer immediatly below";
    }
    uses maintenance-domain;
    uses ma-identifier;
  }

  grouping interface-status {
    description
      "collection of interface related status";
    leaf admin-status {
      config false;
      type leafref {
        path "/if:interfaces-state/if:interface/if:admin-status";
      }
      description
        "oper status from ietf-interface module";
    }
    leaf oper-status {
      config false;
      type leafref {
        path "/if:interfaces-state/if:interface/if:oper-status";
      }
      description
        "oper status from ietf-interface module";
    }
  }
  grouping context-id {
    description
      "grouping for context id, this will be augmented
       by others who use this component";
    choice context-id {
      default "context-null";
      case context-null {
        description
          "this is a place holder when no context is needed";
        leaf context-null {
          type empty;
          description
            "there is no context define";
        }
      }
    }
  }

  grouping flow-entropy {
    description
      "defines the grouping statement for flow-entropy";
    choice flow-entropy {
      case flow-entropy-null;
    }
  }

  container domains {
    status current;
    config true;
    description
      "Contains configuration related data. Within the container
       is list of fault domains. Wihin each domian has List of MA.";
    list domain {
      uses maintenance-domain {
        status current;
      }
      key "md-name technology";
      ordered-by system;
      status current;
      config true;
      description
        "Define the list of Domains within the IETF-OAM";
      container MAs {
        presence
          "Indicates creation of MA within the Domain
           There can be more than one MA within a specified domain";
        status current;
        config true;
        description
          "This container defines MA, within that have multiple MA
           and within MA have MEP, MIP";
        list MA {
          ordered-by system;
          status current;
          config true;
          key "ma-name";
          uses ma-identifier;
          uses context-id;
          leaf ccm-Interval {
            default "interval-invalid";
            description
              "Defines CCM Interval 0- Means disable
               1 - CCM are sent 3 1/3 ms
               2 - CCM are sent every 10 ms
               3- CCM are sent every 100 ms
               4- CCM are sent every 1 s
               5 - CCM are sent every 10 s
               6 - CCM are sent every 1 minute
               7- CCM are sent every 10 mins";
            type CCM-Interval;
            reference "802.1Q Rev5 and 802.1ag";
          }
          leaf ccm-loss-threshold {
            default "3";
            type uint32;
            description
              "number of consecutive CCM messages missed before
               declaring RDI fault. This is monitored per each
               remote MEP";
          }
          leaf ccm-ttl {
            type uint8;
            default "255";
          }
          uses flow-entropy;
          list MEP {
            key "mep-id";
            ordered-by system;
            status current;
            config true;
            description
              "contain list of MEPS";
            uses MEP {
              status current;
            }
            uses interface-status {
              description
                "status of associated interface";
            }
            uses flow-entropy;
            list session {
              key "user-cookie destination-mepid";
              ordered-by user;
              config true;
              description
                "per session basis create the monitoring";
              leaf user-cookie {
                config true;
                type uint32;
                description
                  "user need to specify some cookie to identify
                   multiple sessions between two MEPs";
              }
              leaf ttl {
                config true;
                type uint8;
                default "255";
              }
              leaf interval {
                units "milliseconds";
                default "1000";
                type uint32;
                description
                  "In milli seconds. 0 means continous";
              }
              leaf enable {
                default "false";
                config true;
                type boolean;
                description
                  "enable or disable a monitor session";
              }
              leaf ecmp-choice {
                config true;
                type ecmp-choices;
                description
                  "0 means use the specified interface
                   1 means use round robin";
              }
              leaf destination-mepid {
                type MEP-id;
              }
              container destination-mep-address {
                uses mep-address;
              }
              uses CCM-defect-stats;
              uses context-id;
              uses flow-entropy;
              list outgoing-interface {
                config true;
                key "interface";
                leaf interface {
                  type leafref {
                    path "/if:interfaces/if:interface/if:name";
                  }
                  config true;
                }
              }
            }
          }
          list remote-MEP {
            key "mep-id";
            ordered-by system;
            status current;
            config true;
            description
              "list all of the remote MEP within the MA";
            leaf mep-id {
              mandatory true;
              status current;
              description
                "Assigm MEPID in the range of 1..8191";
              config true;
              type uint32;
              reference "802.1Q Rev5";
            }
            uses mep-address;
            leaf mep-name {
              type string;
              description
                "Defines textual name for MEP. This is not
                 specified in IEEE but defined in IETF OAM
                 for ease of use";
            }
            leaf ccm-rx-error-count {
              type oam-counter32;
              description
                "counts number of CCM packets that was
                 expected but not received";
            }
          }
          list MIP {
            key "interface direction";
            uses MIP;
          }
          uses CCM-defect-stats {
            description
              "CCM defect stats capture at MA level
               This will contain aggregrate stats from all MEP";
          }
          list nested-oam-layer {
            key "offset";
            description
              "List of OAM layers above and below that are related to
               current MA. This allow users to easily navigate up and
down
               to effeciently troubleshoot a connectivity issue";
            uses nested-oam-layer;
          }
        }
      }
    }
  }
  notification CCM-RDI-notification {
    description
      "When RDI is received this notificiation is sent";
    leaf mep-id {
      type MEP-id;
      description
        "Indicate which MEP is seeing the error";
    }
    leaf remote-mepid {
      type MEP-id;
      description
        "Who is seeing the error (if known) if unknown make it 0.";
    }
    leaf error-message {
      type string {
        length "0..255";
      }
      description
        "Error message to indicate more details.";
    }
  }
  rpc ping {
    description
      "Generates Ping and return response";
    input {
      uses maintenance-domain {
        description
          "Specifies the MA-domain";
      }
      uses ma-identifier {
        description
          "identfies the Maintenance association";
      }
      uses context-id;
      uses flow-entropy;
      leaf ttl {
        type uint8;
        default "255";
      }
      leaf ecmp-choice {
        type ecmp-choices;
        description
          "0 means use the specified interface
           1 means use round robin";
      }
      leaf sub-type {
        type identityref {
          base command-sub-type;
        }
        description
          "defines different command types";
      }
      list outgoing-interfaces {
        key "interface";
        leaf interface {
          type if:interface-ref;
        }
      }
      container source-mep {
        uses mep-address;
        leaf mep-id {
          type MEP-id;
        }
      }
      container destination-mep {
        uses mep-address;
        leaf mep-id {
          type MEP-id;
        }
      }
    }
    output {
      uses monitor-stats {
        description
          "Stats of Ping is same as that of monitor sessions";
      }
    }
  }
  rpc trace-route {
    description
      "Generates Trace-route and return response. Starts with TTL
       of one and increment by one at each hop. Untill destination
       reached or TTL reach max valune";
    input {
      uses maintenance-domain {
        description
          "Specifies the MA-domain";
      }
      uses ma-identifier {
        description
          "identfies the Maintenance association";
      }
      uses context-id;
      uses flow-entropy;
      leaf ttl {
        type uint8;
        default "255";
      }
      leaf command-sub-type {
        type identityref {
          base command-sub-type;
        }
        description
          "defines different command types";
      }
      leaf ecmp-choice {
        type ecmp-choices;
        description
          "0 means use the specified interface
           1 means use round robin";
      }
      list outgoing-interfaces {
        key "interface";
        leaf interface {
          type if:interface-ref;
        }
      }
      container source-mep {
        uses mep-address;
        leaf mep-id {
          type MEP-id;
        }
      }
      container destination-mep {
        uses mep-address;
        leaf mep-id {
          type MEP-id;
        }
      }
    }
    output {
      list response {
        key "ttl";
        leaf ttl {
          type uint8;
        }
        container destination-mep {
          uses mep-address;
          leaf mep-id {
            type MEP-id;
          }
        }
        uses monitor-stats;
      }
    }
  }
}
