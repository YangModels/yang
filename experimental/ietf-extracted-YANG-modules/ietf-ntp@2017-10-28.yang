module ietf-ntp {

  namespace "urn:ietf:params:xml:ns:yang:ietf-ntp";

  prefix "ntp";

  import ietf-yang-types {
    prefix "yang";
  }

  import ietf-inet-types {
    prefix "inet";
  }

  import ietf-interfaces {
    prefix "if";
  }

  import iana-crypt-hash {
    prefix ianach;
  }

  import ietf-key-chain {
    prefix "key-chain";
  }

  import ietf-access-control-list {
    prefix "acl";
  }

  import ietf-routing-types {
    prefix "rt-types";
  }

  organization
    "IETF NTP (Network Time Protocol) Working Group";

  contact
    "WG Web:  <http://tools.ietf.org/wg/ntp/>
     WG List:  <mailto: ntpwg@lists.ntp.org
     WG Chair: Karen O'Donoghue
               <mailto: odonoghue@isoc.org>
     Editor:   Eric Wu
               <mailto:eric.wu@huawei.com>
     Editor:   Anil Kumar S N
               <mailto:anil.ietf@gmail.com>
     Editor:   Yi Zhao
               <mailto:yi.z.zhao@ericsson.com>
     Editor:   Dhruv Dhody
               <mailto:dhruv.ietf@gmail.com>
     Editor:   Ankit Kumar Sinha
               <mailto:ankit.ietf@gmail.com>";
  description
    "This YANG module defines essential components for the
     management of a routing subsystem.

     Copyright (c) 2017 IETF Trust and the persons identified
     as authors of the code. All rights reserved.

     Redistribution and use in source and binary forms,
     with or without modification, is permitted pursuant to,
     and subject to the license terms contained in, the
     Simplified BSD License set forth in Section 4.c of the
     IETF Trust's Legal Provisions Relating to IETF Documents
     (http://trustee.ietf.org/license-info).

     This version of this YANG module is part of RFC XXXX;
     see the RFC itself for full legal notices.";

  revision 2017-10-28 {
    description
      "Updated revision.";
    reference
      "RFC XXXX: A YANG Data Model for NTP Management";
  }

  /* Typedef Definitions */

  typedef ntp-stratum {
    type uint8 {
      range "1..16";
    }
    description
      "The level of each server in the hierarchy is defined by
      a stratum number. Primary servers are assigned stratum
      one; secondary servers at each lower level are assigned
      stratum numbers one greater than the preceding level";
  }

  typedef ntp-version {
    type uint8 {
      range "1..4";
    }
    default "3";
    description
      "The current NTP version supported by corresponding
      association.";
  }

  typedef ntp-minpoll {
    type uint8 {
      range "4..17";
    }
    default "6";
    description
      "The minimum poll exponent for this NTP association.";
  }

  typedef ntp-maxpoll {
    type uint8 {
      range "4..17";
    }
    default "10";
    description
      "The maximul poll exponent for this NTP association.";
  }

  typedef access-modes {
    type enumeration {
      enum peer {
        value "0";
        description
          "Sets the fully access authority. Both time
          request and control query can be performed
          on the local NTP service, and the local clock
          can be synchronized to the remote server.";
      }
      enum server {
        value "1";
        description
          "Enables the server access and query.
          Both time requests and control query can be
          performed on the local NTP service, but the
          local clock cannot be synchronized to the
          remote server.";
      }
      enum synchronization {
        value "2";
        description
          "Enables the server to access.
          Only time request can be performed on the
          local NTP service.";
      }
      enum query {
        value "3";
        description
          "Sets the maximum access limitation.
          Control query can be performed only on the
          local NTP service.";
      }
    }
    description
      "This defines NTP acess modes.";
  }

  typedef unicast-configuration-type {
    type enumeration {
      enum server {
        value "0";
        description
          "Use client association mode. This device
          will not provide synchronization to the
          configured NTP server.";
      }
      enum peer {
        value "1";
        description
          "Use symmetric active association mode.
          This device may provide synchronization
          to the configured NTP server.";
      }
    }
    description
      "This defines NTP unicast mode of operation.";
  }

  typedef association-modes {
    type enumeration {
      enum client {
        value "0";
        description
          "Use client association mode(mode 3).
          This device will not provide synchronization
          to the configured NTP server.";
      }
      enum active {
        value "1";
        description
          "Use symmetric active association mode(mode 1).
          This device may synchronize with its NTP peer,
          or provide synchronization to configured NTP peer.";
      }
      enum passive {
        value "2";
        description
          "Use symmetric passive association mode(mode 2).
          This device has learnt this asso dynamically.
          This device may synchronize with its NTP peer.";
      }
      enum broadcast {
        value "3";
        description
          "Use broadcast mode(mode 5).
          This mode defines that its eigther working
          as broadcast-server or multicast-server.";
      }
      enum broadcast-client {
        value "4";
        description
          "This mode defines that its eigther working
          as broadcast-client or multicast-client.";
      }
    }
    description
      "This defines NTP association modes.";
  }

  typedef ntp-clock-status {
    type enumeration {
      enum synchronized {
        value "0";
        description
          "Indicates that the local clock has been
          synchronized with an NTP server or
          the reference clock.";
      }
      enum unsynchronized {
        value "1";
        description
          "Indicates that the local clock has not been
          synchronized with any NTP server.";
      }
    }
    description
      "This defines NTP clock status.";
  }

  typedef ntp-sync-state {
    type enumeration {
      enum clock-not-set {
        value "0";
        description
          "Indicates the clock is not updated.";
      }
      enum freq-set-by-cfg {
        value "1";
        description
          "Indicates the clock frequency is set by
          NTP configuration.";
      }
      enum clock-set {
        value "2";
        description
          "Indicates the clock is set.";
      }
      enum freq-not-determined {
        value "3";
        description
          "Indicates the clock is set but the frequency
          is not determined.";
      }
      enum clock-synchronized {
        value "4";
        description
          "Indicates that the clock is synchronized";
      }
      enum spike {
        value "5";
        description
          "Indicates a time difference of more than 128
          milliseconds is detected between NTP server
          and client clock. The clock change will take
          effect in XXX seconds.";
      }
    }
    description
      "This defines NTP clock sync states.";
  }

  /* Groupings */
  grouping authentication-key {
    description
      "To define an authentication key for a Network Time
      Protocol (NTP) time source.";
    leaf key-id {
      type uint32 {
        range "1..max";
      }
      description
        "Authentication key identifier.";
    }
    leaf algorithm {
      type identityref {
        base key-chain:crypto-algorithm;
      }
      description
        "Authentication algorithm.";
    }
    leaf password {
      type ianach:crypt-hash;
      description "Clear or encrypted mode for password text.";
    }
  }

  grouping authentication-type-param {
    description
        "Authentication type.";
    choice authentication-type {
      description
        "Type of authentication.";
      case symmetric-key {
        leaf key-id {
          type leafref {
            path "/ntp:ntp/ntp:authentication/"
            + "ntp:authentication-keys/ntp:key-id";
          }
          description
            "Authentication key id referenced in this
            association.";
        }
      }
    }
  }

  grouping statistics {
    description
      "NTP packet statistic.";
    leaf packet-sent {
      type yang:counter32;
      description
        "Indicates the total number of packets sent.";
    }
    leaf packet-sent-fail {
      type yang:counter32;
      description
        "Indicates the number of times packet
        sending failed.";
    }
    leaf packet-received {
      type yang:counter32;
      description
        "Indicates the total number of packets received.";
    }
    leaf packet-dropped {
      type yang:counter32;
      description
        "Indicates the number of packets dropped.";
    }
  }

  grouping comman-attributes {
    description
      "NTP common attributes for configuration.";
    leaf minpoll {
      type ntp-minpoll;
      description
        "The minimum poll interval used in this association.";
    }
    leaf maxpoll {
      type ntp-maxpoll;
      description
        "The maximul poll interval used in this association.";
    }
    leaf port {
      type uint16 {
        range "123 | 1025..max";
      }
      default "123";
      description
        "Specify the port used to send NTP packets.";
    }
    leaf version {
      type ntp-version;
      description
        "NTP version.";
    }
  }

  grouping association-ref {
    description
      "Reference to NTP association node";
    leaf associations-address {
        type leafref {
            path "/ntp:ntp/ntp:associations/ntp:address";
        }
        description
          "Indicates the association address
          which result in clock synchronization.";
    }
    leaf associations-local-mode {
        type leafref {
            path "/ntp:ntp/ntp:associations/ntp:local-mode";
        }
        description
          "Indicates the association local-mode
          which result in clock synchronization.";
    }
    leaf associations-isConfigured {
        type leafref {
            path "/ntp:ntp/ntp:associations/ntp:isConfigured";
        }
        description
          "Indicates the association was configured or dynamic
          which result in clock synchronization.";
    }
  }

  /* Configuration data nodes */
  container ntp {
    presence
      "NTP is enable";
    description
      "Configuration parameters for NTP.";
    leaf port {
      type uint16 {
        range "123 | 1025..max";
      }
      default "123";
      description
        "Specify the port used to send NTP packets.";
    }

 container refclock-master {
   presence
      "NTP master clock is enable";
   description
     "Configures the device as NTP server.";
      leaf master-stratum {
        type ntp-stratum;
        default "16";
        description
          "Stratum level from which NTP
          clients get their time synchronized.";
   }
 }
 container authentication {
   description
      "Configuration of authentication.";
      leaf auth-enabled {
        type boolean;
        default false;
        description
          "Controls whether NTP authentication is enabled
          or disabled on this device.";
      }
      list trusted-keys {
        key "key-id";
        description
          "List of keys trusted by NTP.";
        leaf key-id {
          type leafref {
            path "/ntp:ntp/ntp:authentication/"
                + "ntp:authentication-keys/ntp:key-id";
          }
          description
          "The key trusted by NTP.";
        }
      }
      list authentication-keys {
        key "key-id";
        uses authentication-key;
        description
          "List of authentication key.";
      }
 }

 container access-rules {
   description
     "Configuration of access rules.";
      list access-rule {
        key "access-mode";
        description
          "List of access rules.";
        leaf access-mode {
          type access-modes;
          description
            "NTP access mode.";
         }
        leaf acl {
          type leafref {
           path "/acl:access-lists/acl:acl/acl:acl-name";
          }
          description
            "NTP ACL.";
         }
       }
 }

 container clock-state {
   config "false";
   description
     "Operational state of the NTP.";

   container system-status {
     description
        "System status of NTP.";
     leaf clock-state {
       type ntp-clock-status;
       mandatory true;
       description "Indicates the state of system clock.";
     }
     leaf clock-stratum {
         type ntp-stratum;
         mandatory true;
         description
           "Indicates the stratum of the reference clock.";
     }
     leaf clock-refid {
         type union {
             type inet:ipv4-address;
             type binary {
                 length "4";
             }
             type string {
                 length "4";
             }
         }
         mandatory true;
         description
           "IPv4 address or first 32 bits of the MD5 hash of
           the IPv6 address or reference clock of the peer to
           which clock is synchronized.";
     }
     uses association-ref {
       description
         "Reference to Association node";
     }
     leaf nominal-freq {
         type decimal64 {
             fraction-digits 4;
         }
         mandatory true;
         description
           "Indicates the nominal frequency of the
           local clock, in Hz.";
     }
     leaf actual-freq {
         type decimal64 {
             fraction-digits 4;
         }
         mandatory true;
         description
           "Indicates the actual frequency of the
           local clock, in Hz.";
     }
     leaf clock-precision {
         type uint8;
         mandatory true;
         description
           "Precision of the clock of this system
           in Hz.(prec=2^(-n))";
     }
     leaf clock-offset {
         type decimal64 {
             fraction-digits 4;
         }
         description
           "Offset of clock to synchronized peer,
           in milliseconds.";
     }
     leaf root-delay {
         type decimal64 {
             fraction-digits 2;
         }
         description
           "Total delay along path to root clock,
           in milliseconds.";
     }
     leaf root-dispersion {
         type decimal64 {
             fraction-digits 2;
         }
         description
           "Indicates the dispersion between the local clock
           and the master reference clock, in milliseconds.";
     }
     leaf reference-time {
         type yang:date-and-time;
         description
           "Indicates reference timestamp.";
     }
     leaf sync-state {
       type ntp-sync-state;
       mandatory true;
       description
         "Indicates the synchronization status of
         the local clock.";
     }
   }
 }

 list unicast {
   key "address type";
   description
     "list of unicast configuration.";
   leaf address {
     type inet:host;
     description
       "The address of this association.";
   }
   leaf type {
     type unicast-configuration-type;
     description
       "Type for this NTP configuration";
   }
   container authentication{
     description
       "Authentication type.";
     uses authentication-type-param;
   }
   leaf prefer {
     type boolean;
     default "false";
     description
       "Whether this association is preferred.";
   }
   leaf burst {
     type boolean;
     default "false";
     description
       "Sends a series of packets instead of a single packet
       within each synchronization interval to achieve faster
       synchronization.";
   }
   leaf iburst {
     type boolean;
     default "false";
     description
       "Sends a series of packets instead of a single packet
       within the initial synchronization interval to achieve
       faster initial synchronization.";
   }
   leaf source {
     type if:interface-ref;
     description
       "The interface whose ip address this association used
       as source address.";
   }
   uses comman-attributes {
     description
       "Common attribute like port, version, min and max poll.";
   }
 }

 list associations {
   key "address local-mode isConfigured";
   config "false";
   description
     "list of NTP association.";
   leaf address {
     type inet:host;
     description
       "The address of this association.";
   }
   leaf local-mode {
     type association-modes;
     description
       "Local mode for this NTP association.";
   }
   leaf isConfigured {
     type boolean;
     description
       "Whether this association is configured or dynamically learnt.";
   }
   leaf stratum {
     type ntp-stratum;
     description
       "Indicates the stratum of the reference clock.";
   }
   leaf refid {
     type union {
       type inet:ipv4-address;
       type binary {
         length "4";
       }
       type string {
         length "4";
       }
     }
     description
       "Reference clock type or address for the peer.";
   }
   leaf authentication{
     type leafref {
       path "/ntp:ntp/ntp:authentication/"
           + "ntp:authentication-keys/ntp:key-id";
     }
     description
       "Authentication Key used for this association.";
   }
   leaf prefer {
     type boolean;
     default "false";
     description
       "Whether this association is preferred.";
   }
   leaf peer-interface {
     type if:interface-ref;
     description
       "The interface which is used for communication.";
   }
   uses comman-attributes {
     description
       "Common attribute like port, version, min and max poll.";
   }
   leaf reach {
     type uint8;
     description
        "Indicates the reachability of the configured
        server or peer.";
   }
   leaf unreach {
     type uint8;
     description
       "Indicates the unreachability of the configured
       server or peer.";
   }
   leaf poll {
     type uint8;
     description
       "Indicates the polling interval for current,
       in seconds.";
   }
   leaf now {
     type uint32;
     description
       "Indicates the time since the NTP packet was
       not received or last synchronized, in seconds.";
   }
   leaf offset {
     type decimal64 {
       fraction-digits 4;
     }
     description
       "Indicates the offset between the local clock
       and the superior reference clock.";
   }
   leaf delay {
     type decimal64 {
       fraction-digits 2;
     }
     description
       "Indicates the delay between the local clock
       and the superior reference clock.";
   }
   leaf dispersion {
     type decimal64 {
       fraction-digits 2;
     }
     description
       "Indicates the dispersion between the local
       clock and the superior reference clock.";
   }
   leaf originate-time {
     type yang:date-and-time;
     description
       "Indicates packet originate timestamp(T1).";
   }
   leaf receive-time {
     type yang:date-and-time;
     description
       "Indicates packet receive timestamp(T2).";
   }
   leaf transmit-time {
     type yang:date-and-time;
     description
       "Indicates packet transmit timestamp(T3).";
   }
   leaf input-time {
     type yang:date-and-time;
     description
       "Indicates packet input timestamp(T4).";
   }
   container ntp-statistics {
     description
       "Per Peer packet send and receive statistic.";
     uses statistics {
         description
           "NTP send and receive packet statistic.";
     }
   }
 }

 container interfaces {
   description
     "Configuration parameters for NTP interfaces.";
   list interface {
     key "name";
     description
       "List of interfaces.";
     leaf name {
           type if:interface-ref;
           description
             "The interface name.";
     }

     container broadcast-server {
       presence
         "NTP broadcast-server is configured";
       description
         "Configuration of broadcast server.";
       leaf ttl {
         type uint8;
         description
           "Specifies the time to live (TTL) of a
           broadcast packet.";
       }
       container authentication{
         description
           "Authentication type.";
           uses authentication-type-param;
       }
       uses comman-attributes {
         description
           "Common attribute like port, version, min and max poll.";
       }
     }

     container broadcast-client {
       presence
         "NTP broadcast-client is configured";
       description
         "Configuration of broadcast-client.";
     }

     list multicast-server {
       key "address";
       description
         "Configuration of multicast server.";
       leaf address {
          type rt-types:ip-multicast-group-address;
          description
            "The IP address to send NTP multicast packets.";
       }
       leaf ttl {
         type uint8;
         description
           "Specifies the time to live (TTL) of a
           multicast packet.";
       }
       container authentication{
         description
           "Authentication type.";
           uses authentication-type-param;
       }
       uses comman-attributes {
         description
           "Common attribute like port, version, min and max poll.";
       }
     }
     list multicast-client {
       key "address";
       description
         "Configuration of multicast-client.";
       leaf address {
         type rt-types:ip-multicast-group-address;
         description
           "The IP address of the multicast group to join.";
       }
     }
     list manycast-server {
       key "address";
       description
            "Configuration of manycast server.";
       leaf address {
         type rt-types:ip-multicast-group-address;
         description
           "The multicast group IP address to receive
           manycast client messages .";
       }
     }
     list manycast-client {
       key "address";
       description
         "Configuration of manycast-client.";
       leaf address {
         type rt-types:ip-multicast-group-address;
         description
           "The group IP address that the manycast client
           broadcasts the request message to.";
       }
       container authentication{
         description
           "Authentication type.";
           uses authentication-type-param;
       }
       leaf ttl {
         type uint8;
         description
           "Specifies the maximum time to live (TTL) for
           the expanding ring search.";
       }
       leaf minclock {
         type uint8;
         description
           "The minimum manycast survivors in this
           association.";
       }
       leaf maxclock {
         type uint8;
         description
           "The maximum manycast candidates in this
           association.";
       }
       leaf beacon {
         type uint8;
         description
           "The maximum interval between beacons in this
           association.";
       }
       uses comman-attributes {
         description
           "Common attribute like port, version, min and max poll.";
       }
     }
    }
   }
   /* Operational state data */

   container ntp-statistics {
     config "false";
     description
       "Total NTP packet statistic.";
     uses statistics {
         description
           "NTP send and receive packet statistic.";
     }
   }
 }
}
