module ietf-segmented-vpn {
    namespace "urn:ietf:params:xml:ns:yang:ietf-segmented-vpn" ;
    prefix svpn;
    import ietf-yang-types {
        prefix yang;
    }
    import ietf-inet-types {
        prefix inet;
    }
    organization "IETF OPSAWG Working Group";
    contact "
        WG Web:   <https://datatracker.ietf.org/wg/opsawg>
        WG List:  <mailto:netmod@ietf.org>

        Editor:   Roni Even
                  <mailto:roni.even@huawei.com>
                  Qin Wu
                  <mailto:bill.wu@huawei.com>
                  Cheng Ying
                  <mailto:chengying10@chinaunicom.cn>";
    description
     "This YANG module defines a generic service configuration
     model for Composed VPNs. This model is common across all
     vendor implementations.";
    revision 2018-08-21 {
        reference "draft-opsawg-evenwu-yang-composed-vpn-00";
    }
 typedef edge-role {
        type enumeration {
            enum nop {
                description "nop";
            }
            enum pe {
                description "PE";
            }
            enum p {
                description "P";
            }
            enum uni {
                description "UNI";
            }
            enum nni {
                description "NNI";
            }
            enum asbtp {
                description "AsbTP";
            }
        }
        description "Edge Point Role.";
    }
  typedef topo-role {
        type enumeration {
            enum hub {
                description "hub";
            }
            enum spoke {
                description "spoke";
            }
           enum other {
                description "other";
            }
        }
        description "Topo Node Role.";
    }
    typedef protection-role {
        type enumeration {
            enum nop{
                description "NOP";
            }
            enum main{
                description "MAIN";
            }
        }
        description "Protection Role.";
    }
 typedef qos-config-type {
        type enumeration {
            enum nop{
                description "nop.";
            }
            enum template{
                description "standard.";
            }
            enum agile{
                description "custom.";
            }
        }
        description "Qos Config Type.";
    }
    typedef qos-sub-type {
        type enumeration {
            enum nop{
                description "nop";
            }
            enum car{
                description "CAR";
            }
            enum qosProfile{
                description "Qos Profile";
            }
            enum diffservdomain{
                description "diffServDomain";
            }
            enum diffserv{
                description "diffServ";
            }
        }
        description "Qos Detail Type";
    }
 typedef tp-type{
        type enumeration {
            enum nop {
                description "nop";
            }
            enum ptp {
                description "PTP";
            }
            enum ctp {
                description "CTP";
            }
            enum trunk {
                description "TRUNK";
            }
            enum loopback {
                description "LoopBack";
            }
            enum tppool {
                description "TPPool";
            }
        }
        description "Tp Type.";
    }
 typedef layer-rate{
        type enumeration {
            enum lr-unknow {
                description "Layer Rate UNKNOW.";
            }
            enum lr-ip {
                description "Layer Rate IP.";
            }
            enum lr-eth {
                description "Layer Rate Ethernet.";
            }
            enum lr_vxlan {
                description "Layer Rate VXLAN.";
            }
        }
        description "Layer Rate.";
    }
 typedef admin-state {
        type enumeration {
            enum active {
                description "Active status";
            }
            enum inactive {
                description "Inactive status";
            }
            enum partial {
                description "Partial status";
            }
        }
        description "Admin State.";
    }
    typedef oper-state {
        type enumeration {
            enum up {
                description "Up status";
            }
            enum down {
                description "Down status";
            }
            enum degrade {
                description "Degrade status";
            }
        }
        description "Operational Status.";
    }
    typedef sync-state {
        type enumeration {
            enum sync {
                description "Sync status";
            }
            enum out-sync {
                description "Out sync status";
            }
        }
        description "Sync Status";
    }
 typedef eth-encap-type {
        type enumeration {
            enum default {
                description "DEFAULT";
            }
            enum dot1q {
                description "DOT1Q";
            }
            enum qinq {
                description "QINQ";
            }
            enum untag {
                description "UNTAG";
            }
        }
        description "Ethernet Encap Type.";
    }
 typedef protocol-type {
        type enumeration {
            enum static {
                description "Static Routing";
            }
            enum bgp {
                description "bgp";
            }
            enum rip {
                description "rip";
            }
            enum ospf {
                description "ospf";
            }
            enum isis {
                description "isis";
            }
        }
        description "Routing Protocol Type";
    }
    typedef tunnel-type {
        type enumeration {
            enum NOP{
                description "NOP";
            }
            enum MPLS{
                description "MPLS";
            }
            enum MPLS-TP{
                description "MPLS-TP";
            }
            enum MPLS-SR {
                description "MPLS Segment Routing";
            }
           enum SRv6 {
                description "SRv6";
           }

        }
        description "VPN Tunnel Type.";
    }
 typedef service-type {
        type enumeration {
            enum l3vpn {
                description "l3vpn";
            }
            enum l2vpn {
                description "l2vpn";
            }
           enum hybrid {
                description "hybrid vpn";
            }
           enum vxlan {
                description "vxlan";
           }
        }
        description "VPN Service Type.";
    }
    typedef topology {
        type enumeration {
            enum any-to-any {
                description "any to any";
            }
            enum hub-spoke {
                description "hub and spoke VPN topology.";
            }
            enum hub-spoke-disjoint {
                description "Hub and spoke VPN topology where
                Hubs cannot communicate with each other ";
            }
            enum unknow {
                description "unknown.";
            }
        }
        description "Topology.";
    }

    typedef ethernet-action {
        type enumeration {
            enum nop {
                description "nop";
            }
            enum untag {
                description "UNTAG";
            }
            enum stacking {
                description "STACKING";
            }
        }
        description "Ethernet Action.";
    }
 typedef color-type{
        type enumeration {
            enum green{
                description "green";
            }
            enum yellow{
                description "yellow";
            }
            enum red{
                description "red";
            }
            enum all{
                description "all";
            }
        }
        description "Color Type.";
    }
  typedef action-type {
        type enumeration {
            enum nop{
                description "nop";
            }
            enum bandwidth{
                description "bandwidth";
            }
            enum pass{
                description "pass";
            }
            enum discard{
                description "discard";
            }
            enum remark{
                description "remark";
            }
            enum redirect{
                description "redirect";
            }
            enum recolor{
                description "recolor";
            }
            enum addRt{
                description "addRt";
            }
        }
        description "Action Type";
    }
   //----------------------------------------------//
    //typedef
    //----------------------------------------------//
    typedef PWTagMode {
        type enumeration {
            enum raw{
                description "RAW";
            }
            enum tagged{
                description "TAGGED";
            }
        }
        description "PWTagMode";
    }
  grouping QinQVlan {
        description "QinQVlan Grouping.";
        leaf-list cvlan {
            type uint64;
            description "cvlan List.";
        }
        leaf svlan {
            type uint64;
            description "svlan.";
        }
    }
    grouping Dot1QVlan {
        description "Dot1QVlan Grouping.";
        leaf-list dot1q {
            type uint64;
            description "dot1q Vlan List";
        }
    }
//TpTypeSpec
    grouping tp-type-spec{
        description "Tp Type Spec Grouping.";
        leaf layer-rate {
            type layer-rate;
            description "layer Rate";
        }
        choice spec-value {
            description "Spec Value";
            case lr-eth {
                container eth {
                    description "ethernetSpec";
                    uses ethernet-spec;
                }
            }
            case lr-ip {
                container ip {
                    description "ipSpec";
                    uses IpSpec;
                }
            }
            case lr-pw {
                container pw {
                    description "PwSpec";
                    uses PwSpec;
                }
            }
            case lr-vxlan {
                container vxlan {
                    description "vxlanSpec";
                    uses VxlanSpec;
                }
            }
        }
    }
    grouping FlowServices {
        description "FlowServices Grouping.";
        leaf qos-config-type {
            type qos-config-type;
            description "qos Config Type.";
        }
        leaf qos-sub-type {
            type qos-sub-type;
            description "qosDetailType";
        }
        leaf in-template-id {
            type yang:uuid;
            description "in Flow Qos Template ID.";
        }
        leaf out-template-id {
            type yang:uuid;
            description "out Flow Qos Template ID.";
        }
        list flow-service {
            key class-id;
            description "default in flow and behaviors";
            uses FlowAndBehavior;
        }
    }
     grouping TPQosNode {
        description "TPQosNode Grouping.";
        leaf qos-config-type {
            type qos-config-type;
            description "qos Config Type.";
        }
        leaf qos-sub-ype {
            type qos-sub-type;
            description "qos Detail Type";
        }
        leaf in-profile-id {
            type yang:uuid;
            description "inQosProfileId";
        }
        leaf out-profile-id {
            type yang:uuid;
            description "outQosProfileId";
        }
        list in-tp-car {
            key index;
            uses FlowBehavior;
            description "inTpCar";
        }
        list out-tp-car {
            key index;
            uses FlowBehavior;
            description "outTpCar";
         }
    }

//CE spec
    grouping CeTp {
        description "CeTp Grouping.";
        leaf ce-id {
            type yang:uuid;
            description "Site router ID";
        }
        leaf ce-node-id {
            type yang:uuid;
            description "directly connected NE node ID, only valid in
            asbr ";
        }
        leaf ce-tp-id {
            type yang:uuid;
            description "ce Directly connected TP id, only valid in asbr";
        }
        leaf ce-address {
            type inet:ip-address;
            description "ceIfmasterIp";
        }
        leaf location {
            type string {length "0..400";}
            description "CE device location ";
        }
    }
//TPBasicInfo
    grouping TPBasicInfo {
        description "TPBasicInfo Grouping.";
        leaf tp-id {
            type yang:uuid;
            description "An identifier for termination point on a node.";
        }
        leaf tp-name {
            type string {length "0..200";}
            description "The termination point Name on a node. It conforms to
            name rule defined in system. Example FE0/0/1, GE1/2/1.1,
            Eth-Trunk1.1, etc";
        }
        leaf node-id {
            type yang:uuid;
            description "Identifier for a node.";
        }
        leaf edge-role {
            type edge-role;
            description "edge role for TP, for example:UNI/NNI ";
        }
        leaf topo-role {
            type topo-role;
            description "hub/spoke role, etc";
        }
        leaf tp-type {
            type tp-type;
            description "Type";
        }
        leaf working-layer {
            type layer-rate;
            description "working layer";
        }
        list type-spec {
            key "layer-rate";
            uses tp-type-spec;
            description "typeSpecList";
        }
        container tp-qos-node {
            description "tp Qos Node.";
            uses TPQosNode;
        }
        container flow-services{
            description "flow services in one TP.";
            uses FlowServices;
        }
    }
    grouping RouteProtocolSpec {
        description "Routing Protocol Spec Grouping.";
        leaf type {
            type protocol-type;
            description "Protocol type" ;
        }
        choice para {
            description "para" ;
            case static {
                list static {
                    key "index";
                    uses StaticRouteItem;
                    description "staticRouteItems" ;
                }
            }
            case bgp {
                    list bgp {
                            key "index";
                            uses BGPProtocolItem;
                            description "bgpProtocols" ;
                    }
            }
        }
    }
    grouping BGPProtocolItem {
        description "BGPProtocolItem Grouping.";
        leaf index {
            type uint32;
            description "index of BGP protocol item";
        }
        leaf as-no {
            type uint64;
            description "Peer AS Number.";
        }
        leaf max-prefix {
            type int32;
            description "maximum number limit of prefixes.";
        }
        leaf max-prefix-alarm {
            type uint32;
            description "alarm threshold of BGP rout";
        }
        leaf peer-address {
            type inet:ip-address;
            description "peerIp";
        }
    }
     grouping StaticRouteItem {
        description "StaticRouteItem Grouping.";
        leaf index {
            type uint32;
            description "static item index";
        }
        leaf dest-cidr {
            type string;
            description "address prefix specifying the set of
            destination addresses for which the route may be
            used. ";
        }
        leaf egress-tp {
            type yang:uuid;
            description "egress tp";
        }
        leaf route-preference {
            type string;
            description "route priority. Ordinary, work route have
            higher priority.";
        }
        leaf next-hop {
            type inet:ip-address;
            description "Determines the outgoing interface and/or
            next-hop address(es), or a special operation to be
            performed on a packet..";
        }
    }
     grouping ethernet-spec {
        description "Ethernet Spec Grouping.";
        leaf access-type {
            type eth-encap-type;
            description "access frame type";
        }
        choice accessVlanValue {
            description "accessVlanValue";
            case qinq {
                container qinq {
                    description "qinqVlan";
                    uses QinQVlan;
                }
            }
            case dot1q {
                container dot1q {
                    description "dot1q";
                    uses Dot1QVlan;
                }
            }
        }
        leaf vlan-action {
            type ethernet-action;
            description "specify the action when the vlan is matched";
        }
        leaf action {
            type string{length "0..100";}
            description "specify the action value.";
        }
    }
    grouping PwSpec {
        description "PwSpec Grouping.";
        leaf control-word {
            type boolean;
            default false;
            description "control Word.";
        }
        leaf vlan-action {
            type PWTagMode;
            description "pw Vlan Action.";
        }
    }
    grouping IpSpec {
        description "IpSpec Grouping.";
        leaf ip-address {
            type inet:ip-address;
            description "master IP address";
        }
        leaf mtu {
            type uint64;
            description "mtu for ip layer,scope:46~9600";
        }
    }
    grouping VxlanSpec {
        description "VxlanSpec Grouping.";
        leaf vni {
            type uint32;
            description "vni";
        }
        leaf vtep-ip {
            type inet:ip-address;
            description "vtep ip";
        }
    }
    grouping FlowAndBehavior {
        description "FlowAndBehavior Grouping.";
        leaf class-id {
            type yang:uuid;
            description "flowClassifierId";
        }
        list flow-behavior {
            key index;
            uses FlowBehavior;
            description "flowBehaviors";
        }
    }
    grouping FlowBehavior {
        description "FlowAndBehavior Grouping.";
        leaf index {
            type uint32;
            description "index";
        }
        leaf color-type {
            type color-type;
            description "Color Type.";
        }
        leaf action-type {
            type action-type;
            description "action Type";
        }
        leaf action {
            type string;
            description "action";
        }
    }
    grouping VPNBasicInfo {
        description "VPNBasicInfo Grouping.";
        leaf topo {
            type topology;
            description "current support for full-mesh and
            hub-spoke, others is reserved for
            future extensions." ;
        }
        leaf service-type {
            type service-type;
            description "current support for mpls l3vpn/vxlan/L2VPN
            overlay, others is reserved for future extensions." ;
        }
        leaf technology {
            type tunnel-type;
            description "mpls|vxlan overlay l3vpn|eth over sdh|nop";
        }
        leaf admin-state {
            type admin-state;
            description "administrative status." ;
         }
        leaf oper-state {
            type oper-state;
            config false;
            description "Operational status." ;
        }
        leaf sync-state {
            type sync-state;
            config false;
            description "Sync status." ;
        }
    }
 grouping VPN {
        description "VPN Grouping.";
        leaf vpn-id {
            type yang:uuid ;
            description "VPN Identifier." ;
        }
        leaf vpn-name {
            type string  {length "0..200";}
            description "Human-readable name for the VPN service." ;
        }
        uses VPNBasicInfo;
        list access-point {
            key "tp-id";
            description "TP list of the access links which associated
            with CE and PE";
            uses termination-point;
        }
    }
    grouping termination-point {
        description "grouping for termination points.";
        leaf tp-id {
            type yang:uuid;
            description "An identifier for termination point on a node.";
        }
        container peer-ce-node {
            description "CE TP Information.";
            uses CeTp;
        }
        container tp-basic {
            description "Termination point basic info.";
            uses TPBasicInfo;
        }
        list routing-protocol {
            key "type";
            description "route protocol spec.";
            uses RouteProtocolSpec;
        }
        leaf admin-state {
            type admin-state;
            description "administrative status.";
        }
        leaf oper-state {
            type oper-state;
            config false;
            description "Operational status." ;
        }
    }
 grouping segment-vpn {
        description "SegmentVPN Grouping.";
        leaf index {
            type uint32;
            description "index of segment VPN in a composed VPN.";
        }
        leaf protect-role {
            type protection-role;
            description "The protection role of segment VPN, by
            default it is set as nop role.";
        }
        container vpn-info {
            description "vpn information";
            choice vpn-type {
                  description "vpn type.";
                  case wan-vpn {
                      container vpn {
                          description "vpn.";
                          uses VPN;
                        }
                  }
              }
        }
    }
container segment-vpns {
  list segment-vpn {
               key "index";
               description "Segment Vpn list.";
               uses segment-vpn;
           }
    description
    "Container for Segment VPN.";
}
}
