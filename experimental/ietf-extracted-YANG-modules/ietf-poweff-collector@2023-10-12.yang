module ietf-poweff-collector {
  yang-version 1.1;
  namespace "urn:ietf:params:xml:ns:yang:ietf-poweff-collector";
  prefix ietf-poweff-collector;

  import ietf-poweff-types {
    prefix ietf-poweff-types;
  }

  organization
    "IETF OPSA (Operations and Management Area) Working Group";
  contact
    "WG Web:   <https://datatracker.ietf.org/wg/opsawg/>
     WG List:  <mailto:opsawg@ietf.org>
     Editor:  Jan Lindblad
              <mailto:jlindbla@cisco.com>
     Editor:  Snezana Mitrovic
              <mailto:snmitrov@cisco.com>
     Editor:  Marisol Palmero
              <mailto:mpalmero@cisco.com>";
  description
    "This YANG module defines the POWEFF Collector.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions

     Relating to IETF Documents
     (https://trustee.ietf.org/license-info).

     This version of this YANG module is part of RFC XXXX
     (https://www.rfc-editor.org/info/rfcXXXX); see the RFC itself
     for full legal notices.";

  revision 2023-10-12 {
    description
      "Initial revision of POWEFF Collector";
    reference
      "RFC XXXX: ...";
  }

/*

  A COLLECTOR programs one or more SOURCE(s) to generate a
  STREAM of telemetry data.  The STREAM is sent to a specific
  DESTINATION.

  Each STREAM consists of timestamped sensor values from each
  sensor in a sensor group.

             +-------------+
             |  COLLECTOR  |
             +-------------+                     ___________
                    |                           /           \
          +------------------+                 ( DESTINATION )
          v                  v                 |\___________/|
    +------------+    +------------+  STREAM 1 |             |
    |   SOURCE   |    |   SOURCE   |  =======> |             |
    | - sensor 1 |    | - sensor 1 |           |             |
    | - sensor 2 |    | - sensor 4 |  STREAM 2 |             |
    | - sensor 3 |    | - sensor 7 |  =======> |             |
    +------------+    +------------+           |             |
              \\                      STREAM 3 |             |
                =============================>  \___________/

*/

  grouping data-endpoint-g {
    leaf url { type ietf-poweff-types:something; }
    leaf organization { type ietf-poweff-types:something; }
    leaf bucket { type ietf-poweff-types:something; }
    container impl-specific {
      list binding {
        key key;
        leaf key { type string; }
        choice value-type {
          leaf value { type string; }
          leaf-list values { type string; ordered-by user; }
          leaf env-var { type string; }
        }
      }
    }
  }

  grouping sensor-group-g {
    leaf method {
      type identityref {
        base ietf-poweff-types:collection-method;
      }
    }
    container get-static-url-once {
      when "derived-from-or-self(../method, 'ietf-poweff-types:get-static-url-once')";
      leaf url { type ietf-poweff-types:something; }
      leaf format { type ietf-poweff-types:something; } // JSON-IETF, XML, etc
    }
    container gnmi-polling {
      when "derived-from-or-self(../method, 'ietf-poweff-types:gnmi-polling')";
      leaf encoding { type ietf-poweff-types:something; } // self-describing-gpb
      leaf protocol { type ietf-poweff-types:something; } // protocol grpc no-tls
    }
    container restconf-get-polling {
      when "derived-from-or-self(../method, 'ietf-poweff-types:restconf-get-polling')";
      leaf xxx { type string; }
    }
    container netconf-get-polling {
      when "derived-from-or-self(../method, 'ietf-poweff-types:netconf-get-polling')";
      leaf xxx { type string; }
    }
    container restconf-yang-push-subscription {
      when "derived-from-or-self(../method, 'ietf-poweff-types:restconf-yang-push-subscription')";
      leaf xxx { type string; }
    }
    container netconf-yang-push-subscription {
      when "derived-from-or-self(../method, 'ietf-poweff-types:netconf-yang-push-subscription')";
      leaf xxx { type string; }
    }
    container redfish-polling {
      when "derived-from-or-self(../method, 'ietf-poweff-types:redfish-polling')";
      leaf xxx { type string; }
    }
    leaf frequency {
      when "derived-from(../method, 'ietf-poweff-types:cm-polled')";
      type ietf-poweff-types:sample-frequency;
    }
    list path {
      key path;
      leaf path { type ietf-poweff-types:xpath; }
      leaf sensor-type { type identityref { base ietf-poweff-types:sensor-type; }}
      leaf attribution { type string; }
    }
  }

  grouping collector-g {
    container poweff-collector {
      container destinations {
        list destination {
          key id;
          leaf id { type ietf-poweff-types:something; }
          uses data-endpoint-g;
        }
      }

      container sensor-groups {
        list sensor-group {
          key id;
          leaf id { type ietf-poweff-types:something; }
          uses sensor-group-g;
        }
      }

      container streams {
        list stream {
          key id;
          leaf id { type ietf-poweff-types:something; }
          leaf-list source { type string; } // Implementation specific meaning, possibly wildcards
          list sensor-group {
            key name;
            leaf name { type leafref { path ../../../sensor-groups/sensor-group/id; }}
          }
          leaf destination { type leafref { path ../../../destinations/destination/id; }}
        }
      }
    }
  }
}
