module ietf-bgp {

  yang-version "1";

  // namespace
  namespace "urn:ietf:params:xml:ns:yang:ietf-bgp";

  prefix "bgp";

  // import some basic inet types
  import ietf-routing-policy {
    prefix rpol;
  }

  // Common: defines the groupings that are common across more than
  //         one context (where contexts are neighbor, group, global)
  include ietf-bgp-common;
  // Multiprotocol: defines the groupings that are common across more
  //                than one context, and relate to Multiprotocol
  include ietf-bgp-common-multiprotocol;
  // Structure: defines groupings that are shared but are solely used
  //            for structural reasons.
  include ietf-bgp-common-structure;
  // Include peer-group/neighbor/global - these define the groupings
  // that are specific to one context
  include ietf-bgp-neighbor;
  include ietf-bgp-global;
  include ietf-bgp-peer-group;

  // meta
  organization
    "IETF IDR Working Group";

  contact
    "WG Web:   <http://tools.ietf.org/wg/idr>
     WG List:  <idr@ietf.org>

     Editor:  Mahesh Jethanandani (mjethanandani@gmail.com)
            Authors: Keyur Patel,
                     Mahesh Jethanandani,
                     Susan Hares";

  description
    "This module describes a YANG model for BGP protocol
    configuration. It is a limited subset of all of the configuration
    parameters available in the variety of vendor implementations,
    hence it is expected that it would be augmented with vendor-
    specific configuration data as needed. Additional modules or
    submodules to handle other aspects of BGP configuration,
    including policy, VRFs, VPNs, and additional address families
    are also expected.

    This model supports the following BGP configuration level
    hierarchy:

      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]";

  revision "2017-10-17" {
    description
      "Initial Version";
    reference
      "RFC XXXX, BGP Model for Service Provider Network ";
  }

  /*
   * Groupings
   */
  container bgp {
    description
      "Top-level configuration for the BGP router";

    container global {
      description
        "Global configuration for the BGP router";
      uses bgp-global-base;
      uses rpol:apply-policy-group;
    }

    container neighbors {
      description
        "Configuration for BGP neighbors";
      uses bgp-neighbor-list;
    }

    container peer-groups {
      description
        "Configuration for BGP peer-groups";
      uses bgp-peer-group-list;
    }
  }
}
