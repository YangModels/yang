module ietf-isis-sr {
  yang-version 1.1;
  namespace "urn:ietf:params:xml:ns:"
          + "yang:ietf-isis-sr";
  prefix isis-sr;

  import ietf-routing {
    prefix "rt";
    reference "RFC 8349 - A YANG Data Model for Routing
               Management (NMDA Version)";
  }

  import ietf-segment-routing-common {
    prefix "sr-cmn";
  }

  import ietf-segment-routing-mpls {
    prefix "sr-mpls";
  }

  import ietf-isis {
    prefix "isis";
  }

  import iana-routing-types {
    prefix "iana-rt-types";
    reference "RFC 8294 - Common YANG Data Types for the
               Routing Area";
  }

  organization
   "IETF LSR - LSR Working Group";

  contact
    "WG List:  <mailto:lsr@ietf.org>

    Editor:    Stephane Litkowski
               <mailto:stephane.litkowski@orange.com>

    Author:    Acee Lindem
               <mailto:acee@cisco.com>
    Author:    Yingzhen Qu
               <mailto:yingzhen.qu@futurewei.com>
    Author:    Pushpasis Sarkar
               <mailto:pushpasis.ietf@gmail.com>
    Author:    Ing-Wher Chen
               <mailto:ingwherchen@mitre.org>
    Author:    Jeff Tantsura
               <mailto:jefftant.ietf@gmail.com>
    ";

  description
    "The YANG module defines a generic configuration model for
     Segment routing ISIS extensions common across all of the vendor
     implementations.

    This YANG model conforms to the Network Management
    Datastore Architecture (NMDA) as described in RFC 8242.

    Copyright (c) 2021 IETF Trust and the persons identified as
    authors of the code.  All rights reserved.

    Redistribution and use in source and binary forms, with or
    without modification, is permitted pursuant to, and subject to
    the license terms contained in, the Simplified BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.

    This version of this YANG module is part of RFC XXXX;
    see the RFC itself for full legal notices.";

  reference "RFC XXXX";

  revision 2021-01-11 {
  description
    "Initial revision.";
  reference "RFC XXXX";
  }

  /* Identities */
  identity sr-capability {
    description
      "Base identity for ISIS SR-Capabilities sub-TLV flgs";
  }

  identity mpls-ipv4 {
    base sr-capability;
    description
      "If set, then the router is capable of
       processing SR MPLS encapsulated IPv4 packets
       on all interfaces.";
  }

  identity mpls-ipv6 {
    base sr-capability;
    description
      "If set, then the router is capable of
       processing SR MPLS encapsulated IPv6 packets
       on all interfaces.";
  }

  identity prefix-sid-bit {
    description
      "Base identity for prefix sid sub-tlv bits.";
  }

  identity r-bit {
    base prefix-sid-bit;
    description
     "Re-advertisement Flag.";
  }

  identity n-bit {
    base prefix-sid-bit;
    description
     "Node-SID Flag.";
  }

  identity p-bit {
    base prefix-sid-bit;
    description
     "No-PHP (No Penultimate Hop-Popping) Flag.";
  }

  identity e-bit {
    base prefix-sid-bit;
    description
     "Explicit NULL Flag.";
  }

  identity v-bit {
    base prefix-sid-bit;
    description
     "Value Flag.";
  }

  identity l-bit {
    base prefix-sid-bit;
    description
     "Local Flag.";
  }

  identity adj-sid-bit {
    description
      "Base identity for adj sid sub-tlv bits.";
  }

  identity f-bit {
    base adj-sid-bit;
    description
      "Address-Family flag.";
  }

  identity b-bit {
    base adj-sid-bit;
    description
      "Backup flag.";
  }

  identity vi-bit {
    base adj-sid-bit;
    description
      "Value/Index flag.";
  }

  identity lo-bit {
    base adj-sid-bit;
    description
      "Local flag.";
  }

  identity s-bit {
    base adj-sid-bit;
    description
      "Group flag.";
  }

  identity pe-bit {
    base adj-sid-bit;
    description
      "Persistent flag.";
  }

  identity sid-binding-bit {
    description
      "Base identity for sid binding tlv bits.";
  }

  identity af-bit {
    base sid-binding-bit;
    description
      "Address-Family flag.";
  }

  identity m-bit {
    base sid-binding-bit;
    description
      "Mirror Context flag.";
  }

  identity sf-bit {
    base sid-binding-bit;
    description
      "S flag. If set, the binding label tlv should be flooded
       across the entire routing domain.";
  }

  identity d-bit {
    base sid-binding-bit;
    description
      "Leaking flag.";
  }

  identity a-bit {
    base sid-binding-bit;
    description
      "Attached flag.";
  }

  /* Features */

  feature remote-lfa-sr {
    description
     "Enhance rLFA to use SR path.";
  }

  feature ti-lfa {
    description
     "Enhance IPFRR with ti-lfa
     support";
  }

  /* Groupings */

  grouping sid-sub-tlv {
    description "SID/Label sub-TLV grouping.";
    container sid-sub-tlv {
      description
        "Used to advertise the SID/Label associated with a
      prefix or adjacency.";
      leaf sid {
        type uint32;
      description
        "Segment Identifier (SID) - A 20 bit label or
         32 bit SID.";
      }
    }
  }

  grouping sr-capability {
    description
      "SR capability grouping.";
    container sr-capability {
      description
        "Segment Routing capability.";
      container sr-capability {
        leaf-list sr-capability-bits {
          type identityref {
            base sr-capability;
          }
          description "SR Capbility sub-tlv flags list.";
        }
        description
          "SR Capability Flags.";
      }
      container global-blocks {
        description
          "Segment Routing Global Blocks.";
        list global-block {
          description "Segment Routing Global Block.";
          leaf range-size {
            type uint32;
            description "The SID range.";
          }
          uses sid-sub-tlv;
        }
      }
    }
  }

  grouping sr-algorithm {
    description
      "SR algorithm grouping.";
    container sr-algorithms {
      description "All SR algorithms.";
      leaf-list sr-algorithm {
        type uint8;
        description
          "The Segment Routing (SR) algorithms that the router is
           currently using.";
      }
    }
  }

  grouping srlb {
    description
      "SR Local Block grouping.";
    container local-blocks {
      description "List of SRLBs.";
      list local-block {
        description "Segment Routing Local Block.";
        leaf range-size {
          type uint32;
          description "The SID range.";
        }
        uses sid-sub-tlv;
      }
    }
  }

  grouping srms-preference {
    description "The SRMS preference TLV is used to advertise
                 a preference associated with the node that acts
                 as an SR Mapping Server.";
    container srms-preference {
      description "SRMS Preference TLV.";
      leaf preference {
        type uint8 {
          range "0 .. 255";
        }
        description "SRMS preference TLV, vlaue from 0 to 255.";
      }
    }
  }

  grouping adjacency-state {
    description
      "This group will extend adjacency state.";
    list adjacency-sid {
      key value;
      config false;
      leaf af {
        type iana-rt-types:address-family;
        description
          "Address-family associated with the
           segment ID";
      }
      leaf value {
        type uint32;
        description
          "Value of the Adj-SID.";
      }
      leaf weight {
        type uint8;
        description
          "Weight associated with
          the adjacency SID.";
      }
      leaf protection-requested {
        type boolean;
        description
          "Describe if the adjacency SID
           must be protected.";
      }
      description
        "List of adjacency Segment IDs.";
    }
  }

  grouping prefix-segment-id {
    description
      "This group defines segment routing extensions
       for prefixes.";

    list sid-list {
      key value;

      container perfix-sid-flags {
        leaf-list bits {
          type identityref {
            base prefix-sid-bit;
          }
          description
            "Prefix SID Sub-TLV flag bits list.";
        }
        description
          "Describes flags associated with the
           segment ID.";
      }

      leaf algorithm {
        type uint8;
        description
          "Algorithm to be used for path computation.";
      }
      leaf value {
        type uint32;
        description
         "Value of the prefix-SID.";
      }
      description
        "List of segments.";
    }
  }

  grouping adjacency-segment-id {
    description
      "This group defines segment routing extensions
       for adjacencies.";

    list sid-list {
      key value;

      container adj-sid-flags {
        leaf-list bits {
          type identityref {
            base adj-sid-bit;
          }
          description "Adj sid sub-tlv flags list.";
          }
        description "Adj-sid sub-tlv flags.";
      }

      leaf weight {
        type uint8;
        description
          "The value represents the weight of the Adj-SID
           for the purpose of load balancing.";
      }
      leaf neighbor-id {
        type isis:system-id;
        description
          "Describes the system ID of the neighbor
           associated with the SID value. This is only
           used on LAN adjacencies.";
      }
      leaf value {
        type uint32;
        description
          "Value of the Adj-SID.";
      }
      description
        "List of segments.";
    }
  }

  grouping segment-routing-binding-tlv {
    list segment-routing-bindings {
      key "fec range";

      leaf fec {
        type string;
        description
        "IP (v4 or v6) range to be bound to SIDs.";
      }

      leaf range {
        type uint16;
        description
          "Describes number of elements to assign
           a binding to.";
      }

      container sid-binding-flags {
        leaf-list bits {
          type identityref {
            base sid-binding-bit;
          }
          description
            "SID Binding TLV flag bits list.";
        }
        description
          "Binding flags.";
      }

      container binding {
        container prefix-sid {
          uses prefix-segment-id;
          description
            "Binding prefix SID to the range.";
        }
        description
          "Bindings associated with the range.";
      }

      description
        "This container describes list of SID/Label bindings.
         ISIS reference is TLV 149.";
    }
    description
      "Defines binding TLV for database.";
  }

  /* Cfg */

  augment "/rt:routing/" +
          "rt:control-plane-protocols/rt:control-plane-protocol"+
          "/isis:isis" {
    when "/rt:routing/rt:control-plane-protocols/"+
         "rt:control-plane-protocol/rt:type = 'isis:isis'" {
      description
        "This augment ISIS routing protocol when used";
    }
    description
      "This augments ISIS protocol configuration
       with segment routing.";

    uses sr-mpls:sr-control-plane;
    container protocol-srgb {
      if-feature sr-mpls:protocol-srgb;
      uses sr-cmn:srgb;
      description
        "Per-protocol SRGB.";
    }
  }

  augment "/rt:routing/" +
          "rt:control-plane-protocols/rt:control-plane-protocol"+
          "/isis:isis/isis:interfaces/isis:interface" {
    when "/rt:routing/rt:control-plane-protocols/"+
         "rt:control-plane-protocol/rt:type = 'isis:isis'" {
      description
        "This augment ISIS routing protocol when used";
    }
    description
      "This augments ISIS protocol configuration
       with segment routing.";

    uses sr-mpls:igp-interface;
  }

  augment "/rt:routing/" +
          "rt:control-plane-protocols/rt:control-plane-protocol"+
          "/isis:isis/isis:interfaces/isis:interface"+
          "/isis:fast-reroute" {
    when "/rt:routing/rt:control-plane-protocols/"+
         "rt:control-plane-protocol/rt:type = 'isis:isis'" {
      description
        "This augment ISIS routing protocol when used";
    }
    description
      "This augments ISIS IP FRR with TILFA.";

    container ti-lfa {
      if-feature ti-lfa;
      leaf enable {
        type boolean;
        description
          "Enables TI-LFA computation.";
      }
      description
        "TILFA configuration.";
    }
  }

  augment "/rt:routing/" +
          "rt:control-plane-protocols/rt:control-plane-protocol"+
          "/isis:isis/isis:interfaces/isis:interface"+
          "/isis:fast-reroute/isis:lfa/isis:remote-lfa" {
    when "/rt:routing/rt:control-plane-protocols/"+
         "rt:control-plane-protocol/rt:type = 'isis:isis'" {
      description
        "This augment ISIS routing protocol when used";
    }
    description
      "This augments ISIS remoteLFA config with
       use of segment-routing path.";

    leaf use-segment-routing-path {
      if-feature remote-lfa-sr;
      type boolean;
      description
        "force remote LFA to use segment routing
         path instead of LDP path.";
    }
  }

  /* Operational states */

  augment "/rt:routing/" +
          "rt:control-plane-protocols/rt:control-plane-protocol"+
          "/isis:isis/isis:interfaces/isis:interface" +
          "/isis:adjacencies/isis:adjacency" {
    when "/rt:routing/rt:control-plane-protocols/"+
         "rt:control-plane-protocol/rt:type = 'isis:isis'" {
      description
        "This augment ISIS routing protocol when used";
    }
    description
      "This augments ISIS protocol configuration
       with segment routing.";

    uses adjacency-state;
  }

  augment "/rt:routing/" +
          "rt:control-plane-protocols/rt:control-plane-protocol"+
          "/isis:isis/isis:database/isis:levels/isis:lsp"+
          "/isis:router-capabilities" {
    when "/rt:routing/rt:control-plane-protocols/"+
         "rt:control-plane-protocol/rt:type = 'isis:isis'" {
      description
        "This augment ISIS routing protocol when used";
    }
    description
      "This augments ISIS protocol LSDB router capability.";

    uses sr-capability;
    uses sr-algorithm;
    uses srlb;
    uses srms-preference;
  }

  augment "/rt:routing/" +
          "rt:control-plane-protocols/rt:control-plane-protocol"+
          "/isis:isis/isis:database/isis:levels/isis:lsp"+
          "/isis:extended-is-neighbor/isis:neighbor" {
    when "/rt:routing/rt:control-plane-protocols/"+
         "rt:control-plane-protocol/rt:type = 'isis:isis'" {
      description
        "This augment ISIS routing protocol when used";
    }
    description
      "This augments ISIS protocol LSDB neighbor.";
       uses adjacency-segment-id;
  }

  augment "/rt:routing/" +
          "rt:control-plane-protocols/rt:control-plane-protocol"+
          "/isis:isis/isis:database/isis:levels/isis:lsp"+
          "/isis:mt-is-neighbor/isis:neighbor" {
    when "/rt:routing/rt:control-plane-protocols/"+
         "rt:control-plane-protocol/rt:type = 'isis:isis'" {
      description
        "This augment ISIS routing protocol when used";
    }
    description
      "This augments ISIS protocol LSDB neighbor.";
       uses adjacency-segment-id;
  }

  augment "/rt:routing/" +
          "rt:control-plane-protocols/rt:control-plane-protocol"+
          "/isis:isis/isis:database/isis:levels/isis:lsp"+
          "/isis:extended-ipv4-reachability/isis:prefixes" {
    when "/rt:routing/rt:control-plane-protocols/"+
         "rt:control-plane-protocol/rt:type = 'isis:isis'" {
      description
        "This augment ISIS routing protocol when used";
    }
    description
      "This augments ISIS protocol LSDB prefix.";
       uses prefix-segment-id;
  }

  augment "/rt:routing/" +
          "rt:control-plane-protocols/rt:control-plane-protocol"+
          "/isis:isis/isis:database/isis:levels/isis:lsp"+
          "/isis:mt-extended-ipv4-reachability/isis:prefixes" {
    when "/rt:routing/rt:control-plane-protocols/"+
         "rt:control-plane-protocol/rt:type = 'isis:isis'" {
      description
        "This augment ISIS routing protocol when used";
    }
    description
      "This augments ISIS protocol LSDB prefix.";
    uses prefix-segment-id;
  }

  augment "/rt:routing/" +
          "rt:control-plane-protocols/rt:control-plane-protocol"+
          "/isis:isis/isis:database/isis:levels/isis:lsp"+
          "/isis:ipv6-reachability/isis:prefixes" {
    when "/rt:routing/rt:control-plane-protocols/"+
         "rt:control-plane-protocol/rt:type = 'isis:isis'" {
      description
        "This augment ISIS routing protocol when used";
    }
    description
      "This augments ISIS protocol LSDB prefix.";
    uses prefix-segment-id;
  }

  augment "/rt:routing/" +
          "rt:control-plane-protocols/rt:control-plane-protocol"+
          "/isis:isis/isis:database/isis:levels/isis:lsp"+
          "/isis:mt-ipv6-reachability/isis:prefixes" {
    when "/rt:routing/rt:control-plane-protocols/"+
         "rt:control-plane-protocol/rt:type = 'isis:isis'" {
      description
        "This augment ISIS routing protocol when used";
    }
    description
      "This augments ISIS protocol LSDB prefix.";
    uses prefix-segment-id;
  }

  augment "/rt:routing/" +
          "rt:control-plane-protocols/rt:control-plane-protocol"+
          "/isis:isis/isis:database/isis:levels/isis:lsp" {
    when "/rt:routing/rt:control-plane-protocols/"+
         "rt:control-plane-protocol/rt:type = 'isis:isis'" {
      description
        "This augment ISIS routing protocol when used";
    }
    description
      "This augments ISIS protocol LSDB.";
    uses segment-routing-binding-tlv;
  }

  /* Notifications */

}
