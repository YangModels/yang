module ietf-bgp-ls-topo-types {
 yang-version "1.1";

 namespace "urn:ietf:params:xml:ns:yang:ietf-bgp-ls-topo-types";

 prefix "ietf-bgp-ls-topo-types";

 organization
   "IETF LSVR Working Group";

 contact
   "WG Web:   <https://datatracker.ietf.org/wg/lsvr>
    WG List:  <lsvr@ietf.org>

    Authors: Mahesh Jethanandani (mjethanandani at gmail.com),
             Keyur Patel (keyur at arrcus.com),
             Aravind Babu MahendraBabu (aramahen at cisco.com)";

 description
   "Defines identity and type definitions associated with BGP-LS
    topology modules.

    Copyright (c) 2025 IETF Trust and the persons identified as
    authors of the code. All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

 revision 2026-11-02 {
   description
     "Initial Version";
   reference
     "RFC XXXX, BGP Model for Link State Distribution.";
 }

 typedef protocol {
   type enumeration {
     enum isis-l1  {
       value 1;
       description
         "Value of BGP-LS protocol ISIS L1";
     }
     enum isis-l2  {
       value 2;
       description
         "Value of BGP-LS protocol ISIS L2";
     }
     enum ospfv2 {
       value 3;
       description
         "Value of BGP-LS protocol OSPFv2";
     }
     enum direct {
       value 4;
       description
         "Value of BGP-LS protocol Direct";
     }
     enum static {
       value 5;
       description
         "Value of BGP-LS protocol Static";
     }
     enum ospfv3 {
       value 6;
       description
         "Value of BGP-LS protocol OSPFv3";
     }
     enum bgp {
       value 7;
       description
         "Value of BGP-LS protocol BGP";
     }
     enum rsvp-te {
       value 8;
       description
         "Value of BGP-LS protocol RSVP-TE";
     }
     enum sr {
       value 9;
       description
         "Value of BGP-LS protocol SR";
     }
   }
   description
     "BGP-LS Protocol";
   reference
     "RFC 9552: Distribution of Link-State and Traffic Engineering
      Information Using BGP, Section 5.2.";
 }

 typedef nlri-type {
   type enumeration {
     enum node  {
       value 1;
       description
         "Value of BGP-LS Node NLRI";
     }
     enum link  {
       value 2;
       description
         "Value of BGP-LS Link NLRI";
     }
     enum ipv4-prefix {
       value 3;
       description
         "Value of BGP-LS IPv4 Prefix NLRI";
     }
     enum ipv6-prefix {
       value 4;
       description
         "Value of BGP-LS IPv6 Prefix NLRI";
     }
     enum sr-policy-candidate-path {
       value 5;
       description
         "Value of BGP-LS SR Policy Candidate Path NLRI";
     }
     enum srv6-sid {
       value 6;
       description
         "Value of BGP-LS SRv6 SID NLRI";
     }
   }
   description
     "BGP-LS NLRI Types";
   reference
     "RFC 9552: Distribution of Link-State and Traffic Engineering
      Information Using BGP, Section 5.1.";
}

 typedef ospf-route-type {
   type enumeration {
     enum intra-area  {
       value 1;
       description
         "Value of OSPF Route Type Intra Area";
     }
     enum inter-area  {
       value 2;
       description
         "Value of OSPF Route Type Inter Area";
     }
     enum external-1 {
       value 3;
       description
         "Value of OSPF Route Type External 1";
     }
     enum external-2 {
       value 4;
       description
         "Value of OSPF Route Type External 2";
     }
     enum nssa-1 {
       value 5;
       description
         "Value of OSPF Route Type NSSA 1";
     }
     enum nssa-2 {
       value 6;
       description
         "Value of OSPF Route Type NSSA 2";
     }
   }
   description
     "OSPF Route Type";
   reference
     "RFC 9552: Distribution of Link-State and Traffic Engineering
      Information Using BGP, Section 3.2.3.";
}

 typedef node-flag-bits {
    type bits {
     bit overload {
       position 0;
       description
         "Value of Overload bit";
     }
     bit attached {
       position 1;
       description
         "Value of Attached bit";
     }
     bit external {
       position 2;
       description
         "Value of External bit";
     }
     bit abr {
       position 3;
       description
         "Value of ABR bit";
     }
     bit router {
       position 4;
       description
         "Value of Router bit";
     }
     bit v6 {
       position 5;
       description
         "Value of IPv6 bit";
     }
   }
   description
     "BGP-LS Node flag bits";

   reference
     "RFC 9552: Distribution of Link-State and Traffic Engineering
      Information Using BGP. Section 3.3.1.1";
 }

 typedef igp-flags-bits {
    type binary {
     length "1";
   }
   description
     "BGP-LS IGP flag bits";
   reference
     "RFC 9552: Distribution of Link-State and Traffic Engineering
      Information Using BGP, Section 3.3.3.";
 }

 typedef sid-format {
   type enumeration {
     enum label {
       value 1;
       description
         "SID represented as an MPLS label value.";
     }
     enum index {
       value 2;
       description
         "SID represented as an index value.";
     }
   }
   description
     "Format of a SID value (adjacency, prefix, or BGP peer).";
 }

 identity bgp-ls-topo-attr-type {
   description
     "Base identity for BGP-LS topology attribute type.";
 }

 identity bgp-ls-topo-attr-fad-type {
   description
     "Base identity for BGP-LS topology Flexible Algorithm
      Definition (FAD) attribute type.";
 }

 identity bgp-ls-topo-attr-link-local-remote-identifiers {
   base "bgp-ls-topo-attr-type";
   description
     "BGP-LS TLV 258. Link local and remote identifiers";
   reference
     "RFC 9552: Distribution of Link-State and Traffic
     Engineering Information Using BGP.";
 }

 identity bgp-ls-topo-attr-multi-topology-id {
   base "bgp-ls-topo-attr-type";
   description
     "BGP-LS TLV 263. Multi-Topology IDs";
   reference
     "RFC 9552: Distribution of Link-State and Traffic Engineering
     Information Using BGP.";
 }

 identity bgp-ls-topo-attr-node-msd {
   base "bgp-ls-topo-attr-type";
   description
     "BGP-LS TLV 266. Node Maximum SID Depth";
   reference
     "RFC 8814: Signaling Maximum SID Depth (MSD) Using the
     Border Gateway Protocol - Link State";
 }

 identity bgp-ls-topo-attr-link-msd {
   base "bgp-ls-topo-attr-type";
   description
     "BGP-LS TLV 267. Link Maximum SID Depth";
   reference
     "RFC 8814: Signaling Maximum SID Depth (MSD) Using the
     Border Gateway Protocol - Link State";
 }

 identity bgp-ls-topo-attr-node-flag-bits {
   base "bgp-ls-topo-attr-type";
   description
     "BGP-LS TLV 1024. Bit mask describing node attributes";
   reference
     "RFC 9552: Distribution of Link-State and Traffic Engineering
     Information Using BGP.";
 }

 identity bgp-ls-topo-attr-opaque-node {
   base "bgp-ls-topo-attr-type";
   description
     "BGP-LS TLV 1025. Envelope that transparently carries optional
     Node Attribute TLVs advertised by a router";
   reference
     "RFC 9552: Distribution of Link-State and Traffic Engineering
     Information Using BGP.";
 }

 identity bgp-ls-topo-attr-node-name {
   base "bgp-ls-topo-attr-type";
   description
     "BGP-LS TLV 1026. Symbolic name of the router node";
   reference
     "RFC 9552: Distribution of Link-State and Traffic Engineering
     Information Using BGP.";
 }

 identity bgp-ls-topo-attr-isis-area-identifier {
   base "bgp-ls-topo-attr-type";
   description
     "BGP-LS TLV 1027. Area address of an ISIS area";
   reference
     "RFC 9552: Distribution of Link-State and Traffic Engineering
     Information Using BGP.";
 }

 identity bgp-ls-topo-attr-local-ipv4-routerid {
   base "bgp-ls-topo-attr-type";
   description
     "BGP-LS TLV 1028. Auxiliary Router-ID used by the IGP";
   reference
     "RFC 9552: Distribution of Link-State and Traffic Engineering
     Information Using BGP.";
 }

 identity bgp-ls-topo-attr-local-ipv6-routerid {
   base "bgp-ls-topo-attr-type";
   description
     "BGP-LS TLV 1029. Auxiliary Router-ID used by the IGP";
   reference
     "RFC 9552: Distribution of Link-State and Traffic Engineering
     Information Using BGP.";
 }

 identity bgp-ls-topo-attr-remote-ipv4-routerid {
   base "bgp-ls-topo-attr-type";
   description
     "BGP-LS TLV 1030. Remote Router-ID used by the IGP";
   reference
     "RFC 9552: Distribution of Link-State and Traffic Engineering
     Information Using BGP.";
 }

 identity bgp-ls-topo-attr-remote-ipv6-routerid {
   base "bgp-ls-topo-attr-type";
   description
     "BGP-LS TLV 1031. Remote Router-ID used by the IGP";
   reference
     "RFC 9552: Distribution of Link-State and Traffic Engineering
     Information Using BGP.";
 }

 identity bgp-ls-topo-attr-sr-capabilities {
   base "bgp-ls-topo-attr-type";
   description
     "BGP-LS TLV 1034. Node's Segment Routing (SR) capabilities";
   reference
     "RFC 9085: Border Gateway Protocol - Link State (BGP-LS)
      Extensions for Segment Routing";
 }

 identity bgp-ls-topo-attr-sr-algorithm {
   base "bgp-ls-topo-attr-type";
   description
     "BGP-LS TLV 1035. Segment Routing (SR) algorithms supported by
      the node";
   reference
     "RFC 9085: Border Gateway Protocol - Link State (BGP-LS)
      Extensions for Segment Routing";
 }

 identity bgp-ls-topo-attr-srlb {
   base "bgp-ls-topo-attr-type";
   description
     "BGP-LS TLV 1036. Range(s) of labels reserved by the node for
      local SIDs (Segment Identifiers)";
   reference
     "RFC 9085: Border Gateway Protocol - Link State (BGP-LS)
      Extensions for Segment Routing";
 }

 identity bgp-ls-topo-attr-srv6-cap-flags {
   base "bgp-ls-topo-attr-type";
   description
     "BGP-LS TLV 1038. SRv6 Capabilities Flags.";
   reference
     "RFC 9514: Border Gateway Protocol - Link State (BGP-LS)
      Extensions for Segment Routing over IPv6 (SRv6).";
 }

 identity bgp-ls-topo-attr-fad {
   base "bgp-ls-topo-attr-type";
   description
     "BGP-LS TLV 1039. Definition of Flexible Algorithms
      (FA) supported by the node";
   reference
     "RFC 9351: Border Gateway Protocol - Link State (BGP-LS)
      Extensions for Flexible Algorithm Advertisement";
 }

 identity bgp-ls-topo-attr-fad-excl-any-aff {
   base "bgp-ls-topo-attr-fad-type";
   description
     "BGP-LS TLV 1040. Exclude links carrying any of the specified
      affinities";
   reference
     "RFC 9351: Border Gateway Protocol - Link State (BGP-LS)
      Extensions for Flexible Algorithm Advertisement";
 }

 identity bgp-ls-topo-attr-fad-incl-any-aff {
   base "bgp-ls-topo-attr-fad-type";
   description
     "BGP-LS TLV 1041. Include links carrying any of the specified
      affinities";
   reference
     "RFC 9351: Border Gateway Protocol - Link State (BGP-LS)
      Extensions for Flexible Algorithm Advertisement";
 }

 identity bgp-ls-topo-attr-fad-incl-all-aff {
   base "bgp-ls-topo-attr-fad-type";
   description
     "BGP-LS TLV 1042. Include links carrying all of the specified
      affinities";
   reference
     "RFC 9351: Border Gateway Protocol - Link State (BGP-LS)
      Extensions for Flexible Algorithm Advertisement";
 }

 identity bgp-ls-topo-attr-fad-flags {
   base "bgp-ls-topo-attr-fad-type";
   description
     "BGP-LS TLV 1043. Flags associated with the FAD";
   reference
     "RFC 9351: Border Gateway Protocol - Link State (BGP-LS)
      Extensions for Flexible Algorithm Advertisement";
 }

 identity bgp-ls-topo-attr-fad-excl-srlg {
   base "bgp-ls-topo-attr-fad-type";
   description
     "BGP-LS TLV 1045. Exclude links associated with any of the
      specified (Shared Risk Link Group) SRLG";
   reference
     "RFC 9351: Border Gateway Protocol - Link State (BGP-LS)
      Extensions for Flexible Algorithm Advertisement";
 }

 identity bgp-ls-topo-attr-fa-unsupported {
   base "bgp-ls-topo-attr-fad-type";
   description
     "BGP-LS TLV 1046. Indicates the presence of unsupported
     Flexible Algorithm Definition (FAD) sub-TLVs";
   reference
     "RFC 9351: Border Gateway Protocol - Link State (BGP-LS)
      Extensions for Flexible Algorithm Advertisement";
 }

 identity bgp-ls-topo-attr-fad-excl-minimum-bw {
   base "bgp-ls-topo-attr-fad-type";
   description
     "BGP-LS TLV TBD (1049). Exclude links not having a minimum
      specified bandwidth";
   reference
     "RFC TBD: BGP-LS extensions for IP Flexible Algorithms and
      Bandwidth, Delay, Metrics and Constraints";
 }

 identity bgp-ls-topo-attr-fad-excl-maximum-delay {
   base "bgp-ls-topo-attr-fad-type";
   description
     "BGP-LS TLV TBD (1050). Exclude links having delay
      above a maximum specified delay";
   reference
     "RFC TBD: BGP-LS extensions for IP Flexible Algorithms and
      Bandwidth, Delay, Metrics and Constraints";
 }

 identity bgp-ls-topo-attr-fad-excl-any-rev-aff {
   base "bgp-ls-topo-attr-fad-type";
   description
     "BGP-LS TLV TBD (1053). Exclude links carrying any of the
      specified affinities in the reverse direction";
   reference
     "RFC TBD: BGP-LS extensions for Flexible Algorithms Reverse
      Affinity Constraint";
 }

 identity bgp-ls-topo-attr-fad-incl-any-rev-aff {
   base "bgp-ls-topo-attr-fad-type";
   description
     "BGP-LS TLV TBD (1054). Include links carrying any of the
      specified affinities in the reverse direction";
   reference
     "RFC TBD: BGP-LS extensions for Flexible Algorithms Reverse
      Affinity Constraint";
 }

 identity bgp-ls-topo-attr-fad-incl-all-rev-aff {
   base "bgp-ls-topo-attr-fad-type";
   description
     "BGP-LS TLV TBD (1055). Include links carrying all of the
      specified affinities in the reverse direction";
   reference
     "RFC TBD: BGP-LS extensions for Flexible Algorithms Reverse
      Affinity Constraint";
 }

 identity bgp-ls-topo-attr-extended-admin-group {
   base "bgp-ls-topo-attr-type";
   description
     "BGP-LS TLV 1173. Extended Administrative Group";
   reference
     "RFC 9552: Distribution of Link-State and Traffic
      Engineering Information Using BGP.";
 }

 identity bgp-ls-topo-attr-maximum-link-bw {
   base "bgp-ls-topo-attr-type";
   description
     "BGP-LS TLV 1089. Maximum link bandwidth";
   reference
     "RFC 9552: Distribution of Link-State and Traffic
      Engineering Information Using BGP.";
 }

 identity bgp-ls-topo-attr-maximum-reservable-link-bw {
   base "bgp-ls-topo-attr-type";
   description
     "BGP-LS TLV 1090. Maximum reservable link bandwidth";
   reference
     "RFC 9552: Distribution of Link-State and Traffic
      Engineering Information Using BGP.";
 }

 identity bgp-ls-topo-attr-unreserved-bw {
   base "bgp-ls-topo-attr-type";
   description
     "BGP-LS TLV 1091. Unreserved bandwidth";
   reference
     "RFC 9552: Distribution of Link-State and Traffic
      Engineering Information Using BGP.";
 }

 identity bgp-ls-topo-attr-te-default-metric {
   base "bgp-ls-topo-attr-type";
   description
     "BGP-LS TLV 1092. Traffic Engineering default metric";
   reference
     "RFC 9552: Distribution of Link-State and Traffic
      Engineering Information Using BGP.";
 }

 identity bgp-ls-topo-attr-link-protection-type {
   base "bgp-ls-topo-attr-type";
   description
     "BGP-LS TLV 1093. Link protection type";
   reference
     "RFC 9552: Distribution of Link-State and Traffic
      Engineering Information Using BGP.";
 }

 identity bgp-ls-topo-attr-mpls-protocol-mask {
   base "bgp-ls-topo-attr-type";
   description
     "BGP-LS TLV 1094. MPLS protocol mask";
   reference
     "RFC 9552: Distribution of Link-State and Traffic
      Engineering Information Using BGP.";
 }

 identity bgp-ls-topo-attr-igp-metric {
   base "bgp-ls-topo-attr-type";
   description
     "BGP-LS TLV 1095. IGP metric";
   reference
     "RFC 9552: Distribution of Link-State and Traffic
      Engineering Information Using BGP.";
 }

 identity bgp-ls-topo-attr-srlg {
   base "bgp-ls-topo-attr-type";
   description
     "BGP-LS TLV 1096. Shared Risk Link Group (SRLG)";
   reference
     "RFC 9552: Distribution of Link-State and Traffic
      Engineering Information Using BGP.";
 }

 identity bgp-ls-topo-attr-opaque-link {
   base "bgp-ls-topo-attr-type";
   description
     "BGP-LS TLV 1097. Envelope that transparently carries optional
      Link Attribute TLVs advertised by a router";
   reference
     "RFC 9552: Distribution of Link-State and Traffic
      Engineering Information Using BGP.";
 }

 identity bgp-ls-topo-attr-link-name {
   base "bgp-ls-topo-attr-type";
   description
     "BGP-LS TLV 1098. Symbolic name of a link";
   reference
     "RFC 9552: Distribution of Link-State and Traffic
      Engineering Information Using BGP.";
 }

 identity bgp-ls-topo-attr-adjacency-sid {
   base "bgp-ls-topo-attr-type";
   description
     "BGP-LS TLV 1099. Adjacency Segment Identifier (SID)";
   reference
     "RFC 9085: Border Gateway Protocol - Link State (BGP-LS)
      Extensions for Segment Routing";
 }
 identity bgp-ls-topo-attr-lan-adjacency-sid {
   base "bgp-ls-topo-attr-type";
   description
     "BGP-LS TLV 1100. LAN adjacency Segment Identifier (SID)";
   reference
     "RFC 9085: Border Gateway Protocol - Link State (BGP-LS)
      Extensions for Segment Routing";
 }

 identity bgp-ls-topo-attr-bgp-peer-node-sid {
   base "bgp-ls-topo-attr-type";
   description
     "BGP-LS TLV 1101. BGP peer node Segment Identifier (SID)";
   reference
     "RFC 9086: Border Gateway Protocol - Link State (BGP-LS)
      Extensions for Segment Routing";
 }

 identity bgp-ls-topo-attr-bgp-peer-adj-sid {
   base "bgp-ls-topo-attr-type";
   description
     "BGP-LS TLV 1102. BGP peer adjacency Segment Identifier
      (SID)";
   reference
     "RFC 9086: Border Gateway Protocol - Link State (BGP-LS)
      Extensions for Segment Routing";
 }

 identity bgp-ls-topo-attr-bgp-peer-set-sid {
   base "bgp-ls-topo-attr-type";
   description
     "BGP-LS TLV 1103. BGP peer set Segment Identifier (SID)";
   reference
     "RFC 9086: Border Gateway Protocol - Link State (BGP-LS)
      Extensions for Segment Routing";
 }

 identity bgp-ls-topo-attr-srv6-end-x-sid {
   base "bgp-ls-topo-attr-type";
   description
     "BGP-LS TLV 1106. SRv6 End.X SID";
   reference
     "RFC 9514: SRv6 BGP-LS extensions.";
 }

 identity bgp-ls-topo-attr-srv6-isis-lan-end-x-sid {
   base "bgp-ls-topo-attr-type";
   description
     "BGP-LS TLV 1107. SRv6 ISIS LAN End.X SID";
   reference
     "RFC 9514: SRv6 BGP-LS extensions.";
 }

 identity bgp-ls-topo-attr-srv6-ospf-lan-end-x-sid {
   base "bgp-ls-topo-attr-type";
   description
     "BGP-LS TLV 1108. SRv6 OSPF LAN End.X SID";
   reference
     "RFC 9514: SRv6 BGP-LS extensions.";
 }

 identity bgp-ls-topo-attr-unidir-link-delay {
   base "bgp-ls-topo-attr-type";
   description
     "BGP-LS TLV 1114. Unidirectional link delay";
   reference
     "RFC 8571: Link State (BGP-LS) Advertisement of IGP Traffic
      Engineering Performance Metric Extensions.";
 }

 identity bgp-ls-topo-attr-min-max-unidir-link-delay {
   base "bgp-ls-topo-attr-type";
   description
     "BGP-LS TLV 1115. Min/max unidirectional link delay";
   reference
     "RFC 8571: Link State (BGP-LS) Advertisement of IGP Traffic
      Engineering Performance Metric Extensions.";
 }

 identity bgp-ls-topo-attr-unidir-delay-variation {
   base "bgp-ls-topo-attr-type";
   description
     "BGP-LS TLV 1116. Unidirectional delay variation";
   reference
     "RFC 8571: Link State (BGP-LS) Advertisement of IGP Traffic
      Engineering Performance Metric Extensions.";
 }

 identity bgp-ls-topo-attr-unidir-link-loss {
   base "bgp-ls-topo-attr-type";
   description
     "BGP-LS TLV 1117. Unidirectional link loss";
   reference
     "RFC 8571: Link State (BGP-LS) Advertisement of IGP Traffic
      Engineering Performance Metric Extensions.";
 }
 identity bgp-ls-topo-attr-unidir-residual-bw {
   base "bgp-ls-topo-attr-type";
   description
     "BGP-LS TLV 1118. Unidirectional residual bandwidth";
   reference
     "RFC 8571: Link State (BGP-LS) Advertisement of IGP Traffic
      Engineering Performance Metric Extensions.";
 }

 identity bgp-ls-topo-attr-unidir-available-bw {
   base "bgp-ls-topo-attr-type";
   description
     "BGP-LS TLV 1119. Unidirectional available bandwidth";
   reference
     "RFC 8571: Link State (BGP-LS) Advertisement of IGP Traffic
      Engineering Performance Metric Extensions.";
 }

 identity bgp-ls-topo-attr-unidir-utilized-bw {
   base "bgp-ls-topo-attr-type";
   description
     "BGP-LS TLV 1120. Unidirectional utilized bandwidth";
   reference
     "RFC 8571: Link State (BGP-LS) Advertisement of IGP Traffic
      Engineering Performance Metric Extensions.";
 }

 identity bgp-ls-topo-attr-asla {
   base "bgp-ls-topo-attr-type";
   description
     "BGP-LS TLV 1122. Application-Specific Link Attributes";
   reference
     "RFC 9294: Application-Specific Link Attributes Advertisement
      Using the Border Gateway Protocol - Link State (BGP-LS).";
 }

 identity bgp-ls-topo-attr-igp-flags {
   base "bgp-ls-topo-attr-type";
   description
     "BGP-LS TLV 1152. Flags and bits assigned to a prefix";
   reference
     "RFC 9552: Distribution of Link-State and Traffic
      Engineering Information Using BGP.";
 }

 identity bgp-ls-topo-attr-igp-route-tag {
   base "bgp-ls-topo-attr-type";
   description
     "BGP-LS TLV 1153. Tags of a prefix";
   reference
     "RFC 9552: Distribution of Link-State and Traffic
      Engineering Information Using BGP.";
 }

 identity bgp-ls-topo-attr-ext-igp-route-tag {
   base "bgp-ls-topo-attr-type";
   description
     "BGP-LS TLV 1154. Extended route tags of a prefix";
   reference
     "RFC 9552: Distribution of Link-State and Traffic
      Engineering Information Using BGP.";
 }

 identity bgp-ls-topo-attr-prefix-metric {
   base "bgp-ls-topo-attr-type";
   description
     "BGP-LS TLV 1155. Metric of a prefix";
   reference
     "RFC 9552: Distribution of Link-State and Traffic
      Engineering Information Using BGP.";
 }

 identity bgp-ls-topo-attr-ospf-forwarding-address {
   base "bgp-ls-topo-attr-type";
   description
     "BGP-LS TLV 1156. Forwarding address of a prefix";
   reference
     "RFC 9552: Distribution of Link-State and Traffic
      Engineering Information Using BGP.";
 }

 identity bgp-ls-topo-attr-opaque-prefix {
   base "bgp-ls-topo-attr-type";
   description
     "BGP-LS TLV 1157. Envelope that transparently carries optional
      Prefix Attribute TLVs advertised by a router";
   reference
     "RFC 9552: Distribution of Link-State and Traffic
      Engineering Information Using BGP.";
 }

 identity bgp-ls-topo-attr-prefix-sid {
   base "bgp-ls-topo-attr-type";
   description
     "BGP-LS TLV 1158. Prefix Segment Identifiers (SIDs)";
   reference
     "RFC 9085: Border Gateway Protocol - Link State (BGP-LS)
      Extensions for Segment Routing";
 }

 identity bgp-ls-topo-attr-prefix-range {
   base "bgp-ls-topo-attr-type";
   description
     "BGP-LS TLV 1159. Range of prefix-to-SID mapping";
   reference
     "RFC 9085: Border Gateway Protocol - Link State (BGP-LS)
      Extensions for Segment Routing";
 }

 identity bgp-ls-topo-attr-srv6-locator {
   base "bgp-ls-topo-attr-type";
   description
     "BGP-LS TLV 1162. SRv6 locator information associated with a
      prefix";
   reference
     "RFC 9514: Border Gateway Protocol - Link State (BGP-LS)
      Extensions for Segment Routing over IPv6 (SRv6)";
 }

 identity bgp-ls-topo-attr-prefix-attribute-flags {
   base "bgp-ls-topo-attr-type";
   description
     "BGP-LS TLV 1170. Prefix attribute flags";
   reference
     "RFC 9085: Border Gateway Protocol - Link State (BGP-LS)
      Extensions for Segment Routing";
 }

 identity bgp-ls-topo-attr-prefix-src-router-id {
   base "bgp-ls-topo-attr-type";
   description
     "BGP-LS TLV 1171. Source route identifier of a prefix";
   reference
     "RFC 9085: Border Gateway Protocol - Link State (BGP-LS)
      Extensions for Segment Routing";
 }

 identity bgp-ls-topo-attr-l2-bundle-member {
   base "bgp-ls-topo-attr-type";
   description
     "BGP-LS TLV 1172. L2 bundle member";
   reference
     "RFC 9085: Border Gateway Protocol - Link State (BGP-LS)
      Extensions for Segment Routing";
 }

 identity bgp-ls-topo-attr-fa-prefix-metric {
   base "bgp-ls-topo-attr-type";
   description
     "BGP-LS TLV 1044. Flexible Algorithm prefix metric";
   reference
     "RFC 9351: Border Gateway Protocol - Link State (BGP-LS)
      Extensions for Flexible Algorithm Advertisement";
 }

 identity bgp-ls-topo-attr-srv6-endpoint-behavior {
   base "bgp-ls-topo-attr-type";
   description
     "SRv6 endpoint behavior";
   reference
     "RFC 9514: SRv6 BGP-LS extensions.";
 }

 identity bgp-ls-topo-attr-srv6-bgp-peer-node-sid {
   base "bgp-ls-topo-attr-type";
   description
     "SRv6 BGP peer node SID";
   reference
     "RFC 9514: SRv6 BGP-LS extensions.";
 }

 identity bgp-ls-topo-attr-srv6-sid-structure {
   base "bgp-ls-topo-attr-type";
   description
     "SRv6 SID structure";
   reference
     "RFC 9514: SRv6 BGP-LS extensions.";
 }

 identity bgp-ls-topo-attr-unknowns {
   base "bgp-ls-topo-attr-type";
   description
     "Unknown BGP-LS attribute TLVs.";
   reference
     "RFC 9552: Distribution of Link-State and Traffic Engineering
     Information Using BGP.";
 }
}
